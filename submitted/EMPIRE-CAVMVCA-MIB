--MibName=cavmvca
--
-- ========================================================================
--
--                             CA, INC.
--               Proprietary and Confidential Information
--
-- This material contains, and is part of a computer software program
-- which is, proprietary and confidential information owned by COMPUTER
-- ASSOCIATES INTERNATIONAL, INC.  The program, including this material,
-- may not be duplicated, disclosed or reproduced in whole or in part for
-- any purpose without the express written authorization of COMPUTER
-- ASSOCIATES. All authorized reproductions must be marked with this
-- legend.
--
--                          Copyright (c) 2010
--                          All rights reserved
--
--
-- ------------------------------------------------------------------------
-- Mib name: cavmvca

EMPIRE-CAVMVCA-MIB DEFINITIONS ::= BEGIN


IMPORTS
    OBJECT-TYPE
        FROM RFC-1212
    TRAP-TYPE
        FROM RFC-1215
    SnmpAdminString
        FROM SNMP-FRAMEWORK-MIB
    enterprises, TimeTicks, Gauge
        FROM RFC1155-SMI;

empire          OBJECT IDENTIFIER ::= { enterprises 546 }
unix            OBJECT IDENTIFIER ::= { empire 1 }
sysmgmt         OBJECT IDENTIFIER ::= { unix 1 }

traps           OBJECT IDENTIFIER ::= { empire 9 }
applications    OBJECT IDENTIFIER ::= { empire 16 }

cavmvcaim       OBJECT IDENTIFIER ::= { applications 52 }

--cavmvcaim MODULE-IDENTITY
--  LAST-UPDATED "201201240000Z"  
--  ORGANIZATION "CA Technologies, Inc."
--  CONTACT-INFO "http://www.ca.com"
--  DESCRIPTION  "This MIB module defines the 
--                CA Vmware vCenter Aim."

--  REVISION     "201201240000Z"
--  DESCRIPTION  "Added vCenter UUID to all status tables and appropriate traps."

--  REVISION     "201109200000Z"
--  DESCRIPTION  "Added vmvcAimStatNetFolderTable and supporting items.
--                Added vmvcAimStatVAppTable and supporting items.
--                Added vmvcAimStatVMvAppTable and supporting items."

--  REVISION     "201106300000Z"
--  DESCRIPTION  "Added vmvcAimStatHostCPUAvailableForVM.
--                Added vmvcAimStatHostTotalVMCPUUsage.
--                Added vmvcAimStatVMTotalHostMemoryUsage.
--                Widened size of vmvcAimStatHostDatastore.
--                Expanded varbind list of traps to support Multi-Instance VC AIM mode."

--  REVISION     "201105100000Z"
--  DESCRIPTION  "Deprecated vmvcAimStatCustomizationSpecLastUpdated.
--                Added vmvcAimStatCustomizationSpecLastUpdateTimeSec.
--                Fault Tolerance attributes added to vmvcAimStatHostTable and vmvcAimStatVMTable.
--                Added vmvcAimStatVMVDiskHostName.
--                Added vmvcAimStatVMVNICHostName.
--                Added vmvcAimStatCustomSpecUID.
--                Corrected varbind list for Datacenter State Change traps."

--  REVISION     "201102180000Z"
--  DESCRIPTION  "Added Distributed Virtual Switch and Port Group support.
--                Corrected enumeration for vmvcAimStatComputeResourceOverallState.
--                Added vmvcAimStatHostHardwareUUID.
--                Widened size of vmvcAimStatSnapshotDescription.

--  REVISION     "201010150000Z"
--  DESCRIPTION  "Added vmvcAimStatHostMaxSupportedVCPUs.
--                Added vmvcAimStatVMVDiskUnitNumber.
--                Added Disk Latency attributes to vmvcAimStatHostDiskTable.
--                Added vmvcAimStatHostVNICIpV6."

--  REVISION     "201009220000Z"
--  DESCRIPTION  "Added Multi-Instance Configuration support.
--                Widened enumeration of vmvcAimStatVMAlertHeartbeatLoss.
--                Added Port Group policy attributes to vmvcAimStatPortGrpTable.

--  REVISION     "201008200000Z"
--  DESCRIPTION  "Finalization of Single-Instance-Compatibility mode updates.
--                Addition of Local CPU and Memory attributes to vmvcAimStatVCTable.
--                Added vmvcAimStatVMSyncTimeWithHost."

--  REVISION     "201008122200Z"
--  DESCRIPTION  "Additional Single-Instance Compatibility mode updates."

--  REVISION     "201007292200Z" 
--  DESCRIPTION  "Supply VMKernelIP, StaticSwitch, StorageSensor, ResourcePool Type, and GuestDisk Enhancemements.  Single-Instance Compatibility mode updates."

--  REVISION     "201007071300Z" 
--  DESCRIPTION  "convert DisplayString elements to SnmpAdminString"

--  ::= { applications 52 }


vmvcAimConfigGroup      OBJECT IDENTIFIER ::= { cavmvcaim 1 }
vmvcAimStatGroup        OBJECT IDENTIFIER ::= { cavmvcaim 2 }
vmvcAimEventGroup       OBJECT IDENTIFIER ::= { cavmvcaim 4 }
vmvcAimVCEventGroup     OBJECT IDENTIFIER ::= { cavmvcaim 5 }

-- *****************************************************************************
-- Configuration Groups
-- *****************************************************************************
vmvcAimConfigGeneralGroup   OBJECT IDENTIFIER ::= { vmvcAimConfigGroup 1 }
vmvcAimConfigVCGroup        OBJECT IDENTIFIER ::= { vmvcAimConfigGroup 2 }
vmvcAimConfigMonitorGroup   OBJECT IDENTIFIER ::= { vmvcAimConfigGroup 3 }

-- *****************************************************************************
-- Monitor Configuration Groups
-- *****************************************************************************
vmvcAimConfigMonitorVCGroup         OBJECT IDENTIFIER ::= { vmvcAimConfigMonitorGroup 2 }
vmvcAimConfigMonitorDCGroup         OBJECT IDENTIFIER ::= { vmvcAimConfigMonitorGroup 5 }
vmvcAimConfigMonitorHostGroup       OBJECT IDENTIFIER ::= { vmvcAimConfigMonitorGroup 8 }
vmvcAimConfigMonitorResPoolGroup    OBJECT IDENTIFIER ::= { vmvcAimConfigMonitorGroup 9 }
vmvcAimConfigMonitorVMGroup         OBJECT IDENTIFIER ::= { vmvcAimConfigMonitorGroup 10 }
vmvcAimConfigMonitorNetworkGroup    OBJECT IDENTIFIER ::= { vmvcAimConfigMonitorGroup 12 }
vmvcAimConfigMonitorDiskGroup       OBJECT IDENTIFIER ::= { vmvcAimConfigMonitorGroup 13 }
vmvcAimConfigMonitorSensorGroup     OBJECT IDENTIFIER ::= { vmvcAimConfigMonitorGroup 14 }

-- *****************************************************************************
-- Network Monitor Configuration Groups
-- *****************************************************************************
vmvcAimConfigMonitorVSwitchGroup        OBJECT IDENTIFIER ::= { vmvcAimConfigMonitorNetworkGroup 1 }
vmvcAimConfigMonitorPNICGroup           OBJECT IDENTIFIER ::= { vmvcAimConfigMonitorNetworkGroup 3 }
vmvcAimConfigMonitorVMVNICGroup         OBJECT IDENTIFIER ::= { vmvcAimConfigMonitorNetworkGroup 5 }
vmvcAimConfigMonitorDistribVSwitchGroup OBJECT IDENTIFIER ::= { vmvcAimConfigMonitorNetworkGroup 7 }

-- *****************************************************************************
-- Disk Monitor Configuration Groups
-- *****************************************************************************
vmvcAimConfigMonitorDatastoreGroup      OBJECT IDENTIFIER ::= { vmvcAimConfigMonitorDiskGroup 1 }
vmvcAimConfigMonitorVMVDiskGroup        OBJECT IDENTIFIER ::= { vmvcAimConfigMonitorDiskGroup 2 }
vmvcAimConfigMonitorVMGuestDiskGroup    OBJECT IDENTIFIER ::= { vmvcAimConfigMonitorDiskGroup 5 }

-- *****************************************************************************
-- Sensor Monitor Configuration Groups
-- *****************************************************************************
vmvcAimConfigMonitorCPUSensorGroup      OBJECT IDENTIFIER ::= { vmvcAimConfigMonitorSensorGroup 1 }
vmvcAimConfigMonitorMemSensorGroup      OBJECT IDENTIFIER ::= { vmvcAimConfigMonitorSensorGroup 2 }
vmvcAimConfigMonitorFanSensorGroup      OBJECT IDENTIFIER ::= { vmvcAimConfigMonitorSensorGroup 3 }
vmvcAimConfigMonitorVoltageSensorGroup  OBJECT IDENTIFIER ::= { vmvcAimConfigMonitorSensorGroup 4 }
vmvcAimConfigMonitorTempSensorGroup     OBJECT IDENTIFIER ::= { vmvcAimConfigMonitorSensorGroup 5 }
vmvcAimConfigMonitorPowerSensorGroup    OBJECT IDENTIFIER ::= { vmvcAimConfigMonitorSensorGroup 6 }
vmvcAimConfigMonitorStorageSensorGroup  OBJECT IDENTIFIER ::= { vmvcAimConfigMonitorSensorGroup 7 }

-- *****************************************************************************
-- Status Groups
-- *****************************************************************************
vmvcAimStatGeneralGroup             OBJECT IDENTIFIER ::= { vmvcAimStatGroup 1 }
vmvcAimStatVCGroup                  OBJECT IDENTIFIER ::= { vmvcAimStatGroup 2 }
vmvcAimStatCustSpecGroup            OBJECT IDENTIFIER ::= { vmvcAimStatGroup 3 }
vmvcAimStatDCFolderGroup            OBJECT IDENTIFIER ::= { vmvcAimStatGroup 4 }
vmvcAimStatDCGroup                  OBJECT IDENTIFIER ::= { vmvcAimStatGroup 5 }
vmvcAimStatComputeResFolderGroup    OBJECT IDENTIFIER ::= { vmvcAimStatGroup 6 }
vmvcAimStatClusterGroup             OBJECT IDENTIFIER ::= { vmvcAimStatGroup 7 }
vmvcAimStatHostGroup                OBJECT IDENTIFIER ::= { vmvcAimStatGroup 8 }
vmvcAimStatResPoolGroup             OBJECT IDENTIFIER ::= { vmvcAimStatGroup 9 }
vmvcAimStatVMGroup                  OBJECT IDENTIFIER ::= { vmvcAimStatGroup 10 }
vmvcAimStatTemplateGroup            OBJECT IDENTIFIER ::= { vmvcAimStatGroup 11 }
vmvcAimStatNetworkGroup             OBJECT IDENTIFIER ::= { vmvcAimStatGroup 12 }
vmvcAimStatDiskGroup                OBJECT IDENTIFIER ::= { vmvcAimStatGroup 13 }
vmvcAimStatSensorGroup              OBJECT IDENTIFIER ::= { vmvcAimStatGroup 14 }
vmvcAimStatSnapshotGroup            OBJECT IDENTIFIER ::= { vmvcAimStatGroup 15 }


-- *****************************************************************************
-- Status disk Groups
-- *****************************************************************************
vmvcAimStatDatastoreGroup       OBJECT IDENTIFIER ::= { vmvcAimStatDiskGroup 1 }
vmvcAimStatVMVDiskGroup         OBJECT IDENTIFIER ::= { vmvcAimStatDiskGroup 2 }
vmvcAimStatHostDiskGroup        OBJECT IDENTIFIER ::= { vmvcAimStatDiskGroup 3 }
vmvcAimStatSCSIControllerGroup  OBJECT IDENTIFIER ::= { vmvcAimStatDiskGroup 4 }
vmvcAimStatVMGuestDiskGroup     OBJECT IDENTIFIER ::= { vmvcAimStatDiskGroup 5 }

-- *****************************************************************************
-- Status network Groups
-- *****************************************************************************
vmvcAimStatVSwitchGroup         OBJECT IDENTIFIER ::= { vmvcAimStatNetworkGroup 1 }
vmvcAimStatPortGrpGroup         OBJECT IDENTIFIER ::= { vmvcAimStatNetworkGroup 2 }
vmvcAimStatPNICGroup            OBJECT IDENTIFIER ::= { vmvcAimStatNetworkGroup 3 }
vmvcAimStatHostVNICGroup        OBJECT IDENTIFIER ::= { vmvcAimStatNetworkGroup 4 }
vmvcAimStatVMVNICGroup          OBJECT IDENTIFIER ::= { vmvcAimStatNetworkGroup 5 }
vmvcAimStatCustomSpecNICGroup   OBJECT IDENTIFIER ::= { vmvcAimStatNetworkGroup 6 }
vmvcAimStatDistribVSwitchGroup  OBJECT IDENTIFIER ::= { vmvcAimStatNetworkGroup 7 }
vmvcAimStatDVPortGrpGroup       OBJECT IDENTIFIER ::= { vmvcAimStatNetworkGroup 8 }

-- *****************************************************************************
-- Status Sensor Groups
-- *****************************************************************************
vmvcAimStatCPUSensorGroup       OBJECT IDENTIFIER ::= { vmvcAimStatSensorGroup 1 }
vmvcAimStatMemSensorGroup       OBJECT IDENTIFIER ::= { vmvcAimStatSensorGroup 2 }
vmvcAimStatFanSensorGroup       OBJECT IDENTIFIER ::= { vmvcAimStatSensorGroup 3 }
vmvcAimStatVoltageSensorGroup   OBJECT IDENTIFIER ::= { vmvcAimStatSensorGroup 4 }
vmvcAimStatTempSensorGroup      OBJECT IDENTIFIER ::= { vmvcAimStatSensorGroup 5 }
vmvcAimStatPowerSensorGroup     OBJECT IDENTIFIER ::= { vmvcAimStatSensorGroup 6 }
vmvcAimStatStorageSensorGroup   OBJECT IDENTIFIER ::= { vmvcAimStatSensorGroup 7 }


-- *****************************************************************************
-- General Config Group
-- *****************************************************************************
vmvcAimConfigGeneralAgentName OBJECT-TYPE
    SYNTAX SnmpAdminString
    ACCESS read-only
    STATUS mandatory
    DESCRIPTION
        "The name of the agent."
    ::= { vmvcAimConfigGeneralGroup 1 }

vmvcAimConfigGeneralAgentVersion OBJECT-TYPE
    SYNTAX SnmpAdminString
    ACCESS read-only
    STATUS mandatory
    DESCRIPTION
        "The currently installed version of the agent."
    ::= { vmvcAimConfigGeneralGroup 2 }

vmvcAimConfigGeneralColdStartTime OBJECT-TYPE
    SYNTAX TimeTicks
    ACCESS read-only
    STATUS mandatory
    DESCRIPTION
        "The number of time-ticks the AIM has been running."
    ::= { vmvcAimConfigGeneralGroup 3 }

vmvcAimConfigGeneralPollInterval OBJECT-TYPE
    SYNTAX INTEGER
    ACCESS read-write
    STATUS mandatory
    DESCRIPTION
        "The time (in seconds) between the polling by the Agent. Valid values are greater than or equal to 30.
         NOTE:  This parameter is deprecated, and is only accessible when the AIM is in single-instance
                compatibility mode."
    DEFVAL { 120 }
    ::= { vmvcAimConfigGeneralGroup 4 }

vmvcAimConfigGeneralAgentHostName OBJECT-TYPE
    SYNTAX SnmpAdminString
    ACCESS read-only
    STATUS mandatory
    DESCRIPTION
        "The host name on which this agent is running."
    ::= { vmvcAimConfigGeneralGroup 5 }

vmvcAimConfigGeneralWRSLastTime OBJECT-TYPE
    SYNTAX TimeTicks
    ACCESS read-only
    STATUS mandatory
    DESCRIPTION
        "The number of time-ticks since the AIM has fetched the event table.
         NOTE:  This parameter is deprecated, and is only accessible when the AIM is in single-instance
                compatibility mode."
    ::= { vmvcAimConfigGeneralGroup 6 }

vmvcAimConfigGeneralVCEventPoll OBJECT-TYPE
    SYNTAX INTEGER
    ACCESS read-write
    STATUS mandatory
    DESCRIPTION
        "The time (in seconds) between the polling of VC Events by the Agent. Valid values are greater than 
         or equal to 120.
         NOTE:  This parameter is deprecated, and is only accessible when the AIM is in single-instance
                compatibility mode."
    DEFVAL { 120 }
    ::= { vmvcAimConfigGeneralGroup 7 }

vmvcAimConfigGeneralVCEventEnable OBJECT-TYPE
    SYNTAX INTEGER {
        collectAndTrap(1),
        collect(2),
        disable(3)
    }
    ACCESS read-write
    STATUS mandatory
    DESCRIPTION
        "VC Events capturing is enabled or disabled.
         NOTE:  This parameter is deprecated, and is only accessible when the AIM is in single-instance
                compatibility mode."
    DEFVAL { 3 }
    ::= { vmvcAimConfigGeneralGroup 8 }

vmvcAimConfigGeneralVCEventMonitorInfo OBJECT-TYPE
    SYNTAX INTEGER {
        enable(1),
        disable(2)
    }
    ACCESS read-write
    STATUS mandatory
    DESCRIPTION
        "VC Events Info messages capturing is enabled or disabled.
         NOTE:  This parameter is deprecated, and is only accessible when the AIM is in single-instance
                compatibility mode."
    DEFVAL { 2 }
    ::= { vmvcAimConfigGeneralGroup 9 }

vmvcAimConfigGeneralVCEventMonitorUser OBJECT-TYPE
    SYNTAX INTEGER {
        enable(1),
        disable(2)
    }
    ACCESS read-write
    STATUS mandatory
    DESCRIPTION
        "VC Events User messages capturing is enabled or disabled.
         NOTE:  This parameter is deprecated, and is only accessible when the AIM is in single-instance
                compatibility mode."
    DEFVAL { 2 }
    ::= { vmvcAimConfigGeneralGroup 10 }

vmvcAimConfigGeneralVCEventMonitorError OBJECT-TYPE
    SYNTAX INTEGER {
        enable(1),
        disable(2)
    }
    ACCESS read-write
    STATUS mandatory
    DESCRIPTION
        "VC Events Error messages capturing is enabled or disabled.
         NOTE:  This parameter is deprecated, and is only accessible when the AIM is in single-instance
                compatibility mode."
    DEFVAL { 2 }
    ::= { vmvcAimConfigGeneralGroup 11 }

vmvcAimConfigGeneralVCEventMonitorWarning OBJECT-TYPE
    SYNTAX INTEGER {
        enable(1),
        disable(2)
    }
    ACCESS read-write
    STATUS mandatory
    DESCRIPTION
        "VC Events Warning messages capturing is enabled or disabled.
         NOTE:  This parameter is deprecated, and is only accessible when the AIM is in single-instance
                compatibility mode."
    DEFVAL { 2 }
    ::= { vmvcAimConfigGeneralGroup 12 }

vmvcAimConfigGeneralTrapEnableMask OBJECT-TYPE
    SYNTAX INTEGER (0..7)
    ACCESS read-write
    STATUS mandatory
    DESCRIPTION
        "A set of flags to enable classes of traps to be 
         sent by the AIM.  See the individual AIM traps for specifics
             as to which flag enables it.
         The flags are:
         0x1    Send Detected VC Change Traps
         0x2    Send Detected AIM State Change Traps
         0x4    Send AIM Configuration Change Traps"
    DEFVAL { 7 }
    ::= { vmvcAimConfigGeneralGroup 13 }

vmvcAimConfigGeneralLogLevel OBJECT-TYPE
    SYNTAX INTEGER (0..7)
    ACCESS read-write
    STATUS mandatory
    DESCRIPTION
        "The Log Level of the AIM.  This impacts how much logging
         will be written to the AIM log file, and is cumulative (i.e.
         Log Level 4 will get all messages at levels 0 through 4).
         Values are:
         0    FATAL
         1    CRITICAL
         2    WARNING
         3    INFO
         4    DEBUG
         5    DEBUG_LOW
         6    DEBUG_LOWER
         7    DEBUG_LOWEST
         Specifying a debug level greater than 4 is discouraged."
    DEFVAL { 2 }
    ::= { vmvcAimConfigGeneralGroup 14 }

vmvcAimConfigGeneralVCHostName OBJECT-TYPE
    SYNTAX SnmpAdminString
    ACCESS read-write
    STATUS mandatory
    DESCRIPTION
        "The (remote of local) vCenter host name.  This is used for
         connecting to the vCenter Web Service.
         NOTE:  This parameter is deprecated, and is only accessible when the AIM is in single-instance
                compatibility mode."
    ::= { vmvcAimConfigGeneralGroup 15 }

vmvcAimConfigGeneralVCUserName OBJECT-TYPE
    SYNTAX SnmpAdminString
    ACCESS read-write
    STATUS mandatory
    DESCRIPTION
        "The user name for connecting to the vCenter Web Service.
         Please note that this entry can be seen correctly using SNMP GET, but MUST BE encrypted prior 
         to SNMP SET, meaning that only compliant SNMP managers can configure this entry properly.
         NOTE:  This parameter is deprecated, and is only accessible when the AIM is in single-instance
                compatibility mode."
    ::= { vmvcAimConfigGeneralGroup 16 }

vmvcAimConfigGeneralVCPassword OBJECT-TYPE
    SYNTAX SnmpAdminString
    ACCESS read-write
    STATUS mandatory
    DESCRIPTION
        "The encrypted password for connecting to the vCenter Web Service.
         Please note that this entry must be encrypted prior to setting, meaning
         that only compliant SNMP managers can configure this entry properly.
         This parameter can NEVER been seen correctly using SNMP GET.
         NOTE:  This parameter is deprecated, and is only accessible when the AIM is in single-instance
                compatibility mode."
    ::= { vmvcAimConfigGeneralGroup 17 }

vmvcAimConfigGeneralVCProtocol OBJECT-TYPE
    SYNTAX SnmpAdminString
    ACCESS read-write
    STATUS mandatory
    DESCRIPTION
        "The protocol (https or http) for connecting to the vCenter Web Service.
         This agent will use https as the default protocol unless changed here.
         NOTE:  This parameter is deprecated, and is only accessible when the AIM is in single-instance
                compatibility mode."
    ::= { vmvcAimConfigGeneralGroup 18 }

vmvcAimConfigGeneralVCPort OBJECT-TYPE
    SYNTAX INTEGER
    ACCESS read-write
    STATUS mandatory
    DESCRIPTION
        "The port number for connecting to the vCenter Web Service.
         NOTE:  This parameter is deprecated, and is only accessible when the AIM is in single-instance
                compatibility mode."
    DEFVAL { 443 }
    ::= { vmvcAimConfigGeneralGroup 19 }

vmvcAimConfigGeneralPollerStatus OBJECT-TYPE
    SYNTAX INTEGER {
        active(1),
        notInService(2),
        notReady(3),
        createAndGo(4)
    }
    ACCESS read-write
    STATUS mandatory
    DESCRIPTION
        "The status of this Virtual Center AIM according to the Textual Conventions for SNMPv2 (see RFC 1443).  Specifics for each status:
         active(1) - The AIM is currently communicating successfully to the Virtual Center. (ReadOnly value)
         notInService(2) - Setting to this vlaue disables polling on the AIM (and allows for reconfiguration). (Writable value)
         notReady(3) - The AIM has identified a problem communicating to the Virtual Center. (ReadOnly value)
         createAndGo(4) - Setting to this value will reactivate AIM and validate Virtual Center credentials as needed. (Writable value)
         NOTE:  This parameter is deprecated, and is only accessible when the AIM is in single-instance
                compatibility mode."
    ::= { vmvcAimConfigGeneralGroup 20 }


-- *****************************************************************************
-- VC Config Group
-- *****************************************************************************
vmvcAimConfigVCCount OBJECT-TYPE
    SYNTAX INTEGER
    ACCESS read-only
    STATUS mandatory
    DESCRIPTION
        "Number of Virtual Center Instances in vmvcAimConfigVCTable."
    ::= {vmvcAimConfigVCGroup 1}

vmvcAimConfigVCUnusedIndex OBJECT-TYPE
    SYNTAX INTEGER
    ACCESS read-only
    STATUS mandatory
    DESCRIPTION
        "An SNMP GET of this attribute returns an unused VC UID.  This
         is normally used to expedite safe table row creation."
    ::= {vmvcAimConfigVCGroup  2 }

vmvcAimConfigVCTable OBJECT-TYPE
    SYNTAX SEQUENCE OF VmvcAimConfigVCRow
    ACCESS not-accessible
    STATUS mandatory
    DESCRIPTION
        "A table containing the Virtual Center Instances."
    ::= { vmvcAimConfigVCGroup 3 }

vmvcAimConfigVCEntry OBJECT-TYPE
    SYNTAX VmvcAimConfigVCRow
    ACCESS not-accessible
    STATUS mandatory
    DESCRIPTION
        "The Virtual Center Instances Table entry."
    INDEX { vmvcAimConfigVCUID }
    ::= { vmvcAimConfigVCTable 1 }

VmvcAimConfigVCRow ::=
    SEQUENCE {
        vmvcAimConfigVCUID                  INTEGER,
        vmvcAimConfigVCHostName             SnmpAdminString,
        vmvcAimConfigVCUserName             SnmpAdminString,
        vmvcAimConfigVCPassword             SnmpAdminString,
        vmvcAimConfigVCProtocol             SnmpAdminString,
        vmvcAimConfigVCPort                 INTEGER,
        vmvcAimConfigVCPollInterval         INTEGER,
        vmvcAimConfigVCLastPollTime         TimeTicks,
        vmvcAimConfigVCRefreshInterval      INTEGER,
        vmvcAimConfigVCLastRefreshTime      TimeTicks,
        vmvcAimConfigVCEventPollInterval    INTEGER,
        vmvcAimConfigVCEventLastPollTime    TimeTicks,
        vmvcAimConfigVCEventEnable          INTEGER,
        vmvcAimConfigVCEventMonitorInfo     INTEGER,
        vmvcAimConfigVCEventMonitorUser     INTEGER,
        vmvcAimConfigVCEventMonitorWarning  INTEGER,
        vmvcAimConfigVCEventMonitorError    INTEGER,
        vmvcAimConfigVCRowStatus            INTEGER,
        vmvcAimConfigVCDataStatus           INTEGER
    }

vmvcAimConfigVCUID OBJECT-TYPE
    SYNTAX INTEGER (1..2147483647)
    ACCESS read-only
    STATUS mandatory
    DESCRIPTION
        "Integer UID of Virtual Center Instance."
    ::= { vmvcAimConfigVCEntry  1}

vmvcAimConfigVCHostName OBJECT-TYPE
    SYNTAX SnmpAdminString
    ACCESS read-write
    STATUS mandatory
    DESCRIPTION
        "Host Name of the Virtual Center Instance.  Once a VC instance 
         row is added in this table, the VCName is no longer writeable."
    ::= { vmvcAimConfigVCEntry  2}

vmvcAimConfigVCUserName OBJECT-TYPE
    SYNTAX SnmpAdminString
    ACCESS read-write
    STATUS mandatory
    DESCRIPTION
        "The user name for connecting to this Virtual Center Instance.
         Please note that this entry can be seen correctly using SNMP GET, but MUST BE encrypted prior 
         to SNMP SET, meaning that only compliant SNMP managers can configure this entry properly."
    ::= { vmvcAimConfigVCEntry  3 }

vmvcAimConfigVCPassword OBJECT-TYPE
    SYNTAX SnmpAdminString
    ACCESS read-write
    STATUS mandatory
    DESCRIPTION
        "The encrypted password for connecting to this Virtual Center Instance.
         Please note that this entry must be encrypted prior to setting, meaning
         that only compliant SNMP managers can configure this entry properly.
         This parameter can NEVER been seen correctly using SNMP GET."
    ::= { vmvcAimConfigVCEntry  4 }

vmvcAimConfigVCProtocol OBJECT-TYPE
    SYNTAX SnmpAdminString
        ACCESS read-write
        STATUS mandatory
        DESCRIPTION
            "Protocol for connecting to this Virtual Center Instance. Valid
         choices are 'http' or 'https'. Default is 'https'."
    ::= { vmvcAimConfigVCEntry  5 }

vmvcAimConfigVCPort OBJECT-TYPE
    SYNTAX INTEGER
        ACCESS read-write
        STATUS mandatory
        DESCRIPTION
            "Port designation for connecting to this Virtual Center Instance."
    DEFVAL { 443 }
    ::= { vmvcAimConfigVCEntry  6 }

vmvcAimConfigVCPollInterval OBJECT-TYPE
    SYNTAX INTEGER
    ACCESS read-write
    STATUS mandatory
    DESCRIPTION
        "The wait time (in SECONDS) between the standard polling 
         requests by the AIM (timed from the end of the previous poll 
         to the beginning of the next poll). 
         Valid values are 30-3600 sec.  This polling involves 
         retrieving performance metrics and event-driven VC 
         occurrences.  Objects which cannot be retrieved using VC 
         event-driven mechanisms will be polled normally.  These are:
            Datastores
            Customization Specifications
            Sensors (ALL)"
    DEFVAL { 120 }
    ::= { vmvcAimConfigVCEntry  7 }

vmvcAimConfigVCLastPollTime OBJECT-TYPE
    SYNTAX TimeTicks
    ACCESS read-only
    STATUS mandatory
    DESCRIPTION
        "The amount of time since the last successful standard poll."
    ::= { vmvcAimConfigVCEntry  8 }

vmvcAimConfigVCRefreshInterval OBJECT-TYPE
    SYNTAX INTEGER
    ACCESS read-write
    STATUS mandatory
    DESCRIPTION
        "The time (in SECONDS) between full VC refresh of the AIM.
         This refresh is very CPU-intensive, and is normally done on a
         daily basis (i.e. 86400 secs).
         Valid values are 30-604800 seconds (1 week), and must be 
         greater than or equal to vmvcAimConfigVCPollInterval.
         [Strongly suggested to perform this refresh very infrequently, 
          especially for large VC instances.]"
    DEFVAL { 14400 }
    ::= { vmvcAimConfigVCEntry  9 }

vmvcAimConfigVCLastRefreshTime OBJECT-TYPE
    SYNTAX TimeTicks
    ACCESS read-only
    STATUS mandatory
    DESCRIPTION
        "The amount of time since the last successful full VC refresh."
    ::= { vmvcAimConfigVCEntry  10 }

vmvcAimConfigVCEventPollInterval OBJECT-TYPE
    SYNTAX INTEGER
    ACCESS read-write
    STATUS mandatory
    DESCRIPTION
        "The wait time (in SECONDS) between the standard polling 
         requests by the AIM (timed from the end of the previous poll 
         to the beginning of the next poll). Valid values are 30-86400 sec.
         This polling only applies when Event retrieval is enabled (via
         vmvcAimConfigVCEventEnable)."
    DEFVAL { 120 }
    ::= { vmvcAimConfigVCEntry  11 }

vmvcAimConfigVCEventLastPollTime OBJECT-TYPE
    SYNTAX TimeTicks
    ACCESS read-only
    STATUS mandatory
    DESCRIPTION
        "The number of time-ticks since the AIM has fetched 
         the VC Event table."
    ::= { vmvcAimConfigVCEntry  12 }

vmvcAimConfigVCEventEnable OBJECT-TYPE
    SYNTAX INTEGER {
        collectAndTrap(1),
        collect(2),
        disable(3)
    }
    ACCESS read-write
    STATUS mandatory
    DESCRIPTION
        "VC Events capturing is enabled or disabled"
    DEFVAL { 3 }
    ::= { vmvcAimConfigVCEntry  13 }

vmvcAimConfigVCEventMonitorInfo OBJECT-TYPE
    SYNTAX INTEGER {
        enable(1),
        disable(2)
    }
    ACCESS read-write
    STATUS mandatory
    DESCRIPTION
        "VC Events Info messages capturing is enabled or disabled"
    DEFVAL { 2 }
    ::= { vmvcAimConfigVCEntry  14 }

vmvcAimConfigVCEventMonitorUser OBJECT-TYPE
    SYNTAX INTEGER {
        enable(1),
        disable(2)
    }
    ACCESS read-write
    STATUS mandatory
    DESCRIPTION
        "VC Events User messages capturing is enabled or disabled"
    DEFVAL { 2 }
    ::= { vmvcAimConfigVCEntry  15 }

vmvcAimConfigVCEventMonitorWarning OBJECT-TYPE
    SYNTAX INTEGER {
        enable(1),
        disable(2)
    }
    ACCESS read-write
    STATUS mandatory
    DESCRIPTION
        "VC Events Warning messages capturing is enabled or disabled"
    DEFVAL { 2 }
    ::= { vmvcAimConfigVCEntry  16 }

vmvcAimConfigVCEventMonitorError OBJECT-TYPE
    SYNTAX INTEGER {
        enable(1),
        disable(2)
    }
    ACCESS read-write
    STATUS mandatory
    DESCRIPTION
        "VC Events Error messages capturing is enabled or disabled"
    DEFVAL { 2 }
    ::= { vmvcAimConfigVCEntry  17 }

vmvcAimConfigVCRowStatus OBJECT-TYPE
    SYNTAX INTEGER {
        active(1),
        notInService(2),
        notReady(3),
        createAndGo(4),
        createAndWait(5),
        destroy(6)
    }
    ACCESS read-write
    STATUS mandatory
    DESCRIPTION
        "The status of this Virtual Center Instance entry according 
         to the Textual Conventions for SNMPv2 (see RFC 1443).
         active(1)        - The AIM is currently communicating with this VC instance.
         notInService(2)  - Setting to this value disables polling of this VC instance.
         notReady(3)      - The AIM has identified a problem polling this VC instance.  Refer to vmvcAimConfigVCDataStatus for additional info.
         createAndGo(4)   - Setting to this value creates the VC Instance row with row status set to active(1).
         createAndWait(5) - Setting to this value creates the VC Instance row with row status set to notInService(2).
         destroy(6)       - Setting to this value deletes the VC Instance row."
    DEFVAL { 4 }
    ::= { vmvcAimConfigVCEntry  18 }

vmvcAimConfigVCDataStatus OBJECT-TYPE
    SYNTAX INTEGER {
        ready(1),
        notReady(2),
        connectionFailed(3),
        unknownError(4)
    }
    ACCESS read-only
    STATUS mandatory
    DESCRIPTION
        "The status of data retrieval processing for this Virtual
         Center Instance.
         ready(1)            - VC Instance ready, AIM cache populated
         notReady(2)         - VC Instance not ready, AIM cache not yet populated
         connectionFailed(3) - VC Instance connection failed, perhaps credential issue or unavailable VC Instance.  AIM cache retained if populated.
         unknownError(4)     - Unknown Error, AIM cache retained if populated."
    ::= { vmvcAimConfigVCEntry 19 }


-- *****************************************************************************
-- VC Monitor Configuration Group
-- *****************************************************************************
vmvcAimConfigMonServerUpdate OBJECT-TYPE
    SYNTAX INTEGER{
        done(1),
        update(2)
        }
    ACCESS read-write
    STATUS mandatory
    DESCRIPTION
        "One-shot trigger to update all configured VC Servers with 
         Monitoring configuration for all monitoring parameters.
         When completed, Agent will set this attribute to done(1).
         NOTE:  Only monitoring parameters will be updated using this trigger.
         Communication credentials and polling interval parameters will not be 
         updated."
    DEFVAL { 1 }
    ::= { vmvcAimConfigMonitorVCGroup 1 }

vmvcAimConfigMonVCProtocol OBJECT-TYPE
    SYNTAX SnmpAdminString
    ACCESS read-write
    STATUS mandatory
    DESCRIPTION
        "Protocol for connecting to this Virtual Center Instance. Valid
         choices are 'http' or 'https'. Default is 'https'.  The value of this
         attribute is used as a default value for created objects."
     ::= { vmvcAimConfigMonitorVCGroup 2 }

vmvcAimConfigMonVCPort OBJECT-TYPE
    SYNTAX INTEGER
    ACCESS read-write
    STATUS mandatory
    DESCRIPTION
        "Port designation for connecting to this Virtual Center Instance.
         The value of this attribute is used as a default value for created 
         objects."
    DEFVAL { 443 }
    ::= { vmvcAimConfigMonitorVCGroup 3 }

vmvcAimConfigMonVCPollInterval OBJECT-TYPE
    SYNTAX INTEGER
    ACCESS read-write
    STATUS mandatory
    DESCRIPTION
        "The wait time (in SECONDS) between the standard polling 
         requests by the AIM (timed from the end of the previous poll 
         to the beginning of the next poll). 
         Valid values are 30-3600 sec.  This polling involves 
         retrieving performance metrics and event-driven VC 
         occurrences.  Objects which cannot be retrieved using VC 
         event-driven mechanisms will be polled normally.  These are:
            Datastores
            Customization Specifications
            Sensors (ALL)
         The value of this attribute is used as a default value for created
         objects."
    DEFVAL { 120 }
    ::= { vmvcAimConfigMonitorVCGroup 4 }

vmvcAimConfigMonVCRefreshInterval OBJECT-TYPE
    SYNTAX INTEGER
    ACCESS read-write
    STATUS mandatory
    DESCRIPTION
        "The time (in SECONDS) between full VC refresh of the AIM.
         This refresh is very CPU-intensive, and is normally done on a
         daily basis (i.e. 86400 secs).
         Valid values are 30-604800 seconds (1 week), and must be 
         greater than or equal to vmvcAimConfigVCPollInterval.
         [Strongly suggested to perform this refresh very infrequently, 
          especially for large VC instances.]
         The value of this attribute is used as a default value for created
         objects."
    DEFVAL { 14400 }
    ::= { vmvcAimConfigMonitorVCGroup 5 }

vmvcAimConfigMonVCEventPollInterval OBJECT-TYPE
    SYNTAX INTEGER
    ACCESS read-write
    STATUS mandatory
    DESCRIPTION
        "The wait time (in SECONDS) between the standard polling 
         requests by the AIM (timed from the end of the previous poll 
         to the beginning of the next poll). Valid values are 30-86400 sec.
         This polling only applies when Event retrieval is enabled (via
         vmvcAimConfigVCEventEnable).  The value of this attribute is used 
         as a default value for created objects."
    DEFVAL { 120 }
    ::= { vmvcAimConfigMonitorVCGroup 6 }

vmvcAimConfigMonVCEventEnable OBJECT-TYPE
    SYNTAX INTEGER {
        collectAndTrap(1),
        collect(2),
        disable(3)
    }
    ACCESS read-write
    STATUS mandatory
    DESCRIPTION
        "VC Events capturing is enabled or disabled.  The value of this 
         attribute is used as a default value for created objects."
    DEFVAL { 3 }
    ::= { vmvcAimConfigMonitorVCGroup 7 }

vmvcAimConfigMonVCEventMonitorInfo OBJECT-TYPE
    SYNTAX INTEGER {
        enable(1),
        disable(2)
    }
    ACCESS read-write
    STATUS mandatory
    DESCRIPTION
        "VC Events Info messages capturing is enabled or disabled.  The value 
         of this attribute is used as a default value for created objects."
    DEFVAL { 2 }
    ::= { vmvcAimConfigMonitorVCGroup 8 }

vmvcAimConfigMonVCEventMonitorUser OBJECT-TYPE
    SYNTAX INTEGER {
        enable(1),
        disable(2)
    }
    ACCESS read-write
    STATUS mandatory
    DESCRIPTION
        "VC Events User messages capturing is enabled or disabled.  The value 
         of this attribute is used as a default value for created objects."
    DEFVAL { 2 }
    ::= { vmvcAimConfigMonitorVCGroup 9 }

vmvcAimConfigMonVCEventMonitorWarning OBJECT-TYPE
    SYNTAX INTEGER {
        enable(1),
        disable(2)
    }
    ACCESS read-write
    STATUS mandatory
    DESCRIPTION
        "VC Events Warning messages capturing is enabled or disabled.  The value 
         of this attribute is used as a default value for created objects."
    DEFVAL { 2 }
    ::= { vmvcAimConfigMonitorVCGroup 10 }

vmvcAimConfigMonVCEventMonitorError OBJECT-TYPE
    SYNTAX INTEGER {
        enable(1),
        disable(2)
    }
    ACCESS read-write
    STATUS mandatory
    DESCRIPTION
        "VC Events Error messages capturing is enabled or disabled.  The value 
         of this attribute is used as a default value for created objects."
    DEFVAL { 2 }
    ::= { vmvcAimConfigMonitorVCGroup 11 }

vmvcAimConfigMonServerStatusAlert OBJECT-TYPE
    SYNTAX INTEGER{
        not-running-warn(1),
        not-running-crit(2)
        }
    ACCESS read-write
    STATUS mandatory
    DESCRIPTION
        "Type of alert for server status, based on the value of 
         vmvcAimConfigVCRowStatus.  The value of this attribute 
         is used as a default value for newly configured servers."
    DEFVAL { 2 }
    ::= { vmvcAimConfigMonitorVCGroup 12 }

vmvcAimConfigMonServerStatusMonitor OBJECT-TYPE
    SYNTAX INTEGER{
        do-not-monitor(1),
        monitor(2)
        }
    ACCESS read-write
    STATUS mandatory
    DESCRIPTION
        "Monitor state of VC Service Status.  The value of this 
         attribute is used as a default value for newly configured 
         servers."
    DEFVAL { 2 }
    ::= { vmvcAimConfigMonitorVCGroup 13 }

vmvcAimConfigMonServerLocalCPUUsageWarn OBJECT-TYPE
    SYNTAX INTEGER
    ACCESS read-write
    STATUS mandatory
    DESCRIPTION
        "Warning threshold for the CPU usage of the Local VC server.
         The value of this attribute is used as a default 
         value for newly configured servers."
    DEFVAL { 60 }
    ::= { vmvcAimConfigMonitorVCGroup 14 }

vmvcAimConfigMonServerLocalCPUUsageCrit OBJECT-TYPE
    SYNTAX INTEGER
    ACCESS read-write
    STATUS mandatory
    DESCRIPTION
        "Critical threshold for the CPU usage of the Local VC server.
         The value of this attribute is used as a default 
         value for newly configured servers."
    DEFVAL { 80 }
    ::= { vmvcAimConfigMonitorVCGroup 15 }

vmvcAimConfigMonServerLocalCPUUsageAlert OBJECT-TYPE
    SYNTAX INTEGER{
        warning-only(1),
        critical-only(2),
        both(3)
        }
    ACCESS read-write
    STATUS mandatory
    DESCRIPTION
        "Type of alert for the CPU usage of the Local VC server.
         The value of this attribute is used as a default 
         value for newly configured servers."
    DEFVAL { 3 }
    ::= { vmvcAimConfigMonitorVCGroup 16 }

vmvcAimConfigMonServerLocalCPUMonitor OBJECT-TYPE
    SYNTAX INTEGER{
        do-not-monitor(1),
        monitor(2)
        }
    ACCESS read-write
    STATUS mandatory
    DESCRIPTION
        "Type of monitoring for the CPU usage of the Local VC server.
         The value of this attribute is used as a default 
         value for newly configured servers."
    DEFVAL { 2 }
    ::= { vmvcAimConfigMonitorVCGroup 17 }

vmvcAimConfigMonServerLocalCPULagSetting OBJECT-TYPE
    SYNTAX INTEGER
    ACCESS read-write
    STATUS mandatory
    DESCRIPTION
        "The number of times the threshold should be breached before
         the status change occurs for the CPU usage of the Local VC server.
         The value of this attribute is used as a default 
         value for newly configured servers."
    DEFVAL { 3 }
    ::= { vmvcAimConfigMonitorVCGroup 18 }

vmvcAimConfigMonServerLocalMemoryWarn OBJECT-TYPE
    SYNTAX INTEGER
    ACCESS read-write
    STATUS mandatory
    DESCRIPTION
        "Warning threshold for the memory of the Local VC server.
         The value of this attribute is used as a default 
         value for newly configured servers."
    DEFVAL { 60 }
    ::= { vmvcAimConfigMonitorVCGroup 19 }

vmvcAimConfigMonServerLocalMemoryCrit OBJECT-TYPE
    SYNTAX INTEGER
    ACCESS read-write
    STATUS mandatory
    DESCRIPTION
        "Critical threshold for the memory of the Local VC server.
         The value of this attribute is used as a default 
         value for newly configured servers."
    DEFVAL { 80 }
    ::= { vmvcAimConfigMonitorVCGroup 20 }

vmvcAimConfigMonServerLocalMemoryAlert OBJECT-TYPE
    SYNTAX INTEGER{
        warning-only(1),
        critical-only(2),
        both(3)
        }
    ACCESS read-write
    STATUS mandatory
    DESCRIPTION
        "Type of alert for the memory of the Local VC server.
         The value of this attribute is used as a default 
         value for newly configured servers."
    DEFVAL { 3 }
    ::= { vmvcAimConfigMonitorVCGroup 21 }

vmvcAimConfigMonServerLocalMemoryMonitor OBJECT-TYPE
    SYNTAX INTEGER{
        do-not-monitor(1),
        monitor(2)
        }
    ACCESS read-write
    STATUS mandatory
    DESCRIPTION
        "Type of monitoring for the memory of the Local VC server.
         The value of this attribute is used as a default 
         value for newly configured servers."
    DEFVAL { 2 }
    ::= { vmvcAimConfigMonitorVCGroup 22 }

vmvcAimConfigMonServerTotalCPUUsageWarnThresh OBJECT-TYPE
    SYNTAX INTEGER
    ACCESS read-write
    STATUS mandatory
    DESCRIPTION
        "Warning threshold for the total CPU usage for all hosts under
         this VC.  The value of this attribute is used as a default 
         value for newly configured servers."
    DEFVAL { 60 }
    ::= { vmvcAimConfigMonitorVCGroup 23 }

vmvcAimConfigMonServerTotalCPUUsageCritThresh OBJECT-TYPE
    SYNTAX INTEGER
    ACCESS read-write
    STATUS mandatory
    DESCRIPTION
        "Critical threshold for the total CPU usage for all hosts under
         this VC.  The value of this attribute is used as a default 
         value for newly configured servers."
    DEFVAL { 80 }
    ::= { vmvcAimConfigMonitorVCGroup 24 }

vmvcAimConfigMonServerTotalMemWarnThresh OBJECT-TYPE
    SYNTAX INTEGER
    ACCESS read-write
    STATUS mandatory
    DESCRIPTION
        "Warning threshold for the total mem usage for all hosts under
         this VC.  The value of this attribute is used as a default 
         value for newly configured servers."
    DEFVAL { 60 }
    ::= { vmvcAimConfigMonitorVCGroup 25 }

vmvcAimConfigMonServerTotalMemCritThresh OBJECT-TYPE
    SYNTAX INTEGER
    ACCESS read-write
    STATUS mandatory
    DESCRIPTION
        "Critical threshold for the total mem usage for all hosts under
         this VC.  The value of this attribute is used as a default 
         value for newly configured servers."
    DEFVAL { 80 }
    ::= { vmvcAimConfigMonitorVCGroup 26 }

vmvcAimConfigMonServerTotalDatastoreFreeSpaceWarnThresh OBJECT-TYPE
    SYNTAX INTEGER
    ACCESS read-write
    STATUS mandatory
    DESCRIPTION
        "Warning threshold for datastore free space.  The value of this
                 attribute is used as a default value for newly configured
                 servers."
    DEFVAL { 40 }
    ::= { vmvcAimConfigMonitorVCGroup 27 }

vmvcAimConfigMonServerTotalDatastoreFreeSpaceCritThresh OBJECT-TYPE
    SYNTAX INTEGER
    ACCESS read-write
    STATUS mandatory
    DESCRIPTION
        "Critical threshold for datastore free space.  The value of this
                 attribute is used as a default value for newly configured
                 servers."
    DEFVAL { 20 }
    ::= { vmvcAimConfigMonitorVCGroup 28 }


-- *****************************************************************************
-- Datacenter Monitor Configuration Group
-- *****************************************************************************
vmvcAimConfigMonDatacenterUpdate OBJECT-TYPE
    SYNTAX INTEGER{
        done(1),
        update(2)
        }
    ACCESS read-write
    STATUS mandatory
    DESCRIPTION
        "One-shot trigger to update all Datacenter objects with 
         Monitoring configuration for all monitoring parameters.
         When completed, Agent will set this attribute to done(1)."
    DEFVAL { 1 }
    ::= { vmvcAimConfigMonitorDCGroup 1 }

vmvcAimConfigMonDatacenterVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorDCGroup 2 }

vmvcAimConfigMonDatacenterTotalCPUUsageWarnThresh OBJECT-TYPE
    SYNTAX INTEGER
    ACCESS read-write
    STATUS mandatory
    DESCRIPTION
        "Warning threshold for Total CPU usage.  The value of this
                 attribute is used as a default value for created objects."
    DEFVAL { 60 }
    ::= { vmvcAimConfigMonitorDCGroup 3 }

vmvcAimConfigMonDatacenterTotalCPUUsageCritThresh OBJECT-TYPE
    SYNTAX INTEGER
    ACCESS read-write
    STATUS mandatory
    DESCRIPTION
        "Critical threshold  for Total CPU usage.  The value of this
                 attribute is used as a default value for created objects."
    DEFVAL { 80 }
    ::= { vmvcAimConfigMonitorDCGroup 4 }

vmvcAimConfigMonDatacenterTotalMemWarnThres OBJECT-TYPE
    SYNTAX INTEGER
    ACCESS read-write
    STATUS mandatory
    DESCRIPTION 
        "Sets the Memory warning threshold value.  Must be lower than 
         the Memory critical threshold value. The value of this
                 attribute is used as a default value for created objects."
    DEFVAL { 60 }
    ::= { vmvcAimConfigMonitorDCGroup 5 }

vmvcAimConfigMonDatacenterTotalMemCritThres OBJECT-TYPE
    SYNTAX INTEGER
    ACCESS read-write
    STATUS mandatory
    DESCRIPTION 
        "Sets the Memory critical threshold value.  Must be higher than 
         the Memory warning threshold value. The value of this
                 attribute is used as a default value for created objects."
    DEFVAL { 80 }
    ::= { vmvcAimConfigMonitorDCGroup 6 }


-- *****************************************************************************
-- Host Monitor Configuration Group
-- *****************************************************************************
vmvcAimConfigMonHostUpdate OBJECT-TYPE
    SYNTAX INTEGER{
        done(1),
        update(2)
        }
    ACCESS read-write
    STATUS mandatory
    DESCRIPTION
        "One-shot trigger to update all ESX Host objects with 
         Monitoring configuration for all monitoring parameters.
         When completed, Agent will set this attribute to done(1)."
    DEFVAL { 1 }
    ::= { vmvcAimConfigMonitorHostGroup  1 }

vmvcAimConfigMonHostVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorHostGroup  2 }

vmvcAimConfigMonHostMonitor OBJECT-TYPE
    SYNTAX INTEGER{
                do-not-monitor(1),
                monitor(2)
         }
    ACCESS read-write
    STATUS mandatory
    DESCRIPTION
        "Status of the host if it is monitored or not monitored.  The 
         value of this attribute is used as a default value for created objects."
    DEFVAL {2}
    ::= { vmvcAimConfigMonitorHostGroup  3 }

vmvcAimConfigMonHostAlertCPUUsageWarnThresh OBJECT-TYPE
    SYNTAX INTEGER
    ACCESS read-write
    STATUS mandatory
    DESCRIPTION
        "Warning threshold  for CPU usage.  The value of this
                 attribute is used as a default value for created objects."
    DEFVAL { 60 }
    ::= { vmvcAimConfigMonitorHostGroup  4 }

vmvcAimConfigMonHostAlertCPUUsageCritThresh OBJECT-TYPE
    SYNTAX INTEGER
    ACCESS read-write
    STATUS mandatory
    DESCRIPTION
        "Critical threshold  for CPU usage.  The value of this
                 attribute is used as a default value for created objects."
    DEFVAL { 80 }
    ::= { vmvcAimConfigMonitorHostGroup  5 }

vmvcAimConfigMonHostCPUAlert OBJECT-TYPE
    SYNTAX INTEGER{
        warning-only(1),
        critical-only(2),
        both(3)    
        }
    ACCESS read-write
    STATUS mandatory
    DESCRIPTION
        "Alert of the cpu status.  The value of this
                 attribute is used as a default value for created objects."
    DEFVAL { 3 }
    ::= { vmvcAimConfigMonitorHostGroup  6 }

vmvcAimConfigMonHostAlertMemoryUsageWarnThreshold OBJECT-TYPE
    SYNTAX INTEGER 
    ACCESS read-write
    STATUS mandatory
    DESCRIPTION
        "Warning Threshold for Memory Usage.  The value of this
                 attribute is used as a default value for created objects."
    DEFVAL { 60 }
    ::= { vmvcAimConfigMonitorHostGroup  7 }

vmvcAimConfigMonHostAlertMemoryUsageCritThreshold OBJECT-TYPE
    SYNTAX INTEGER
    ACCESS read-write
    STATUS mandatory
    DESCRIPTION
        "Critical Threshold for Memory Usage.  The value of this
                 attribute is used as a default value for created objects."
    DEFVAL { 80 }
    ::= { vmvcAimConfigMonitorHostGroup  8 }

vmvcAimConfigMonHostMemoryAlert OBJECT-TYPE
    SYNTAX INTEGER{
        warning(1),
        critical(2),
        both(3)
        }
    ACCESS read-write
    STATUS mandatory
    DESCRIPTION
        "Alert of the memory status. That may be warning(1), critical(2)
         or both(3).  The value of this attribute is used as a default 
         value for created objects."
    DEFVAL { 3 }
    ::= { vmvcAimConfigMonitorHostGroup  9 }

vmvcAimConfigMonHostTotalVMCPUWarnThreshold OBJECT-TYPE
    SYNTAX INTEGER
    ACCESS read-write
    STATUS mandatory
    DESCRIPTION
        "The warning threshold of CPU usage of all the virtual machines 
         on the ESX Server.  The value of this attribute is used as 
         a default value for created objects."
    DEFVAL { 60 }
    ::= { vmvcAimConfigMonitorHostGroup 10 }

vmvcAimConfigMonHostTotalVMCPUCritThreshold OBJECT-TYPE
    SYNTAX INTEGER
    ACCESS read-write
    STATUS mandatory
    DESCRIPTION
        "The critical threshold of CPU usage of all the virtual machines
         on the ESX Server.  The value of this attribute is used as 
         a default value for created objects."
    DEFVAL { 80 }
    ::= { vmvcAimConfigMonitorHostGroup 11 }

vmvcAimConfigMonHostTotalCPUWarnThreshold OBJECT-TYPE
    SYNTAX INTEGER
    ACCESS read-write
    STATUS mandatory
    DESCRIPTION
        "The warning threshold of CPU Usage of the VMs and ESX Console.
         The value of this attribute is used as a default value for 
         created objects."
    DEFVAL { 60 }
    ::= { vmvcAimConfigMonitorHostGroup 12 }

vmvcAimConfigMonHostTotalCPUCritThreshold OBJECT-TYPE
    SYNTAX INTEGER
    ACCESS read-write
    STATUS mandatory
    DESCRIPTION
        "The critical threshold of CPU Usage of the VMs and ESX Console.
         The value of this attribute is used as a default value for 
         created objects."
    DEFVAL { 80 }
    ::= { vmvcAimConfigMonitorHostGroup 13 }

vmvcAimConfigMonHostTotalVMMemoryWarnThreshold OBJECT-TYPE
    SYNTAX INTEGER
    ACCESS read-write
    STATUS mandatory
    DESCRIPTION
        "The warning threshold of memory usage of all the virtual 
         machines on the ESX Server with respect to Total Machine 
         Memory.  The value of this attribute is used as a default 
         value for created objects."
    DEFVAL { 60 }
    ::= { vmvcAimConfigMonitorHostGroup 14 }

vmvcAimConfigMonHostTotalVMMemoryCritThreshold OBJECT-TYPE
    SYNTAX INTEGER
    ACCESS read-write
    STATUS mandatory
    DESCRIPTION
        "The critical threshold of memory usage of all the virtual 
         machines on the ESX Server with respect to Total Machine 
         Memory.  The value of this attribute is used as a default 
         value for created objects."
    DEFVAL { 80 }
    ::= { vmvcAimConfigMonitorHostGroup 15 }

vmvcAimConfigMonHostMemoryOtherWarnThreshold OBJECT-TYPE
    SYNTAX INTEGER
    ACCESS read-write
    STATUS mandatory
    DESCRIPTION
        "The warning threshold for memory usage of the ESX Server 
         Console with respect to Total Machine Memory.  The value of this
                 attribute is used as a default value for created objects."
    DEFVAL { 60 }
    ::= { vmvcAimConfigMonitorHostGroup 16 }

vmvcAimConfigMonHostMemoryOtherCritThreshold OBJECT-TYPE
    SYNTAX INTEGER
    ACCESS read-write
    STATUS mandatory
    DESCRIPTION
        "The critical threshold for memory usage of the ESX Server i
         Console with respect to Total Machine Memory.  The value of this
                 attribute is used as a default value for created objects."
    DEFVAL { 80 }
    ::= { vmvcAimConfigMonitorHostGroup 17 }

vmvcAimConfigMonHostMemoryTotalWarnThreshold OBJECT-TYPE
    SYNTAX INTEGER
    ACCESS read-write
    STATUS mandatory
    DESCRIPTION
        "The warning threshold for the total memory usage ( sum of ESX 
         Server Console and all VMs ) with respect to Total Machine 
         Memory.  The value of this attribute is used as a default 
         value for created objects."
    DEFVAL { 60 }
    ::= { vmvcAimConfigMonitorHostGroup 18 }

vmvcAimConfigMonHostMemoryTotalCritThreshold OBJECT-TYPE
    SYNTAX INTEGER
    ACCESS read-write
    STATUS mandatory
    DESCRIPTION
        "The critical threshold for the total memory usage ( sum of ESX 
         Server Console and all VMs ) with respect to Total Machine 
         Memory.  The value of this attribute is used as a default 
         value for created objects."
    DEFVAL { 80 }
    ::= { vmvcAimConfigMonitorHostGroup 19 }

vmvcAimConfigMonHostCPUMonitor OBJECT-TYPE
    SYNTAX INTEGER {
         do-not-monitor(1),
        monitor(2)
    }
    ACCESS read-write
    STATUS mandatory
    DESCRIPTION    
        "Flag indicating whether the CPU usage for node to be 
         monitored(2) or not(1).  The value of this
                 attribute is used as a default value for created objects."
    DEFVAL { 2 }
    ::= { vmvcAimConfigMonitorHostGroup 20 }

vmvcAimConfigMonHostCPULagSetting OBJECT-TYPE
    SYNTAX  INTEGER
    ACCESS  read-write
    STATUS  mandatory
    DESCRIPTION 
        "The number of consecutive times the threshold should be 
         breached before the status change occurs.  The value of this
                 attribute is used as a default value for created objects."
    DEFVAL { 3 }
    ::= { vmvcAimConfigMonitorHostGroup 21 }

vmvcAimConfigMonHostMemoryMonitor OBJECT-TYPE
    SYNTAX INTEGER {
         do-not-monitor(1),
        monitor(2)
    }
    ACCESS read-write
    STATUS mandatory
    DESCRIPTION    
        "Flag indicating whether the Memory usage for host to be 
         monitored(2) or not(1).  The value of this
                 attribute is used as a default value for created objects."
    DEFVAL { 2 }
    ::= { vmvcAimConfigMonitorHostGroup 22 }


-- *****************************************************************************
-- Resource Pool Monitor Configuration Group
-- *****************************************************************************
vmvcAimConfigMonResourcePoolUpdate OBJECT-TYPE
    SYNTAX INTEGER{
        done(1),
        update(2)
        }
    ACCESS read-write
    STATUS mandatory
    DESCRIPTION
        "One-shot trigger to update all Resource Pool objects with 
         Monitoring configuration for all monitoring parameters.
         When completed, Agent will set this attribute to done(1)."
    DEFVAL { 1 }
    ::= { vmvcAimConfigMonitorResPoolGroup  1 }

vmvcAimConfigMonResourcePoolVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorResPoolGroup  2 }

vmvcAimConfigMonResourcePoolCPUUsageWarn OBJECT-TYPE
    SYNTAX INTEGER
    ACCESS read-write
    STATUS mandatory
    DESCRIPTION
        "Resource Pool CPU Warning Threshold.  The value of this
                 attribute is used as a default value for created objects."
    DEFVAL { 60 }
    ::= { vmvcAimConfigMonitorResPoolGroup  3 }

vmvcAimConfigMonResourcePoolCPUUsageCrit OBJECT-TYPE
    SYNTAX INTEGER
    ACCESS read-write
    STATUS mandatory
    DESCRIPTION
        "Critical Threshold for Resource Pool CPU usage.  The value of 
         this attribute is used as a default value for created objects."
    DEFVAL { 80 }
    ::= { vmvcAimConfigMonitorResPoolGroup  4 }

vmvcAimConfigMonResourcePoolCPUAlert OBJECT-TYPE
    SYNTAX INTEGER{
        warning-only(1),
        critical-only(2),
        both(3)    
        }
    ACCESS read-write
    STATUS mandatory
    DESCRIPTION
        "Resource Pool CPU Alert.  The value of this attribute is used 
         as a default value for created objects."
    DEFVAL { 3 }
    ::= { vmvcAimConfigMonitorResPoolGroup  5 }

vmvcAimConfigMonResourcePoolMemUsageWarn OBJECT-TYPE
    SYNTAX INTEGER
    ACCESS read-write
    STATUS mandatory
    DESCRIPTION
        "Resource Pool Memory Warning Threshold.  The value of this
                 attribute is used as a default value for created objects."
    DEFVAL { 60 }
    ::= { vmvcAimConfigMonitorResPoolGroup  6 }

vmvcAimConfigMonResourcePoolMemUsageCrit OBJECT-TYPE
    SYNTAX INTEGER
    ACCESS read-write
    STATUS mandatory
    DESCRIPTION
        "Resource Pool Memory Critical Threshold.  The value of this
                 attribute is used as a default value for created objects."
    DEFVAL { 80 }
    ::= { vmvcAimConfigMonitorResPoolGroup  7 }

vmvcAimConfigMonResourcePoolMemAlert OBJECT-TYPE
    SYNTAX INTEGER{
        warning-only(1),
        critical-only(2),
        both(3)    
        }
    ACCESS read-write
    STATUS mandatory
    DESCRIPTION
        "Resource Pool Memory Alert.  The value of this
                 attribute is used as a default value for created objects."
    DEFVAL { 3 }
    ::= { vmvcAimConfigMonitorResPoolGroup  8 }

vmvcAimConfigMonResourcePoolMonitor OBJECT-TYPE
    SYNTAX INTEGER{
        do-not-monitor(1),
        monitor(2)
        }
    ACCESS read-write
    STATUS mandatory
    DESCRIPTION
        "Flag to indicate whether Resource Pool to be monitered(2) or i
         not(1).  The value of this attribute is used as a default 
         value for created objects."
    DEFVAL { 2 }
    ::= { vmvcAimConfigMonitorResPoolGroup  9 }

vmvcAimConfigMonResourcePoolAlert OBJECT-TYPE
    SYNTAX INTEGER{
        not-green-warning(1),
        not-green-critical(2)
        }
    ACCESS read-write
    STATUS mandatory
    DESCRIPTION
        "Resource Pool Alert whether warning or critical.  The value of 
         this attribute is used as a default value for created objects."
    DEFVAL { 2 }
    ::= { vmvcAimConfigMonitorResPoolGroup 10 }


-- *****************************************************************************
-- VM Monitor Configuration Group
-- *****************************************************************************
vmvcAimConfigMonVMUpdate OBJECT-TYPE
    SYNTAX INTEGER{
        done(1),
        update(2)
        }
    ACCESS read-write
    STATUS mandatory
    DESCRIPTION
        "One-shot trigger to update all Virtual Machine objects with 
         Monitoring configuration for all monitoring parameters.
         When completed, Agent will set this attribute to done(1)."
    DEFVAL { 1 }
    ::= { vmvcAimConfigMonitorVMGroup  1 }

vmvcAimConfigMonVMVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorVMGroup  2 }

vmvcAimConfigMonVMMonitor OBJECT-TYPE
    SYNTAX INTEGER{
        do-not-monitor(1),
        monitor(2)
        }
    ACCESS read-write
    STATUS mandatory
    DESCRIPTION
        "Flag indicating whether the virtual machine has to be 
         monitored(2) or not(1).  The value of this attribute is used 
         as a default value for created objects."
    DEFVAL { 2 }
    ::= { vmvcAimConfigMonitorVMGroup  3 }

vmvcAimConfigMonVMAlertPowerOffStatus OBJECT-TYPE
    SYNTAX INTEGER{
        off-warning(1),
        off-critical(2),
        off-normal(3)
        }
    ACCESS read-write
    STATUS mandatory
    DESCRIPTION
        "VM Poweroff status alert.  The value of this attribute is used 
         as a default value for created objects."
    DEFVAL { 3 }
    ::= { vmvcAimConfigMonitorVMGroup  4 }

vmvcAimConfigMonVMAlertHeartbeatLoss OBJECT-TYPE
    SYNTAX INTEGER{
        no-heartbeat-warning(1),
        no-heartbeat-critical(2),
        no-heartbeat-ok(3)
        }
    ACCESS read-write
    STATUS mandatory
    DESCRIPTION
        "VM Heartbeat Loss alert.  Setting to no-heartbeat-ok(3) effectively
         disables the Heartbeat monitoring.
         The value of this attribute is used as a default value for created objects."
    DEFVAL { 2 }
    ::= { vmvcAimConfigMonitorVMGroup  5 }

vmvcAimConfigMonVMCPUSharesWarnThreshold OBJECT-TYPE
    SYNTAX INTEGER
    ACCESS read-write
    STATUS mandatory
    DESCRIPTION
        "VM CPU Shares Warning Threshold.  The value of this attribute 
         is used as a default value for created objects."
    DEFVAL { 60 }
    ::= { vmvcAimConfigMonitorVMGroup  6 }

vmvcAimConfigMonVMCPUSharesCritThreshold OBJECT-TYPE
    SYNTAX INTEGER
    ACCESS read-write
    STATUS mandatory
    DESCRIPTION
        "VM CPU Shares Critical Threshold.  The value of this attribute 
         is used as a default value for created objects."
    DEFVAL { 80 }
    ::= { vmvcAimConfigMonitorVMGroup  7 }

vmvcAimConfigMonVMCPUAlert OBJECT-TYPE
    SYNTAX INTEGER{
        warning(1),
        critical(2),
        both(3)
        }
    ACCESS read-write
    STATUS mandatory
    DESCRIPTION
        "VM CPU usage Alert. That may be warning, critical or both.
         The value of this attribute is used as a default value for 
         created objects."
    DEFVAL { 3 }
    ::= { vmvcAimConfigMonitorVMGroup  8 }

vmvcAimConfigMonVMMemoryWarnThreshold OBJECT-TYPE
    SYNTAX INTEGER
    ACCESS read-write
    STATUS mandatory
    DESCRIPTION
        "VM Memory Warning Threshold.  The value of this attribute is 
         used as a default value for created objects."
    DEFVAL { 60 }
    ::= { vmvcAimConfigMonitorVMGroup  9 }

vmvcAimConfigMonVMMemoryCritThreshold OBJECT-TYPE
    SYNTAX INTEGER
    ACCESS read-write
    STATUS mandatory
    DESCRIPTION
        "VM Memory critical Threshold.  The value of this attribute is 
         used as a default value for created objects."
    DEFVAL { 80 }
    ::= { vmvcAimConfigMonitorVMGroup 10 }

vmvcAimConfigMonVMMemoryAlert OBJECT-TYPE
    SYNTAX INTEGER{
        warning(1),
        critical(2),
        both(3)
        }
    ACCESS read-write
    STATUS mandatory
    DESCRIPTION
        "VM memory Alert. That may be warning, critical or both.
         The value of this attribute is used as a default value for 
         created objects."
    DEFVAL { 3 }
    ::= { vmvcAimConfigMonitorVMGroup 11 }

vmvcAimConfigMonVMPctReadyWarnThreshold OBJECT-TYPE
    SYNTAX INTEGER
    ACCESS read-write
    STATUS mandatory
    DESCRIPTION
        "Warning threshold for the VMPctReady variable.  The value of
                 this attribute is used as a default value for created objects."
    DEFVAL { 5 }
    ::= { vmvcAimConfigMonitorVMGroup 12 }

vmvcAimConfigMonVMPctReadyCritThreshold OBJECT-TYPE
    SYNTAX INTEGER
    ACCESS read-write
    STATUS mandatory
    DESCRIPTION
        "Critical threshold for the VMPctReady variable.  The value of
                 this attribute is used as a default value for created objects."
    DEFVAL { 15 }
    ::= { vmvcAimConfigMonitorVMGroup 13 }

vmvcAimConfigMonVMPctReadyAlert OBJECT-TYPE
    SYNTAX INTEGER{
        warning(1),
        critical(2),
        both(3)
        }
    ACCESS read-write
    STATUS mandatory
    DESCRIPTION
        "The level of alert to raise  for VMPctReady.  This may be 
         warning, critical or both.  The value of this attribute is 
         used as a default value for created objects."
    DEFVAL { 3 }
    ::= { vmvcAimConfigMonitorVMGroup 14 }

vmvcAimConfigMonVMCPUMonitor OBJECT-TYPE
    SYNTAX INTEGER{
        do-not-monitor(1),
        monitor(2)
        }
    ACCESS read-write
    STATUS mandatory
    DESCRIPTION
        "Flag inidicating whether the virtual machine CPU has to be 
         monitored(2) or not(1).  The value of this attribute is used 
         as a default value for created objects."
    DEFVAL { 2 }
    ::= { vmvcAimConfigMonitorVMGroup 15 }

vmvcAimConfigMonVMCPULagSetting OBJECT-TYPE
    SYNTAX INTEGER
    ACCESS read-write
    STATUS mandatory
    DESCRIPTION 
        "VM CPU lag setting.  The value of this attribute is used as a 
         default value for created objects."
    DEFVAL { 3 }
    ::= { vmvcAimConfigMonitorVMGroup 16 }

vmvcAimConfigMonVMMemoryMonitor OBJECT-TYPE
    SYNTAX INTEGER{
        do-not-monitor(1),
        monitor(2)
        }
    ACCESS read-write
    STATUS mandatory
    DESCRIPTION
        "Flag inidicating whether the virtual machine Memory has to be 
         monitored(2) or not(1).  The value of this attribute is used 
         as a default value for created objects."
    DEFVAL { 2 }
    ::= { vmvcAimConfigMonitorVMGroup 17 }


-- *****************************************************************************
-- Virtual Switch Monitor Configuration Group
-- *****************************************************************************
vmvcAimConfigMonSwitchUpdate OBJECT-TYPE
    SYNTAX INTEGER{
        done(1),
        update(2)
        }
    ACCESS read-write
    STATUS mandatory
    DESCRIPTION
        "One-shot trigger to update all Virtual Switch objects with 
         Monitoring configuration for all monitoring parameters.
         When completed, Agent will set this attribute to done(1)."
    DEFVAL { 1 }
    ::= { vmvcAimConfigMonitorVSwitchGroup 1 }

vmvcAimConfigMonSwitchVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorVSwitchGroup 2 }

vmvcAimConfigMonSwitchMonitor OBJECT-TYPE
    SYNTAX INTEGER{
        do-not-monitor(1),
        monitor(2)
        }
    ACCESS read-write
    STATUS mandatory
    DESCRIPTION
        "Flag indicate whether Switch to be Monitored(2) or not(1).  The 
         value of this attribute is used as a default value for 
         created objects."
    DEFVAL {2 }
    ::= { vmvcAimConfigMonitorVSwitchGroup 3 }

vmvcAimConfigMonSwitchAlert OBJECT-TYPE
    SYNTAX INTEGER{
        one-nic-down-warn(1),
        one-nic-down-crit(2),
        all-nic-down-warn(3),
        all-nic-down-crit(4)
        }
    ACCESS read-write
    STATUS mandatory
    DESCRIPTION
        "Switch alert status.  The value of this attribute is used
                 as a default value for created objects."
    DEFVAL { 2 }
    ::= { vmvcAimConfigMonitorVSwitchGroup 4 }


-- *****************************************************************************
-- Physical NIC Monitor Configuration Group
-- *****************************************************************************
vmvcAimConfigMonPNICUpdate OBJECT-TYPE
    SYNTAX INTEGER{
        done(1),
        update(2)
        }
    ACCESS read-write
    STATUS mandatory
    DESCRIPTION
        "One-shot trigger to update all Physical NIC objects with 
         Monitoring configuration for all monitoring parameters.
         When completed, Agent will set this attribute to done(1)."
    DEFVAL { 1 }
    ::= { vmvcAimConfigMonitorPNICGroup 1 }

vmvcAimConfigMonPNICVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorPNICGroup 2 }

vmvcAimConfigMonPNICMonitor OBJECT-TYPE
    SYNTAX INTEGER{
        do-not-monitor(1),
        monitor(2)
        }
    ACCESS read-write
    STATUS mandatory
    DESCRIPTION
        "The flag to indicate whether or not PNIC has to be monitored(2)
         or not(1).  The value of this attribute is used as a default 
         value for created objects."
    DEFVAL {2 }
    ::= { vmvcAimConfigMonitorPNICGroup 3 }

vmvcAimConfigMonPNICAlert OBJECT-TYPE
    SYNTAX INTEGER{
        link-down-warn(1),
        link-down-crit(2)
        }
    ACCESS read-write
    STATUS mandatory
    DESCRIPTION
        "PNIC Alert if it is warning or critical.  The value of this 
         attribute is used as a default value for created objects."
    DEFVAL {2 }
    ::= { vmvcAimConfigMonitorPNICGroup 4 }


-- *****************************************************************************
-- VM Virtual NIC Monitor Configuration Group
-- *****************************************************************************
vmvcAimConfigMonVMVNICUpdate OBJECT-TYPE
    SYNTAX INTEGER{
        done(1),
        update(2)
        }
    ACCESS read-write
    STATUS mandatory
    DESCRIPTION
        "One-shot trigger to update all VM Virtual NIC objects with 
         Monitoring configuration for all monitoring parameters.
         When completed, Agent will set this attribute to done(1)."
    DEFVAL { 1 }
    ::= { vmvcAimConfigMonitorVMVNICGroup 1 }

vmvcAimConfigMonVMVNICVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorVMVNICGroup 2 }

vmvcAimConfigMonVMVNICMonitor OBJECT-TYPE
    SYNTAX INTEGER {
        do-not-monitor(1),
        monitor(2)
    }
    ACCESS read-write
    STATUS mandatory
    DESCRIPTION
        "The flag indicating whether to monitor the VNIC or not.   The 
         value of this attribute is used as a default value for 
         created objects."
    DEFVAL { 2 }
    ::= { vmvcAimConfigMonitorVMVNICGroup 3 }

vmvcAimConfigMonVMVNICAlert OBJECT-TYPE
    SYNTAX INTEGER {
        disconnected-warn(1),
        disconnected-critical(2)
    }
    ACCESS read-write
    STATUS mandatory
    DESCRIPTION
        "Level for the alert.   The value of this attribute is used as 
         a default value for created objects."
    DEFVAL { 2 }
    ::= { vmvcAimConfigMonitorVMVNICGroup 4 }


-- *****************************************************************************
-- Distributed Virtual Switch Monitor Configuration Group
-- *****************************************************************************
vmvcAimConfigMonitorDVSwitchUpdate OBJECT-TYPE
    SYNTAX INTEGER{
        done(1),
        update(2)
        }
    ACCESS read-write
    STATUS mandatory
    DESCRIPTION
        "One-shot trigger to update all Distributed Virtual Switch objects with 
         Monitoring configuration for all monitoring parameters.
         When completed, Agent will set this attribute to done(1)."
    DEFVAL { 1 }
    ::= { vmvcAimConfigMonitorDistribVSwitchGroup 1 }

vmvcAimConfigMonitorDVSwitchVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorDistribVSwitchGroup 2 }

vmvcAimConfigMonDVSwitchMonitor OBJECT-TYPE
    SYNTAX INTEGER {
        do-not-monitor(1),
        monitor(2)
    }
    ACCESS read-write
    STATUS mandatory
    DESCRIPTION
        "Flag whether to monitor this Distributed Virtual Switch or not.   The 
         value of this attribute is used as a default value for 
         created objects."
    DEFVAL { 2 }
    ::= { vmvcAimConfigMonitorDistribVSwitchGroup 3 }

vmvcAimConfigMonDVSwitchAlert OBJECT-TYPE
    SYNTAX INTEGER {
        not-green-warn(1),
        not-green-critical(2),
        follow-overallStatus(3)
    }
    ACCESS read-write
    STATUS mandatory
    DESCRIPTION
        "Level choices for the alert, as follows:
            not-green-warn       -  Set the State=warning(3) if OverallStatus!=green
            not-green-crit       -  Set the State=critical(4) if OverallStatus!=green
            follow-overallStatus -  Use the OverallStatus to set the State, as follows:
               OverallStatus=gray    ->  State=unknown(1)
               OverallStatus=green   ->  State=ok(2)
               OverallStatus=yellow  ->  State=warning(3)
               OverallStatus=red     ->  State=critical(4)
         The value of this attribute is used as a default value for created objects."
    DEFVAL { 3 }
    ::= { vmvcAimConfigMonitorDistribVSwitchGroup 4 }


-- *****************************************************************************
-- Datastore Monitor Configuration Group
-- *****************************************************************************
vmvcAimConfigMonDatastoreUpdate OBJECT-TYPE
    SYNTAX INTEGER{
        done(1),
        update(2)
        }
    ACCESS read-write
    STATUS mandatory
    DESCRIPTION
        "One-shot trigger to update all Datastore objects with 
         Monitoring configuration for all monitoring parameters.
         When completed, Agent will set this attribute to done(1)."
    DEFVAL { 1 }
    ::= { vmvcAimConfigMonitorDatastoreGroup  1 }

vmvcAimConfigMonDatastoreVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorDatastoreGroup  2 }

vmvcAimConfigMonDatastoreMonitor OBJECT-TYPE
    SYNTAX INTEGER{
        do-not-monitor(1),
        monitor(2)
        }
    ACCESS read-write
    STATUS mandatory
    DESCRIPTION
        "The flag indicating whether to monitor the datastore or not.
         The value of this attribute is used as a default value for 
         created objects."
    DEFVAL {2 }
    ::= { vmvcAimConfigMonitorDatastoreGroup  3 }

vmvcAimConfigMonDatastoreFreeSpaceAlert OBJECT-TYPE
    SYNTAX INTEGER{
        warning-only(1),
        critical-only(2),
        both(3)
        }
    ACCESS read-write
    STATUS mandatory
    DESCRIPTION
        "Datastore Free Space Alert.  This may be warning, critical or 
         both.  The value of this attribute is used as a default value 
         for created objects."
    DEFVAL {3}
    ::= { vmvcAimConfigMonitorDatastoreGroup  4 }

vmvcAimConfigMonDatastoreFreeSpaceWarnThresh OBJECT-TYPE
    SYNTAX INTEGER
    ACCESS read-write
    STATUS mandatory
    DESCRIPTION
        "Warning threshold for datastore free space.  The value of this 
         attribute is used as a default value for created objects."
    DEFVAL { 40 }
    ::= { vmvcAimConfigMonitorDatastoreGroup  5 }

vmvcAimConfigMonDatastoreFreeSpaceCritThresh OBJECT-TYPE
    SYNTAX INTEGER
    ACCESS read-write
    STATUS mandatory
    DESCRIPTION
        "Critical threshold for datastore free space.  The value of this
         attribute is used as a default value for created objects."
    DEFVAL { 20 }
    ::= { vmvcAimConfigMonitorDatastoreGroup  6 }

vmvcAimConfigMonDatastoreAccessibleAlert OBJECT-TYPE
    SYNTAX INTEGER{
        not-accessible-warn(1),
        not-accessible-crit(2)
    }
    ACCESS read-write
    STATUS mandatory
    DESCRIPTION
        "Datastore Accessible Alert.  The value of this attribute is 
         used as a default value for created objects."
    DEFVAL {2 }
    ::= { vmvcAimConfigMonitorDatastoreGroup  7 }


-- *****************************************************************************
-- VM Virtual Disk Monitor Configuration Group
-- *****************************************************************************
vmvcAimConfigMonVMVDiskUpdate OBJECT-TYPE
    SYNTAX INTEGER{
        done(1),
        update(2)
        }
    ACCESS read-write
    STATUS mandatory
    DESCRIPTION
        "One-shot trigger to update all VM Virtual Disk objects with 
         Monitoring configuration for all monitoring parameters.
         When completed, Agent will set this attribute to done(1)."
    DEFVAL { 1 }
    ::= { vmvcAimConfigMonitorVMVDiskGroup  1 }

vmvcAimConfigMonVMVDiskVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorVMVDiskGroup  2 }

vmvcAimConfigMonVMVDiskMonitor OBJECT-TYPE
    SYNTAX INTEGER {
        do-not-monitor(1),
        monitor(2)
    }
    ACCESS read-write
    STATUS mandatory
    DESCRIPTION
        "Flag indicating whether the Device to be monitored(2) or 
         not(1).  The value of this attribute is used as a default 
         value for created objects."
    DEFVAL { 1 }
    ::= { vmvcAimConfigMonitorVMVDiskGroup  3 }

vmvcAimConfigMonVMVDiskKBReadAlert OBJECT-TYPE
    SYNTAX INTEGER {
        no-read-warning(1),
        no-read-critical(2)
    }
    ACCESS read-write
    STATUS mandatory
    DESCRIPTION
        "The level of alert to raise if the Disk is monitored and 
         there is a loss of KB read.  The value of this attribute is
                 used as a default value for created objects."
    DEFVAL { 2 }
    ::= { vmvcAimConfigMonitorVMVDiskGroup  4 }

vmvcAimConfigMonVMVDiskKBWriteAlert OBJECT-TYPE
    SYNTAX INTEGER {
        no-write-warning(1),
        no-write-critical(2)
    }
    ACCESS read-write
    STATUS mandatory
    DESCRIPTION
        "The level of alert to raise if the Disk is monitored and 
         there is a loss of KB read.  The value of this attribute is
                 used as a default value for created objects."
    DEFVAL { 2 }
    ::= { vmvcAimConfigMonitorVMVDiskGroup  5 }


-- *****************************************************************************
-- VM Guest Disk Monitor Configuration Group
-- *****************************************************************************
vmvcAimConfigMonVMGuestDiskUpdate OBJECT-TYPE
    SYNTAX INTEGER{
        done(1),
        update(2)
        }
    ACCESS read-write
    STATUS mandatory
    DESCRIPTION
        "One-shot trigger to update all VM Guest Disk objects with 
         Monitoring configuration for all monitoring parameters.
         When completed, Agent will set this attribute to done(1)."
    DEFVAL { 1 }
    ::= { vmvcAimConfigMonitorVMGuestDiskGroup  1 }

vmvcAimConfigMonVMGuestDiskVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorVMGuestDiskGroup  2 }

vmvcAimConfigMonVMGuestDiskMonitor OBJECT-TYPE
    SYNTAX INTEGER {
        do-not-monitor(1),
        monitor(2)
    }
    ACCESS read-write
    STATUS mandatory
    DESCRIPTION
        "Flag indicating whether the Guest Disk Usage is to be 
         monitored(2) or not(1).  The value of this attribute 
         is used as a default value for created objects."
    DEFVAL { 2 }
    ::= { vmvcAimConfigMonitorVMGuestDiskGroup  3 }

vmvcAimConfigMonVMGuestDiskAlert OBJECT-TYPE
    SYNTAX INTEGER {
        warning-only(1),
        critical-only(2),
        both(3)
        }
    ACCESS read-write
    STATUS mandatory
    DESCRIPTION
        "Guest Disk Usage Alert.  This may be warning, critical or 
         both.  The value of this attribute is used as a default value 
         for created objects."
    DEFVAL {3}
    ::= { vmvcAimConfigMonitorVMGuestDiskGroup  4 }

vmvcAimConfigMonVMGuestDiskUsageWarnThresh OBJECT-TYPE
    SYNTAX INTEGER
    ACCESS read-write
    STATUS mandatory
    DESCRIPTION
        "Guest Disk Usage Warning Threshold (must be lower than the 
         Critical Threshold).  The value of this attribute is 
         used as a default value for created objects."
    DEFVAL { 60 }
    ::= { vmvcAimConfigMonitorVMGuestDiskGroup  5 }

vmvcAimConfigMonVMGuestDiskUsageCritThresh OBJECT-TYPE
    SYNTAX INTEGER
    ACCESS read-write
    STATUS mandatory
    DESCRIPTION
        "Guest Disk Usage Critical Threshold (must be higher than the 
         Warning Threshold).  The value of this attribute is used as a 
         default value for created objects."
    DEFVAL { 80 }
    ::= { vmvcAimConfigMonitorVMGuestDiskGroup  6 }


-- *****************************************************************************
-- CPU Sensor Monitor Configuration Group
-- *****************************************************************************
vmvcAimConfigMonCPUSensorUpdate OBJECT-TYPE
    SYNTAX INTEGER{
        done(1),
        update(2)
        }
    ACCESS read-write
    STATUS mandatory
    DESCRIPTION
        "One-shot trigger to update all CPU Sensor objects with 
         Monitoring configuration for all monitoring parameters.
         When completed, Agent will set this attribute to done(1)."
    DEFVAL { 1 }
    ::= { vmvcAimConfigMonitorCPUSensorGroup  1 }

vmvcAimConfigMonCPUSensorVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorCPUSensorGroup  2 }

vmvcAimConfigMonCPUSensorAlert OBJECT-TYPE
    SYNTAX INTEGER {
        not-green-warn(1),
        not-green-critical(2)
    }
    ACCESS read-write
    STATUS mandatory
    DESCRIPTION
        "Level for the alert.   The value of this attribute is
                 used as a default value for created objects."
    DEFVAL { 2 }
    ::= { vmvcAimConfigMonitorCPUSensorGroup  3 }

vmvcAimConfigMonCPUSensorMonitor OBJECT-TYPE
    SYNTAX INTEGER {
        do-not-monitor(1),
        monitor(2)
    }
    ACCESS read-write
    STATUS mandatory
    DESCRIPTION
        "Flag whether to monitor the Sensor or not.   The value of this 
         attribute is used as a default value for created objects."
    DEFVAL { 2 }
    ::= { vmvcAimConfigMonitorCPUSensorGroup  4 }


-- *****************************************************************************
-- Mem Sensor Monitor Configuration Group
-- *****************************************************************************
vmvcAimConfigMonMemSensorUpdate OBJECT-TYPE
    SYNTAX INTEGER{
        done(1),
        update(2)
        }
    ACCESS read-write
    STATUS mandatory
    DESCRIPTION
        "One-shot trigger to update all Memory Sensor objects with 
         Monitoring configuration for all monitoring parameters.
         When completed, Agent will set this attribute to done(1)."
    DEFVAL { 1 }
    ::= { vmvcAimConfigMonitorMemSensorGroup  1 }

vmvcAimConfigMonMemSensorVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorMemSensorGroup  2 }

vmvcAimConfigMonMemSensorAlert OBJECT-TYPE
    SYNTAX INTEGER {
        not-green-warn(1),
        not-green-critical(2)
    }
    ACCESS read-write
    STATUS mandatory
    DESCRIPTION
        "Level for the alert.   The value of this attribute is
                 used as a default value for created objects."
    DEFVAL { 2 }
    ::= { vmvcAimConfigMonitorMemSensorGroup  3 }

vmvcAimConfigMonMemSensorMonitor OBJECT-TYPE
    SYNTAX INTEGER {
        do-not-monitor(1),
        monitor(2)
    }
    ACCESS read-write
    STATUS mandatory
    DESCRIPTION
        "Flag whether to monitor the Sensor or not.   The value of this 
         attribute is used as a default value for created objects."
    DEFVAL { 2 }
    ::= { vmvcAimConfigMonitorMemSensorGroup  4 }


-- *****************************************************************************
-- Fan Sensor Monitor Configuration Group
-- *****************************************************************************
vmvcAimConfigMonFanSensorUpdate OBJECT-TYPE
    SYNTAX INTEGER{
        done(1),
        update(2)
        }
    ACCESS read-write
    STATUS mandatory
    DESCRIPTION
        "One-shot trigger to update all Fan Sensor objects with 
         Monitoring configuration for all monitoring parameters.
         When completed, Agent will set this attribute to done(1)."
    DEFVAL { 1 }
    ::= { vmvcAimConfigMonitorFanSensorGroup  1 }

vmvcAimConfigMonFanSensorVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorFanSensorGroup  2 }

vmvcAimConfigMonFanSensorAlert OBJECT-TYPE
    SYNTAX INTEGER {
        not-green-warn(1),
        not-green-critical(2)
    }
    ACCESS read-write
    STATUS mandatory
    DESCRIPTION
        "Level for the alert.   The value of this attribute is
                 used as a default value for created objects."
    DEFVAL { 2 }
    ::= { vmvcAimConfigMonitorFanSensorGroup  3 }

vmvcAimConfigMonFanSensorMonitor OBJECT-TYPE
    SYNTAX INTEGER {
        do-not-monitor(1),
        monitor(2)
    }
    ACCESS read-write
    STATUS mandatory
    DESCRIPTION
        "Flag whether to monitor the Sensor or not.   The value of this 
         attribute is used as a default value for created objects."
    DEFVAL { 2 }
    ::= { vmvcAimConfigMonitorFanSensorGroup  4 }


-- *****************************************************************************
-- Voltage Sensor Monitor Configuration Group
-- *****************************************************************************
vmvcAimConfigMonVoltageSensorUpdate OBJECT-TYPE
    SYNTAX INTEGER{
        done(1),
        update(2)
        }
    ACCESS read-write
    STATUS mandatory
    DESCRIPTION
        "One-shot trigger to update all Voltage Sensor objects with 
         Monitoring configuration for all monitoring parameters.
         When completed, Agent will set this attribute to done(1)."
    DEFVAL { 1 }
    ::= { vmvcAimConfigMonitorVoltageSensorGroup  1 }

vmvcAimConfigMonVoltageSensorVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorVoltageSensorGroup  2 }

vmvcAimConfigMonVoltageSensorAlert OBJECT-TYPE
    SYNTAX INTEGER {
        not-green-warn(1),
        not-green-critical(2)
    }
    ACCESS read-write
    STATUS mandatory
    DESCRIPTION
        "Level for the alert.   The value of this attribute is
                 used as a default value for created objects."
    DEFVAL { 2 }
    ::= { vmvcAimConfigMonitorVoltageSensorGroup  3 }

vmvcAimConfigMonVoltageSensorMonitor OBJECT-TYPE
    SYNTAX INTEGER {
        do-not-monitor(1),
        monitor(2)
    }
    ACCESS read-write
    STATUS mandatory
    DESCRIPTION
        "Flag whether to monitor the Sensor or not.   The value of this 
         attribute is used as a default value for created objects."
    DEFVAL { 2 }
    ::= { vmvcAimConfigMonitorVoltageSensorGroup  4 }


-- *****************************************************************************
-- Temp Sensor Monitor Configuration Group
-- *****************************************************************************
vmvcAimConfigMonTempSensorUpdate OBJECT-TYPE
    SYNTAX INTEGER{
        done(1),
        update(2)
        }
    ACCESS read-write
    STATUS mandatory
    DESCRIPTION
        "One-shot trigger to update all Temp Sensor objects with 
         Monitoring configuration for all monitoring parameters.
         When completed, Agent will set this attribute to done(1)."
    DEFVAL { 1 }
    ::= { vmvcAimConfigMonitorTempSensorGroup  1 }

vmvcAimConfigMonTempSensorVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorTempSensorGroup  2 }

vmvcAimConfigMonTempSensorAlert OBJECT-TYPE
    SYNTAX INTEGER {
        not-green-warn(1),
        not-green-critical(2)
    }
    ACCESS read-write
    STATUS mandatory
    DESCRIPTION
        "Level for the alert.   The value of this attribute is
                 used as a default value for created objects."
    DEFVAL { 2 }
    ::= { vmvcAimConfigMonitorTempSensorGroup  3 }

vmvcAimConfigMonTempSensorMonitor OBJECT-TYPE
    SYNTAX INTEGER {
        do-not-monitor(1),
        monitor(2)
    }
    ACCESS read-write
    STATUS mandatory
    DESCRIPTION
        "Flag whether to monitor the Sensor or not.   The value of this 
         attribute is used as a default value for created objects."
    DEFVAL { 2 }
    ::= { vmvcAimConfigMonitorTempSensorGroup  4 }


-- *****************************************************************************
-- Power Sensor Monitor Configuration Group
-- *****************************************************************************
vmvcAimConfigMonPowerSensorUpdate OBJECT-TYPE
    SYNTAX INTEGER{
        done(1),
        update(2)
        }
    ACCESS read-write
    STATUS mandatory
    DESCRIPTION
        "One-shot trigger to update all Power Sensor objects with 
         Monitoring configuration for all monitoring parameters.
         When completed, Agent will set this attribute to done(1)."
    DEFVAL { 1 }
    ::= { vmvcAimConfigMonitorPowerSensorGroup  1 }

vmvcAimConfigMonPowerSensorVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorPowerSensorGroup  2 }

vmvcAimConfigMonPowerSensorAlert OBJECT-TYPE
    SYNTAX INTEGER {
        not-green-warn(1),
        not-green-critical(2)
    }
    ACCESS read-write
    STATUS mandatory
    DESCRIPTION
        "Level for the alert.   The value of this attribute is
                 used as a default value for created objects."
    DEFVAL { 2 }
    ::= { vmvcAimConfigMonitorPowerSensorGroup  3 }

vmvcAimConfigMonPowerSensorMonitor OBJECT-TYPE
    SYNTAX INTEGER {
        do-not-monitor(1),
        monitor(2)
    }
    ACCESS read-write
    STATUS mandatory
    DESCRIPTION
        "Flag whether to monitor the Sensor or not.   The value of this 
         attribute is used as a default value for created objects."
    DEFVAL { 2 }
    ::= { vmvcAimConfigMonitorPowerSensorGroup  4 }


-- *****************************************************************************
-- Storage Sensor Monitor Configuration Group
-- *****************************************************************************
vmvcAimConfigMonStorageSensorUpdate OBJECT-TYPE
    SYNTAX INTEGER{
        done(1),
        update(2)
        }
    ACCESS read-write
    STATUS mandatory
    DESCRIPTION
        "One-shot trigger to update all Storage Sensor objects with 
         Monitoring configuration for all monitoring parameters.
         When completed, Agent will set this attribute to done(1)."
    DEFVAL { 1 }
    ::= { vmvcAimConfigMonitorStorageSensorGroup  1 }

vmvcAimConfigMonStorageSensorVCUID OBJECT-TYPE
    SYNTAX INTEGER
    ACCESS read-write
    STATUS mandatory
    DESCRIPTION
        "This attribute will scope the UPDATE request to the objects 
         within a single matching VC Instance UID 
         (see vmvcAimConfigVCTable).  If this attribute
         is set to zero(0), all objects will be updated."
    DEFVAL { 0 }
    ::= { vmvcAimConfigMonitorStorageSensorGroup  2 }

vmvcAimConfigMonStorageSensorAlert OBJECT-TYPE
    SYNTAX INTEGER {
        not-green-warn(1),
        not-green-critical(2)
    }
    ACCESS read-write
    STATUS mandatory
    DESCRIPTION
        "Level for the alert.   The value of this attribute is
         used as a default value for created objects."
    DEFVAL { 2 }
    ::= { vmvcAimConfigMonitorStorageSensorGroup  3 }

vmvcAimConfigMonStorageSensorMonitor OBJECT-TYPE
    SYNTAX INTEGER {
        do-not-monitor(1),
        monitor(2)
    }
    ACCESS read-write
    STATUS mandatory
    DESCRIPTION
        "Flag whether to monitor the Sensor or not.   The value of this 
         attribute is used as a default value for created objects."
    DEFVAL { 2 }
    ::= { vmvcAimConfigMonitorStorageSensorGroup  4 }


-- *****************************************************************************
-- General Stat Group
-- *****************************************************************************
vmvcAimStatGenTotal OBJECT-TYPE
    SYNTAX INTEGER
    ACCESS read-only
    STATUS mandatory
    DESCRIPTION
        "The total number of Objects monitored."
    ::= { vmvcAimStatGeneralGroup 1 }

vmvcAimStatGenTotalWarn OBJECT-TYPE
    SYNTAX INTEGER
    ACCESS read-only
    STATUS mandatory
    DESCRIPTION
        "The number of monitored objects in a warning state."
    ::= { vmvcAimStatGeneralGroup 2 }

vmvcAimStatGenTotalCrit OBJECT-TYPE
    SYNTAX INTEGER
    ACCESS read-only
    STATUS mandatory
    DESCRIPTION
        "The number of monitored objects in a critical state."
    ::= { vmvcAimStatGeneralGroup 3 }

vmvcAimStatGenTotalHost OBJECT-TYPE
        SYNTAX INTEGER
    ACCESS read-only
    STATUS mandatory
    DESCRIPTION
        "Total number of hosts monitored."
    ::= { vmvcAimStatGeneralGroup 4 }

vmvcAimStatGenTotalHostWarn OBJECT-TYPE
        SYNTAX INTEGER
    ACCESS read-only
    STATUS mandatory
    DESCRIPTION
        "Total number of hosts in warning state, calculated as the highest severity of the following:
             vmvcAimStatHostMemoryState
             vmvcAimStatHostCPUAggregateStatus"
    ::= { vmvcAimStatGeneralGroup 5 }

vmvcAimStatGenTotalHostCrit OBJECT-TYPE
        SYNTAX INTEGER
    ACCESS read-only
    STATUS mandatory
    DESCRIPTION
        "Total number of hosts in critical state, calculated as the highest severity of the following:
             vmvcAimStatHostMemoryState
             vmvcAimStatHostCPUAggregateStatus"
    ::= { vmvcAimStatGeneralGroup 6 }

vmvcAimStatGenTotalVM OBJECT-TYPE
    SYNTAX INTEGER
    ACCESS read-only
    STATUS mandatory
    DESCRIPTION
        "Total number of VMs monitored."
    ::= { vmvcAimStatGeneralGroup 7 }

vmvcAimStatGenTotalVMWarn OBJECT-TYPE
    SYNTAX INTEGER
    ACCESS read-only
    STATUS mandatory
    DESCRIPTION
        "Total number of VMs in warning state, calculated as the highest severity of the following:
             vmvcAimStatVMPowerState
             vmvcAimStatVMHeartbeatState
             vmvcAimStatVMMemoryState
             vmvcAimStatVMPctReadyState
             vmvcAimStatVMCPUAggregateStatus"
    ::= { vmvcAimStatGeneralGroup 8 }

vmvcAimStatGenTotalVMCrit OBJECT-TYPE
    SYNTAX INTEGER
    ACCESS read-only
    STATUS mandatory
    DESCRIPTION
        "Total number of VMs in critical state, calculated as the highest severity of the following:
             vmvcAimStatVMPowerState
             vmvcAimStatVMHeartbeatState
             vmvcAimStatVMMemoryState
             vmvcAimStatVMPctReadyState
             vmvcAimStatVMCPUAggregateStatus"
    ::= { vmvcAimStatGeneralGroup 9 }

vmvcAimStatGenTotalDatastore OBJECT-TYPE
    SYNTAX INTEGER
    ACCESS read-only
    STATUS mandatory
    DESCRIPTION
        "Total number of Datastores monitored."
    ::= { vmvcAimStatGeneralGroup 10 }

vmvcAimStatGenTotalDatastoreWarn OBJECT-TYPE
    SYNTAX INTEGER
    ACCESS read-only
    STATUS mandatory
    DESCRIPTION
        "Total number of Datastores in warning state, calculated as the highest severity of the following:
             vmvcAimStatDatastoreFreeSpaceState
             vmvcAimStatDatastoreAccessState"
    ::= { vmvcAimStatGeneralGroup 11 }

vmvcAimStatGenTotalDatastoreCrit OBJECT-TYPE
    SYNTAX INTEGER
    ACCESS read-only
    STATUS mandatory
    DESCRIPTION
        "Total number of Datastores in critical state, calculated as the highest severity of the following:
             vmvcAimStatDatastoreFreeSpaceState
             vmvcAimStatDatastoreAccessState"
    ::= { vmvcAimStatGeneralGroup 12 }

vmvcAimStatGenTotalVDisk OBJECT-TYPE
    SYNTAX INTEGER
    ACCESS read-only
    STATUS mandatory
    DESCRIPTION
        "Total number of VDisks Monitored"
    ::= { vmvcAimStatGeneralGroup 13 }

vmvcAimStatGenTotalVDiskWarn OBJECT-TYPE
    SYNTAX INTEGER
    ACCESS read-only
    STATUS mandatory
    DESCRIPTION
        "Total number of VDisks in warning state, based on vmvcAimStatVMVDiskState."
    ::= { vmvcAimStatGeneralGroup 14 }

vmvcAimStatGenTotalVDiskCrit OBJECT-TYPE
    SYNTAX INTEGER
    ACCESS read-only
    STATUS mandatory
    DESCRIPTION
        "Total number of VDisks in critical state, based on vmvcAimStatVMVDiskState."
    ::= { vmvcAimStatGeneralGroup 15 }

vmvcAimStatGenTotalVSwitch OBJECT-TYPE
    SYNTAX INTEGER
    ACCESS read-only
    STATUS mandatory
    DESCRIPTION
        "Total number of VSwitchs monitored."
    ::= { vmvcAimStatGeneralGroup 16 }

vmvcAimStatGenTotalVSwitchWarn OBJECT-TYPE
    SYNTAX INTEGER
    ACCESS read-only
    STATUS mandatory
    DESCRIPTION
        "Total number of VSwitchs in warning state, based on vmvcAimStatSwitchState."
    ::= { vmvcAimStatGeneralGroup 17 }

vmvcAimStatGenTotalVSwitchCrit OBJECT-TYPE
    SYNTAX INTEGER
    ACCESS read-only
    STATUS mandatory
    DESCRIPTION
        "Total number of VSwitchs in critical state, based on vmvcAimStatSwitchState."
    ::= { vmvcAimStatGeneralGroup 18 }

vmvcAimStatGenTotalPNIC OBJECT-TYPE
    SYNTAX INTEGER
    ACCESS read-only
    STATUS mandatory
    DESCRIPTION
        "Total number of Physical NICs monitored."
    ::= { vmvcAimStatGeneralGroup 19 }

vmvcAimStatGenTotalPNICWarn OBJECT-TYPE
    SYNTAX INTEGER
    ACCESS read-only
    STATUS mandatory
    DESCRIPTION
        "Total number of Physical NICs in warning state, based on vmvcAimStatPNICState."
    ::= { vmvcAimStatGeneralGroup 20 }

vmvcAimStatGenTotalPNICCrit OBJECT-TYPE
    SYNTAX INTEGER
    ACCESS read-only
    STATUS mandatory
    DESCRIPTION
        "Total number of Physical NICs in critical state, based on vmvcAimStatPNICState."
    ::= { vmvcAimStatGeneralGroup 21 }

vmvcAimStatGenTotalVNIC OBJECT-TYPE
    SYNTAX INTEGER
    ACCESS read-only
    STATUS mandatory
    DESCRIPTION
        "Total number of Virtual NICs monitored."
    ::= { vmvcAimStatGeneralGroup 22 }

vmvcAimStatGenTotalVNICWarn OBJECT-TYPE
    SYNTAX INTEGER
    ACCESS read-only
    STATUS mandatory
    DESCRIPTION
        "Total number of Virtual NICs in warning state, based on vmvcAimStatVMVNICState."
    ::= { vmvcAimStatGeneralGroup 23 }

vmvcAimStatGenTotalVNICCrit OBJECT-TYPE
    SYNTAX INTEGER
    ACCESS read-only
    STATUS mandatory
    DESCRIPTION
        "Total number of Virtual NICs in critical state, based on vmvcAimStatVMVNICState."
    ::= { vmvcAimStatGeneralGroup 24 }

vmvcAimStatGenTotalCPUSensors OBJECT-TYPE
    SYNTAX INTEGER
    ACCESS read-only
    STATUS mandatory
    DESCRIPTION
        "Total number of CPU Sensors monitored."
    ::= { vmvcAimStatGeneralGroup 25 }

vmvcAimStatGenTotalCPUSensorsWarn OBJECT-TYPE
    SYNTAX INTEGER
    ACCESS read-only
    STATUS mandatory
    DESCRIPTION
        "Total number of CPUSensors in warning state, based on vmvcAimStatCPUSensorState."
    ::= { vmvcAimStatGeneralGroup 26 }

vmvcAimStatGenTotalCPUSensorsCrit OBJECT-TYPE
    SYNTAX INTEGER
    ACCESS read-only
    STATUS mandatory
    DESCRIPTION
        "Total number of CPUSensors in critical state, based on vmvcAimStatCPUSensorState."
    ::= { vmvcAimStatGeneralGroup 27 }

vmvcAimStatGenTotalMemSensors OBJECT-TYPE
    SYNTAX INTEGER
    ACCESS read-only
    STATUS mandatory
    DESCRIPTION
        "Total number of MemSensors monitored."
    ::= { vmvcAimStatGeneralGroup 28 }

vmvcAimStatGenTotalMemSensorsWarn OBJECT-TYPE
    SYNTAX INTEGER
    ACCESS read-only
    STATUS mandatory
    DESCRIPTION
        "Total number of MemSensors in warning state, based on vmvcAimStatMemSensorState."
    ::= { vmvcAimStatGeneralGroup 29 }

vmvcAimStatGenTotalMemSensorsCrit OBJECT-TYPE
    SYNTAX INTEGER
    ACCESS read-only
    STATUS mandatory
    DESCRIPTION
        "Total number of MemSensors in critical state, based on vmvcAimStatMemSensorState."
    ::= { vmvcAimStatGeneralGroup 30 }

vmvcAimStatGenTotalFanSensors OBJECT-TYPE
    SYNTAX INTEGER
    ACCESS read-only
    STATUS mandatory
    DESCRIPTION
        "Total number of FanSensors monitored."
    ::= { vmvcAimStatGeneralGroup 31 }

vmvcAimStatGenTotalFanSensorsWarn OBJECT-TYPE
    SYNTAX INTEGER
    ACCESS read-only
    STATUS mandatory
    DESCRIPTION
        "Total number of FanSensors in warning state, based on vmvcAimStatFanSensorState."
    ::= { vmvcAimStatGeneralGroup 32 }

vmvcAimStatGenTotalFanSensorsCrit OBJECT-TYPE
    SYNTAX INTEGER
    ACCESS read-only
    STATUS mandatory
    DESCRIPTION
        "Total number of FanSensors in critical state, based on vmvcAimStatFanSensorState."
    ::= { vmvcAimStatGeneralGroup 33 }

vmvcAimStatGenTotalVoltageSensors OBJECT-TYPE
    SYNTAX INTEGER
    ACCESS read-only
    STATUS mandatory
    DESCRIPTION
        "Total number of VoltageSensors monitored."
    ::= { vmvcAimStatGeneralGroup 34 }

vmvcAimStatGenTotalVoltageSensorsWarn OBJECT-TYPE
    SYNTAX INTEGER
    ACCESS read-only
    STATUS mandatory
    DESCRIPTION
        "Total number of VoltageSensors in warning state, based on vmvcAimStatVoltageSensorState."
    ::= { vmvcAimStatGeneralGroup 35 }

vmvcAimStatGenTotalVoltageSensorsCrit OBJECT-TYPE
    SYNTAX INTEGER
    ACCESS read-only
    STATUS mandatory
    DESCRIPTION
        "Total number of VoltageSensors in critical state, based on vmvcAimStatVoltageSensorState."
    ::= { vmvcAimStatGeneralGroup 36 }

vmvcAimStatGenTotalTempSensors OBJECT-TYPE
    SYNTAX INTEGER
    ACCESS read-only
    STATUS mandatory
    DESCRIPTION
        "Total number of TempSensors monitored."
    ::= { vmvcAimStatGeneralGroup 37 }

vmvcAimStatGenTotalTempSensorsWarn OBJECT-TYPE
    SYNTAX INTEGER
    ACCESS read-only
    STATUS mandatory
    DESCRIPTION
        "Total number of TempSensors in warning state, based on vmvcAimStatTempSensorState."
    ::= { vmvcAimStatGeneralGroup 38 }

vmvcAimStatGenTotalTempSensorsCrit OBJECT-TYPE
    SYNTAX INTEGER
    ACCESS read-only
    STATUS mandatory
    DESCRIPTION
        "Total number of TempSensors in critical state, based on vmvcAimStatTempSensorState."
    ::= { vmvcAimStatGeneralGroup 39 }

vmvcAimStatGenTotalPowerSensors OBJECT-TYPE
    SYNTAX INTEGER
    ACCESS read-only
    STATUS mandatory
    DESCRIPTION
        "Total number of PowerSensors monitored."
    ::= { vmvcAimStatGeneralGroup 40 }

vmvcAimStatGenTotalPowerSensorsWarn OBJECT-TYPE
    SYNTAX INTEGER
    ACCESS read-only
    STATUS mandatory
    DESCRIPTION
        "Total number of PowerSensors in warning state, based on vmvcAimStatPowerSensorState."
    ::= { vmvcAimStatGeneralGroup 41 }

vmvcAimStatGenTotalPowerSensorsCrit OBJECT-TYPE
    SYNTAX INTEGER
    ACCESS read-only
    STATUS mandatory
    DESCRIPTION
        "Total number of PowerSensors in critical state, based on vmvcAimStatPowerSensorState."
    ::= { vmvcAimStatGeneralGroup 42 }

vmvcAimStatGenTotalDatacenters OBJECT-TYPE
    SYNTAX INTEGER
    ACCESS read-only
    STATUS mandatory
    DESCRIPTION
        "Total number of Datacenters monitored."
    ::= { vmvcAimStatGeneralGroup 43 }

vmvcAimStatGenTotalDatacentersWarn OBJECT-TYPE
    SYNTAX INTEGER
    ACCESS read-only
    STATUS mandatory
    DESCRIPTION
        "Total number of Datacenters in warning state, based on vmvcAimStatDatacenterOverallState."
    ::= { vmvcAimStatGeneralGroup 44 }

vmvcAimStatGenTotalDatacentersCrit OBJECT-TYPE
    SYNTAX INTEGER
    ACCESS read-only
    STATUS mandatory
    DESCRIPTION
        "Total number of Datacenters in critical state, based on vmvcAimStatDatacenterOverallState."
    ::= { vmvcAimStatGeneralGroup 45 }

vmvcAimStatGenTotalResPools OBJECT-TYPE
    SYNTAX INTEGER
    ACCESS read-only
    STATUS mandatory
    DESCRIPTION
        "Total number of Resource Pools monitored."
    ::= { vmvcAimStatGeneralGroup 46 }

vmvcAimStatGenTotalResPoolsWarn OBJECT-TYPE
    SYNTAX INTEGER
    ACCESS read-only
    STATUS mandatory
    DESCRIPTION
        "Total number of Resource Pools in warning state, calculated as the highest severity of the following:
             vmvcAimStatResourcePoolCPUState
             vmvcAimStatResourcePoolMemState
             vmvcAimStatResourcePoolState"
    ::= { vmvcAimStatGeneralGroup 47 }

vmvcAimStatGenTotalResPoolsCrit OBJECT-TYPE
    SYNTAX INTEGER
    ACCESS read-only
    STATUS mandatory
    DESCRIPTION
        "Total number of Resource Pools in critical state, calculated as the highest severity of the following:
             vmvcAimStatResourcePoolCPUState
             vmvcAimStatResourcePoolMemState
             vmvcAimStatResourcePoolState"
    ::= { vmvcAimStatGeneralGroup 48 }

vmvcAimStatGenTotalVMGuestDisks OBJECT-TYPE
    SYNTAX INTEGER
    ACCESS read-only
    STATUS mandatory
    DESCRIPTION
        "Total number of VM Guest Disks monitored."
    ::= { vmvcAimStatGeneralGroup 49 }

vmvcAimStatGenTotalVMGuestDisksWarn OBJECT-TYPE
    SYNTAX INTEGER
    ACCESS read-only
    STATUS mandatory
    DESCRIPTION
        "Total number of VM Guest Disks in warning state, based on vmvcAimStatVMGuestDiskState."
    ::= { vmvcAimStatGeneralGroup 50 }

vmvcAimStatGenTotalVMGuestDisksCrit OBJECT-TYPE
    SYNTAX INTEGER
    ACCESS read-only
    STATUS mandatory
    DESCRIPTION
        "Total number of VM Guest Disks in critical state, based on vmvcAimStatVMGuestDiskState."
    ::= { vmvcAimStatGeneralGroup 51 }

vmvcAimStatGenTotalCustSpec OBJECT-TYPE
    SYNTAX INTEGER
    ACCESS read-only
    STATUS mandatory
    DESCRIPTION
        "Total number of Customization Specifications."
    ::= { vmvcAimStatGeneralGroup 52 }

vmvcAimStatGenTotalCustSpecWarn OBJECT-TYPE
    SYNTAX INTEGER
    ACCESS read-only
    STATUS mandatory
    DESCRIPTION
        "Total number of Customization Specifications in warning state.  Currently always zero(0)."
    ::= { vmvcAimStatGeneralGroup 53 }

vmvcAimStatGenTotalCustSpecCrit OBJECT-TYPE
    SYNTAX INTEGER
    ACCESS read-only
    STATUS mandatory
    DESCRIPTION
        "Total number of Customization Specifications in critical state.  Currently always zero(0)."
    ::= { vmvcAimStatGeneralGroup 54 }

vmvcAimStatGenTotalDCFolder OBJECT-TYPE
    SYNTAX INTEGER
    ACCESS read-only
    STATUS mandatory
    DESCRIPTION
        "Total number of Datacenter Folders."
    ::= { vmvcAimStatGeneralGroup 55 }

vmvcAimStatGenTotalDCFolderWarn OBJECT-TYPE
    SYNTAX INTEGER
    ACCESS read-only
    STATUS mandatory
    DESCRIPTION
        "Total number of Datacenter Folders in warning state.  Currently always zero(0)."
    ::= { vmvcAimStatGeneralGroup 56 }

vmvcAimStatGenTotalDCFolderCrit OBJECT-TYPE
    SYNTAX INTEGER
    ACCESS read-only
    STATUS mandatory
    DESCRIPTION
        "Total number of Datacenter Folders in critical state.  Currently always zero(0)."
    ::= { vmvcAimStatGeneralGroup 57 }

vmvcAimStatGenTotalCompResFolder OBJECT-TYPE
    SYNTAX INTEGER
    ACCESS read-only
    STATUS mandatory
    DESCRIPTION
        "Total number of ComputeResource Folders."
    ::= { vmvcAimStatGeneralGroup 58 }

vmvcAimStatGenTotalCompResFolderWarn OBJECT-TYPE
    SYNTAX INTEGER
    ACCESS read-only
    STATUS mandatory
    DESCRIPTION
        "Total number of ComputeResource Folders in warning state.  Currently always zero(0)."
    ::= { vmvcAimStatGeneralGroup 59 }

vmvcAimStatGenTotalCompResFolderCrit OBJECT-TYPE
    SYNTAX INTEGER
    ACCESS read-only
    STATUS mandatory
    DESCRIPTION
        "Total number of ComputeResource Folders in critical state.  Currently always zero(0)."
    ::= { vmvcAimStatGeneralGroup 60 }

vmvcAimStatGenTotalCluster OBJECT-TYPE
    SYNTAX INTEGER
    ACCESS read-only
    STATUS mandatory
    DESCRIPTION
        "Total number of Clusters."
    ::= { vmvcAimStatGeneralGroup 61 }

vmvcAimStatGenTotalClusterWarn OBJECT-TYPE
    SYNTAX INTEGER
    ACCESS read-only
    STATUS mandatory
    DESCRIPTION
        "Total number of Clusters in warning state.  Currently always zero(0)."
    ::= { vmvcAimStatGeneralGroup 62 }

vmvcAimStatGenTotalClusterCrit OBJECT-TYPE
    SYNTAX INTEGER
    ACCESS read-only
    STATUS mandatory
    DESCRIPTION
        "Total number of Clusters in critical state.  Currently always zero(0)."
    ::= { vmvcAimStatGeneralGroup 63 }

vmvcAimStatGenTotalTemplate OBJECT-TYPE
    SYNTAX INTEGER
    ACCESS read-only
    STATUS mandatory
    DESCRIPTION
        "Total number of Templates."
    ::= { vmvcAimStatGeneralGroup 64 }

vmvcAimStatGenTotalTemplateWarn OBJECT-TYPE
    SYNTAX INTEGER
    ACCESS read-only
    STATUS mandatory
    DESCRIPTION
        "Total number of Templates in warning state.  Currently always zero(0)."
    ::= { vmvcAimStatGeneralGroup 65 }

vmvcAimStatGenTotalTemplateCrit OBJECT-TYPE
    SYNTAX INTEGER
    ACCESS read-only
    STATUS mandatory
    DESCRIPTION
        "Total number of Templates in critical state.  Currently always zero(0)."
    ::= { vmvcAimStatGeneralGroup 66 }

vmvcAimStatGenTotalPortGrp OBJECT-TYPE
    SYNTAX INTEGER
    ACCESS read-only
    STATUS mandatory
    DESCRIPTION
        "Total number of Port Groups."
    ::= { vmvcAimStatGeneralGroup 67 }

vmvcAimStatGenTotalPortGrpWarn OBJECT-TYPE
    SYNTAX INTEGER
    ACCESS read-only
    STATUS mandatory
    DESCRIPTION
        "Total number of Port Groups in warning state.  Currently always zero(0)."
    ::= { vmvcAimStatGeneralGroup 68 }

vmvcAimStatGenTotalPortGrpCrit OBJECT-TYPE
    SYNTAX INTEGER
    ACCESS read-only
    STATUS mandatory
    DESCRIPTION
        "Total number of Port Groups in critical state.  Currently always zero(0)."
    ::= { vmvcAimStatGeneralGroup 69 }

vmvcAimStatGenTotalHostVNIC OBJECT-TYPE
    SYNTAX INTEGER
    ACCESS read-only
    STATUS mandatory
    DESCRIPTION
        "Total number of Host Virtual NICs."
    ::= { vmvcAimStatGeneralGroup 70 }

vmvcAimStatGenTotalHostVNICWarn OBJECT-TYPE
    SYNTAX INTEGER
    ACCESS read-only
    STATUS mandatory
    DESCRIPTION
        "Total number of Host Virtual NICs in warning state.  Currently always zero(0)."
    ::= { vmvcAimStatGeneralGroup 71 }

vmvcAimStatGenTotalHostVNICCrit OBJECT-TYPE
    SYNTAX INTEGER
    ACCESS read-only
    STATUS mandatory
    DESCRIPTION
        "Total number of Host Virtual NICs in critical state.  Currently always zero(0)."
    ::= { vmvcAimStatGeneralGroup 72 }

vmvcAimStatGenTotalCustSpecNIC OBJECT-TYPE
    SYNTAX INTEGER
    ACCESS read-only
    STATUS mandatory
    DESCRIPTION
        "Total number of Customization Specification NICs."
    ::= { vmvcAimStatGeneralGroup 73 }

vmvcAimStatGenTotalCustSpecNICWarn OBJECT-TYPE
    SYNTAX INTEGER
    ACCESS read-only
    STATUS mandatory
    DESCRIPTION
        "Total number of Customization Specification NICs in warning state.  Currently always zero(0)."
    ::= { vmvcAimStatGeneralGroup 74 }

vmvcAimStatGenTotalCustSpecNICCrit OBJECT-TYPE
    SYNTAX INTEGER
    ACCESS read-only
    STATUS mandatory
    DESCRIPTION
        "Total number of Customization Specification NICs in critical state.  Currently always zero(0)."
    ::= { vmvcAimStatGeneralGroup 75 }

vmvcAimStatGenTotalHostDisk OBJECT-TYPE
    SYNTAX INTEGER
    ACCESS read-only
    STATUS mandatory
    DESCRIPTION
        "Total number of Host Disks."
    ::= { vmvcAimStatGeneralGroup 76 }

vmvcAimStatGenTotalHostDiskWarn OBJECT-TYPE
    SYNTAX INTEGER
    ACCESS read-only
    STATUS mandatory
    DESCRIPTION
        "Total number of Host Disks in warning state.  Currently always zero(0)."
    ::= { vmvcAimStatGeneralGroup 77 }

vmvcAimStatGenTotalHostDiskCrit OBJECT-TYPE
    SYNTAX INTEGER
    ACCESS read-only
    STATUS mandatory
    DESCRIPTION
        "Total number of Host Disks in critical state.  Currently always zero(0)."
    ::= { vmvcAimStatGeneralGroup 78 }

vmvcAimStatGenTotalSCSIController OBJECT-TYPE
    SYNTAX INTEGER
    ACCESS read-only
    STATUS mandatory
    DESCRIPTION
        "Total number of SCSI Controllers."
    ::= { vmvcAimStatGeneralGroup 79 }

vmvcAimStatGenTotalSCSIControllerWarn OBJECT-TYPE
    SYNTAX INTEGER
    ACCESS read-only
    STATUS mandatory
    DESCRIPTION
        "Total number of SCSI Controllers in warning state.  Currently always zero(0)."
    ::= { vmvcAimStatGeneralGroup 80 }

vmvcAimStatGenTotalSCSIControllerCrit OBJECT-TYPE
    SYNTAX INTEGER
    ACCESS read-only
    STATUS mandatory
    DESCRIPTION
        "Total number of SCSI Controllers in critical state.  Currently always zero(0)."
    ::= { vmvcAimStatGeneralGroup 81 }

vmvcAimStatGenTotalSnapshot OBJECT-TYPE
    SYNTAX INTEGER
    ACCESS read-only
    STATUS mandatory
    DESCRIPTION
        "Total number of Snapshots."
    ::= { vmvcAimStatGeneralGroup 82 }

vmvcAimStatGenTotalSnapshotWarn OBJECT-TYPE
    SYNTAX INTEGER
    ACCESS read-only
    STATUS mandatory
    DESCRIPTION
        "Total number of Snapshots in warning state.  Currently always zero(0)."
    ::= { vmvcAimStatGeneralGroup 83 }

vmvcAimStatGenTotalSnapshotCrit OBJECT-TYPE
        SYNTAX INTEGER
    ACCESS read-only
    STATUS mandatory
    DESCRIPTION
        "Total number of Snapshots in critical state.  Currently always zero(0)."
    ::= { vmvcAimStatGeneralGroup 84 }

vmvcAimStatGenTotalStorageSensors OBJECT-TYPE
    SYNTAX INTEGER
    ACCESS read-only
    STATUS mandatory
    DESCRIPTION
        "Total number of StorageSensors monitored."
    ::= { vmvcAimStatGeneralGroup 85 }

vmvcAimStatGenTotalStorageSensorsWarn OBJECT-TYPE
    SYNTAX INTEGER
    ACCESS read-only
    STATUS mandatory
    DESCRIPTION
        "Total number of StorageSensors in warning state, based on vmvcAimStatStorageSensorState."
    ::= { vmvcAimStatGeneralGroup 86 }

vmvcAimStatGenTotalStorageSensorsCrit OBJECT-TYPE
    SYNTAX INTEGER
    ACCESS read-only
    STATUS mandatory
    DESCRIPTION
        "Total number of StorageSensors in critical state, based on vmvcAimStatStorageSensorState."
    ::= { vmvcAimStatGeneralGroup 87 }

vmvcAimStatGenTotalVC OBJECT-TYPE
    SYNTAX INTEGER
    ACCESS read-only
    STATUS mandatory
    DESCRIPTION
        "Total number of Virtual Centers monitored."
    ::= { vmvcAimStatGeneralGroup 88 }

vmvcAimStatGenTotalVCWarn OBJECT-TYPE
    SYNTAX INTEGER
    ACCESS read-only
    STATUS mandatory
    DESCRIPTION
        "Total number of Virtual Centers in warning state, based on vmvcAimStatVCState."
    ::= { vmvcAimStatGeneralGroup 89 }

vmvcAimStatGenTotalVCCrit OBJECT-TYPE
    SYNTAX INTEGER
    ACCESS read-only
    STATUS mandatory
    DESCRIPTION
        "Total number of in critical state, based on vmvcAimStatVCState."
    ::= { vmvcAimStatGeneralGroup 90 }

vmvcAimStatGenTotalDistribVSwitch OBJECT-TYPE
    SYNTAX INTEGER
    ACCESS read-only
    STATUS mandatory
    DESCRIPTION
        "Total number of Distributed Virtual Switches monitored."
    ::= { vmvcAimStatGeneralGroup 91 }

vmvcAimStatGenTotalDistribVSwitchWarn OBJECT-TYPE
    SYNTAX INTEGER
    ACCESS read-only
    STATUS mandatory
    DESCRIPTION
        "Total number of Distributed Virtual Switches in warning state, based on vmvcAimStatDVSwitchState."
    ::= { vmvcAimStatGeneralGroup 92 }

vmvcAimStatGenTotalDistribVSwitchCrit OBJECT-TYPE
    SYNTAX INTEGER
    ACCESS read-only
    STATUS mandatory
    DESCRIPTION
        "Total number of Distributed Virtual Switches in critical state, based on vmvcAimStatDVSwitchState."
    ::= { vmvcAimStatGeneralGroup 93 }

vmvcAimStatGenTotalDVPortGrp OBJECT-TYPE
    SYNTAX INTEGER
    ACCESS read-only
    STATUS mandatory
    DESCRIPTION
        "Total number of Distributed Virtual Port Groups monitored."
    ::= { vmvcAimStatGeneralGroup 94 }

vmvcAimStatGenTotalDVPortGrpWarn OBJECT-TYPE
    SYNTAX INTEGER
    ACCESS read-only
    STATUS mandatory
    DESCRIPTION
        "Total number of Distributed Virtual Port Groups in warning state.  Currently always zero(0)."
    ::= { vmvcAimStatGeneralGroup 95 }

vmvcAimStatGenTotalDVPortGrpCrit OBJECT-TYPE
    SYNTAX INTEGER
    ACCESS read-only
    STATUS mandatory
    DESCRIPTION
        "Total number of Distributed Virtual Port Groups in warning state.  Currently always zero(0)."
    ::= { vmvcAimStatGeneralGroup 96 }

vmvcAimStatGenTotalNetFolder OBJECT-TYPE
    SYNTAX INTEGER
    ACCESS read-only
    STATUS mandatory
    DESCRIPTION
        "Total number of Network Folders monitored."
    ::= { vmvcAimStatGeneralGroup 97 }

vmvcAimStatGenTotalNetFolderWarn OBJECT-TYPE
    SYNTAX INTEGER
    ACCESS read-only
    STATUS mandatory
    DESCRIPTION
        "Total number of Network Folders in warning state.  Currently always zero(0)."
    ::= { vmvcAimStatGeneralGroup 98 }

vmvcAimStatGenTotalNetFolderCrit OBJECT-TYPE
    SYNTAX INTEGER
    ACCESS read-only
    STATUS mandatory
    DESCRIPTION
        "Total number of Network Folders in warning state.  Currently always zero(0)."
    ::= { vmvcAimStatGeneralGroup 99 }


-- *****************************************************************************
-- Status VC Group
-- *****************************************************************************
vmvcAimStatServerName OBJECT-TYPE
    SYNTAX SnmpAdminString
    ACCESS read-only
    STATUS mandatory
    DESCRIPTION
        "Name of the server VC is running on.
         NOTE:  This parameter is deprecated, and is only accessible when the AIM is in single-instance
                compatibility mode."
    ::= { vmvcAimStatVCGroup 1 }

vmvcAimStatServerProduct OBJECT-TYPE
    SYNTAX SnmpAdminString
    ACCESS read-only
    STATUS mandatory
    DESCRIPTION
        "Name of VC product.
         NOTE:  This parameter is deprecated, and is only accessible when the AIM is in single-instance
                compatibility mode."
    ::= { vmvcAimStatVCGroup 2 }

vmvcAimStatServerOSType OBJECT-TYPE
    SYNTAX SnmpAdminString
    ACCESS read-only
    STATUS mandatory
    DESCRIPTION
        "Type of the OS VC is running on.
         NOTE:  This parameter is deprecated, and is only accessible when the AIM is in single-instance
                compatibility mode."
    ::= { vmvcAimStatVCGroup 3 }

vmvcAimStatServerVer OBJECT-TYPE
    SYNTAX SnmpAdminString
    ACCESS read-only
    STATUS mandatory
    DESCRIPTION
        "VC version.
         NOTE:  This parameter is deprecated, and is only accessible when the AIM is in single-instance
                compatibility mode."
    ::= { vmvcAimStatVCGroup 4 }

vmvcAimStatServerAPIVer OBJECT-TYPE
    SYNTAX SnmpAdminString
    ACCESS read-only
    STATUS mandatory
    DESCRIPTION
        "Version of the VI SDK.
         NOTE:  This parameter is deprecated, and is only accessible when the AIM is in single-instance
                compatibility mode."
    ::= { vmvcAimStatVCGroup 5}

vmvcAimStatServerBuild OBJECT-TYPE
    SYNTAX SnmpAdminString
    ACCESS read-only
    STATUS mandatory
    DESCRIPTION
        "Build of the VC server.
         NOTE:  This parameter is deprecated, and is only accessible when the AIM is in single-instance
                compatibility mode."
    ::= { vmvcAimStatVCGroup 6}

vmvcAimStatServerProdLine OBJECT-TYPE
    SYNTAX SnmpAdminString
    ACCESS read-only
    STATUS mandatory
    DESCRIPTION
        "Product Identifier.
         NOTE:  This parameter is deprecated, and is only accessible when the AIM is in single-instance
                compatibility mode."
    ::= { vmvcAimStatVCGroup 7}

vmvcAimStatServerStatus OBJECT-TYPE
    SYNTAX INTEGER{
        not-running(1),
        running(2)
        }
    ACCESS read-only
    STATUS mandatory
    DESCRIPTION
        "Status of VirtualCenter service.
         NOTE:  This parameter is deprecated, and is only accessible when the AIM is in single-instance
                compatibility mode."
    ::= { vmvcAimStatVCGroup 8}

vmvcAimStatServerStatusAlert OBJECT-TYPE
    SYNTAX INTEGER{
        not-running-warn(1),
        not-running-crit(2)
        }
    ACCESS read-write
    STATUS mandatory
    DESCRIPTION
        "Type of alert for server status.
         NOTE:  This parameter is deprecated, and is only accessible when the AIM is in single-instance
                compatibility mode."
    DEFVAL { 2 }
    ::= { vmvcAimStatVCGroup 9}

vmvcAimStatServerStatusMonitor OBJECT-TYPE
    SYNTAX INTEGER{
        do-not-monitor(1),
        monitor(2)
        }
    ACCESS read-write
    STATUS mandatory
    DESCRIPTION
        "Monitor state of VC Service Status.
         NOTE:  This parameter is deprecated, and is only accessible when the AIM is in single-instance
                compatibility mode."
    DEFVAL { 2 }
    ::= { vmvcAimStatVCGroup 10}

vmvcAimStatServerState OBJECT-TYPE
    SYNTAX INTEGER {
        unknown(1),
        ok(2),
        warning(3),
        critical(4)
    }
    ACCESS read-only
    STATUS mandatory
    DESCRIPTION
        "State of VirtualCenter service.
         NOTE:  This parameter is deprecated, and is only accessible when the AIM is in single-instance
                compatibility mode."
    ::= { vmvcAimStatVCGroup 11}

vmvcAimStatServerCPUUsage OBJECT-TYPE
    SYNTAX INTEGER
    ACCESS read-only
    STATUS mandatory
    DESCRIPTION
        "CPU Usage of the Host.
         NOTE:  This parameter is only retrievable when the AIM is installed on the local vCenter instance.
                When AIM is remote, this parameter is zero(0).
         NOTE:  This parameter is deprecated, and is only accessible when the AIM is in single-instance
                compatibility mode."
    ::= { vmvcAimStatVCGroup  12}

vmvcAimStatServerAlertCPUUsageWarnThresh OBJECT-TYPE
    SYNTAX INTEGER
    ACCESS read-write
    STATUS mandatory
    DESCRIPTION
        "Warning threshold  for CPU usage.
         NOTE:  This parameter is deprecated, and is only accessible when the AIM is in single-instance
                compatibility mode."
    DEFVAL { 60 }
    ::= { vmvcAimStatVCGroup  13}

vmvcAimStatServerAlertCPUUsageCritThresh OBJECT-TYPE
    SYNTAX INTEGER
    ACCESS read-write
    STATUS mandatory
    DESCRIPTION
        "Critical threshold  for CPU usage.
         NOTE:  This parameter is deprecated, and is only accessible when the AIM is in single-instance
                compatibility mode."
    DEFVAL { 80 }
    ::= { vmvcAimStatVCGroup  14}

vmvcAimStatServerCPUAlert OBJECT-TYPE
    SYNTAX INTEGER{
        warning-only(1),
        critical-only(2),
        both(3)    
        }
    ACCESS read-write
    STATUS mandatory
    DESCRIPTION
        "Alert of the cpu status.
         NOTE:  This parameter is deprecated, and is only accessible when the AIM is in single-instance
                compatibility mode."
    DEFVAL { 3 }
    ::= { vmvcAimStatVCGroup  15}

vmvcAimStatServerCPUState OBJECT-TYPE
    SYNTAX INTEGER {
        unknown(1),
        ok(2),
        warning(3),
        critical(4)
    }
    ACCESS read-only
    STATUS mandatory
    DESCRIPTION
        "CPU State of host.
         NOTE:  This parameter is deprecated, and is only accessible when the AIM is in single-instance
                compatibility mode."
    ::= { vmvcAimStatVCGroup  16}

vmvcAimStatServerMemUsage OBJECT-TYPE
    SYNTAX INTEGER
    ACCESS read-only
    STATUS mandatory
    DESCRIPTION 
        "The percentage of Physical Memory Usage of the Server.
         NOTE:  This parameter is only retrievable when the AIM is installed on the local vCenter instance.
                When AIM is remote, this parameter is zero(0).
         NOTE:  This parameter is deprecated, and is only accessible when the AIM is in single-instance
                compatibility mode."
    ::= { vmvcAimStatVCGroup 17 }

vmvcAimStatServerTotalPhysMem OBJECT-TYPE
    SYNTAX INTEGER
    ACCESS read-only
    STATUS mandatory
    DESCRIPTION 
        "The Total Physical Memory (in MB) of the Server.
         NOTE:  This parameter is only retrievable when the AIM is installed on the local vCenter instance.
                When AIM is remote, this parameter is zero(0).
         NOTE:  This parameter is deprecated, and is only accessible when the AIM is in single-instance
                compatibility mode."
    ::= { vmvcAimStatVCGroup 18 }

vmvcAimStatServerUsedPhysMem OBJECT-TYPE
    SYNTAX INTEGER
    ACCESS read-only
    STATUS mandatory
    DESCRIPTION    
        "The Memory Used (in MB) of the Server.
         NOTE:  This parameter is only retrievable when the AIM is installed on the local vCenter instance.
                When AIM is remote, this parameter is zero(0).
         NOTE:  This parameter is deprecated, and is only accessible when the AIM is in single-instance
                compatibility mode."
    ::= { vmvcAimStatVCGroup 19 }

vmvcAimStatServerMemWarnThres OBJECT-TYPE
    SYNTAX INTEGER
    ACCESS read-write
    STATUS mandatory
    DESCRIPTION 
        "Sets the Memory warning threshold value.  Must be lower than the Memory critical threshold value.
         NOTE:  This parameter is deprecated, and is only accessible when the AIM is in single-instance
                compatibility mode."
    DEFVAL { 60 }
    ::= { vmvcAimStatVCGroup 20 }

vmvcAimStatServerMemCritThres OBJECT-TYPE
    SYNTAX INTEGER
    ACCESS read-write
    STATUS mandatory
    DESCRIPTION 
        "Sets the Memory critical threshold value.  Must be higher than the Memory warning threshold value.
         NOTE:  This parameter is deprecated, and is only accessible when the AIM is in single-instance
                compatibility mode."
    DEFVAL { 80 }
    ::= { vmvcAimStatVCGroup 21 }

vmvcAimStatServerMemAlert OBJECT-TYPE
    SYNTAX INTEGER {
        warning-only(1),
        critical-only(2),
        warning-critical(3)
    }
    ACCESS read-write
    STATUS mandatory
    DESCRIPTION 
        "The level of alert to raise, only warning alert, or only critical alert or both.
         NOTE:  This parameter is deprecated, and is only accessible when the AIM is in single-instance
                compatibility mode."
    DEFVAL { 3 }
    ::= { vmvcAimStatVCGroup 22 }

vmvcAimStatServerMemState OBJECT-TYPE
    SYNTAX INTEGER {
        unknown(1),
        ok(2),
        warning(3),
        critical(4)
    }
    ACCESS read-only
    STATUS mandatory
    DESCRIPTION 
        "The State of the Memory Usage of the Server(mem-ok, mem-warning, mem-critical).
         NOTE:  This parameter is deprecated, and is only accessible when the AIM is in single-instance
                compatibility mode."
    ::= { vmvcAimStatVCGroup 23 }

vmvcAimStatServerTotalCPUUsage OBJECT-TYPE
    SYNTAX INTEGER
    ACCESS read-only
    STATUS mandatory
    DESCRIPTION
        "Aggregation of CPU Usage of all Hosts running under the VC.
         NOTE:  This parameter is deprecated, and is only accessible when the AIM is in single-instance
                compatibility mode."
    ::= { vmvcAimStatVCGroup  24}

vmvcAimStatServerTotalCPUUsageWarnThresh OBJECT-TYPE
    SYNTAX INTEGER
    ACCESS read-write
    STATUS mandatory
    DESCRIPTION
        "Warning threshold  for Total CPU usage.
         NOTE:  This parameter is deprecated, and is only accessible when the AIM is in single-instance
                compatibility mode."
    DEFVAL { 60 }
    ::= { vmvcAimStatVCGroup  25}

vmvcAimStatServerTotalCPUUsageCritThresh OBJECT-TYPE
    SYNTAX INTEGER
    ACCESS read-write
    STATUS mandatory
    DESCRIPTION
        "Critical threshold  for Total CPU usage.
         NOTE:  This parameter is deprecated, and is only accessible when the AIM is in single-instance
                compatibility mode."
    DEFVAL { 80 }
    ::= { vmvcAimStatVCGroup  26}

vmvcAimStatServerTotalCPUState OBJECT-TYPE
    SYNTAX INTEGER {
        unknown(1),
        ok(2),
        warning(3),
        critical(4)
    }
    ACCESS read-only
    STATUS mandatory
    DESCRIPTION
        "Total CPU State of VC.
         NOTE:  This parameter is deprecated, and is only accessible when the AIM is in single-instance
                compatibility mode."
    ::= { vmvcAimStatVCGroup  27}

vmvcAimStatServerTotalMemUsage OBJECT-TYPE
    SYNTAX INTEGER
    ACCESS read-only
    STATUS mandatory
    DESCRIPTION 
        "The percentage of Total Physical Memory Usage of all hosts running under the VC.
         NOTE:  This parameter is deprecated, and is only accessible when the AIM is in single-instance
                compatibility mode."
    ::= { vmvcAimStatVCGroup 28 }

vmvcAimStatServerTotalMemWarnThres OBJECT-TYPE
    SYNTAX INTEGER
    ACCESS read-write
    STATUS mandatory
    DESCRIPTION 
        "Sets the Memory warning threshold value.  Must be lower than the Memory critical threshold value.
         NOTE:  This parameter is deprecated, and is only accessible when the AIM is in single-instance
                compatibility mode."
    DEFVAL { 60 }
    ::= { vmvcAimStatVCGroup 29 }

vmvcAimStatServerTotalMemCritThres OBJECT-TYPE
    SYNTAX INTEGER
    ACCESS read-write
    STATUS mandatory
    DESCRIPTION 
        "Sets the Memory critical threshold value.  Must be higher than the Memory warning threshold value.
         NOTE:  This parameter is deprecated, and is only accessible when the AIM is in single-instance
                compatibility mode."
    DEFVAL { 80 }
    ::= { vmvcAimStatVCGroup 30 }

vmvcAimStatServerTotalMemState OBJECT-TYPE
    SYNTAX INTEGER {
        unknown(1),
        ok(2),
        warning(3),
        critical(4)
    }
    ACCESS read-only
    STATUS mandatory
    DESCRIPTION 
        "The State of the Total Memory Usage of the Server(ok, warning, critical).
         NOTE:  This parameter is deprecated, and is only accessible when the AIM is in single-instance
                compatibility mode."
    ::= { vmvcAimStatVCGroup 31 }

vmvcAimStatServerTotalDatastoreCapacity OBJECT-TYPE
    SYNTAX INTEGER
    ACCESS read-only
    STATUS mandatory
    DESCRIPTION
        "Total Capacity of all datastores in VC.
         NOTE:  This parameter is deprecated, and is only accessible when the AIM is in single-instance
                compatibility mode."
    ::= { vmvcAimStatVCGroup  32}

vmvcAimStatServerTotalDatastoreFreeSpace OBJECT-TYPE
    SYNTAX INTEGER
    ACCESS read-only
    STATUS mandatory
    DESCRIPTION
        "Total Free space of all datastores in MB.
         NOTE:  This parameter is deprecated, and is only accessible when the AIM is in single-instance
                compatibility mode."
    ::= { vmvcAimStatVCGroup  33}

vmvcAimStatServerTotalDatastoreFreeSpacePct OBJECT-TYPE
    SYNTAX INTEGER
    ACCESS read-only
    STATUS mandatory
    DESCRIPTION
        "Total Free space Percentage of all datastores.
         NOTE:  This parameter is deprecated, and is only accessible when the AIM is in single-instance
                compatibility mode."
    ::= { vmvcAimStatVCGroup  34}

vmvcAimStatServerTotalDatastoreFreeSpaceWarnThresh OBJECT-TYPE
    SYNTAX INTEGER
    ACCESS read-write
    STATUS mandatory
    DESCRIPTION
        "Warning threshold for datastore free space.
         NOTE:  This parameter is deprecated, and is only accessible when the AIM is in single-instance
                compatibility mode."
    DEFVAL { 40 }
    ::= { vmvcAimStatVCGroup  35}

vmvcAimStatServerTotalDatastoreFreeSpaceCritThresh OBJECT-TYPE
    SYNTAX INTEGER
    ACCESS read-write
    STATUS mandatory
    DESCRIPTION
        "Critical threshold for datastore free space.
         NOTE:  This parameter is deprecated, and is only accessible when the AIM is in single-instance
                compatibility mode."
    DEFVAL { 20 }
    ::= { vmvcAimStatVCGroup  36}

vmvcAimStatServerTotalDatastoreFreeSpaceState OBJECT-TYPE
    SYNTAX INTEGER {
        unknown(1),
        ok(2),
        warning(3),
        critical(4)
    }
    ACCESS read-only
    STATUS mandatory
    DESCRIPTION
        "Datastore Free Space State.Can be ok,warning or critical.
         NOTE:  This parameter is deprecated, and is only accessible when the AIM is in single-instance
                compatibility mode."
    ::= { vmvcAimStatVCGroup  37}

vmvcAimStatServerCPUMonitor OBJECT-TYPE
    SYNTAX INTEGER {
         do-not-monitor(1),
        monitor(2)
    }
    ACCESS read-write
    STATUS mandatory
    DESCRIPTION    
        "Flag indicating whether the CPU usage for node to be monitored(2) or not(1).
         NOTE:  This parameter is deprecated, and is only accessible when the AIM is in single-instance
                compatibility mode."
    DEFVAL { 2 }
    ::= { vmvcAimStatVCGroup  38}

vmvcAimStatServerCPULagSetting OBJECT-TYPE
    SYNTAX  INTEGER
    ACCESS  read-write
    STATUS  mandatory
    DESCRIPTION 
        "The number of consecutive times the threshold should be breached before the status change occurs.
         NOTE:  This parameter is deprecated, and is only accessible when the AIM is in single-instance
                compatibility mode."
    DEFVAL { 3 }
    ::= { vmvcAimStatVCGroup  39}

vmvcAimStatServerCPULagValue OBJECT-TYPE
    SYNTAX  INTEGER
    ACCESS  read-only
    STATUS  mandatory
    DESCRIPTION 
        "The current running count of the number of consecutive times the status is in the current status.
         NOTE:  This parameter is deprecated, and is only accessible when the AIM is in single-instance
                compatibility mode."
    ::= { vmvcAimStatVCGroup  40}

vmvcAimStatServerCPUAggregateStatus OBJECT-TYPE
    SYNTAX INTEGER {
        unknown(1),
        ok(2),
        warning(3),
        critical(4)
    }
    ACCESS  read-only
    STATUS  mandatory
    DESCRIPTION
        "The current aggregate CPU Status (ok, warning, critical).
         NOTE:  This parameter is deprecated, and is only accessible when the AIM is in single-instance
                compatibility mode."
    ::= { vmvcAimStatVCGroup  41}

vmvcAimStatServerMemoryMonitor OBJECT-TYPE
    SYNTAX INTEGER {
         do-not-monitor(1),
        monitor(2)
    }
    ACCESS read-write
    STATUS mandatory
    DESCRIPTION    
        "Flag indicating whether the Memory usage for host to be monitored(2) or not(1).
         NOTE:  This parameter is deprecated, and is only accessible when the AIM is in single-instance
                compatibility mode."
    DEFVAL { 2 }
    ::= { vmvcAimStatVCGroup  42}

vmvcAimStatServerIPAddress OBJECT-TYPE
    SYNTAX SnmpAdminString
    ACCESS read-only
    STATUS mandatory
    DESCRIPTION
        "The IP Address of the Virtual Center Server.
         NOTE:  This parameter is deprecated, and is only accessible when the AIM is in single-instance
                compatibility mode."
    ::= { vmvcAimStatVCGroup 43}
    
vmvcAimStatServerMAC OBJECT-TYPE
    SYNTAX SnmpAdminString
    ACCESS read-only
    STATUS mandatory
    DESCRIPTION
        "The MAC address of the network adapter for the Virtual Center Server.
         NOTE:  This parameter is deprecated, and is only accessible when the AIM is in single-instance
                compatibility mode."
    ::= { vmvcAimStatVCGroup  44}

vmvcAimStatVCCount OBJECT-TYPE
    SYNTAX INTEGER
    ACCESS read-only
    STATUS mandatory
    DESCRIPTION
        "Number of configured VC Servers in vmvcAimStatVCTable."
    ::= { vmvcAimStatVCGroup  45}

vmvcAimStatVCTable OBJECT-TYPE
    SYNTAX SEQUENCE OF VmvcAimStatVCRow
    ACCESS not-accessible
    STATUS mandatory
    DESCRIPTION
        "A table containing the Virtual Center Instance 
         status information."
    ::= { vmvcAimStatVCGroup  46}

vmvcAimStatVCEntry OBJECT-TYPE
    SYNTAX VmvcAimStatVCRow
    ACCESS not-accessible
    STATUS mandatory
    DESCRIPTION
        "The Virtual Center Instance Status Table entry."
    INDEX { vmvcAimStatVCUID }
    ::= { vmvcAimStatVCTable 1 }

VmvcAimStatVCRow ::=
    SEQUENCE {
        vmvcAimStatVCUID                            INTEGER,
        vmvcAimStatVCName                           SnmpAdminString,
        vmvcAimStatVCProduct                        SnmpAdminString,
        vmvcAimStatVCOSType                         SnmpAdminString,
        vmvcAimStatVCVer                            SnmpAdminString,
        vmvcAimStatVCAPIVer                         SnmpAdminString,
        vmvcAimStatVCBuild                          SnmpAdminString,
        vmvcAimStatVCProdLine                       SnmpAdminString,
        vmvcAimStatVCStatusAlert                    INTEGER,
        vmvcAimStatVCStatusMonitor                  INTEGER,
        vmvcAimStatVCState                          INTEGER,
        vmvcAimStatVCLocalCPUUsage                  INTEGER,
        vmvcAimStatVCLocalCPUUsageWarn              INTEGER,
        vmvcAimStatVCLocalCPUUsageCrit              INTEGER,
        vmvcAimStatVCLocalCPUUsageAlert             INTEGER,
        vmvcAimStatVCLocalCPUState                  INTEGER,
        vmvcAimStatVCLocalMemUsage                  INTEGER,
        vmvcAimStatVCLocalTotalPhysMem              INTEGER,
        vmvcAimStatVCLocalUsedPhysMem               INTEGER,
        vmvcAimStatVCLocalMemWarn                   INTEGER,
        vmvcAimStatVCLocalMemCrit                   INTEGER,
        vmvcAimStatVCLocalMemAlert                  INTEGER,
        vmvcAimStatVCLocalMemState                  INTEGER,
        vmvcAimStatVCTotalCPUUsage                  INTEGER,
        vmvcAimStatVCTotalCPUUsageWarn              INTEGER,
        vmvcAimStatVCTotalCPUUsageCrit              INTEGER,
        vmvcAimStatVCTotalCPUState                  INTEGER,
        vmvcAimStatVCTotalMemUsage                  INTEGER,
        vmvcAimStatVCTotalMemWarn                   INTEGER,
        vmvcAimStatVCTotalMemCrit                   INTEGER,
        vmvcAimStatVCTotalMemState                  INTEGER,
        vmvcAimStatVCTotalDatastoreCapacity         INTEGER,
        vmvcAimStatVCTotalDatastoreFreeSpace        INTEGER,
        vmvcAimStatVCTotalDatastoreFreeSpacePct     INTEGER,
        vmvcAimStatVCTotalDatastoreFreeSpaceWarn    INTEGER,
        vmvcAimStatVCTotalDatastoreFreeSpaceCrit    INTEGER,
        vmvcAimStatVCTotalDatastoreFreeSpaceState   INTEGER,
        vmvcAimStatVCLocalCPUMonitor                INTEGER,
        vmvcAimStatVCLocalCPULagSetting             INTEGER,
        vmvcAimStatVCLocalCPULagValue               INTEGER,
        vmvcAimStatVCLocalCPUAggregateState         INTEGER,
        vmvcAimStatVCLocalMemoryMonitor             INTEGER,
        vmvcAimStatVCIPAddress                      SnmpAdminString,
        vmvcAimStatVCMAC                            SnmpAdminString,
        vmvcAimStatVCUUID                           SnmpAdminString
    }

vmvcAimStatVCUID OBJECT-TYPE
        SYNTAX INTEGER (1..2147483647)
        ACCESS read-only
        STATUS mandatory
        DESCRIPTION
                "Integer UID of Virtual Center Instance."
        ::= { vmvcAimStatVCEntry  1 }

vmvcAimStatVCName OBJECT-TYPE
    SYNTAX SnmpAdminString
    ACCESS read-only
    STATUS mandatory
    DESCRIPTION
        "Name of the server this VC instance is running on."
    ::= { vmvcAimStatVCEntry  2 }

vmvcAimStatVCProduct OBJECT-TYPE
    SYNTAX SnmpAdminString
    ACCESS read-only
    STATUS mandatory
    DESCRIPTION
        "Name of this VC instance product."
    ::= { vmvcAimStatVCEntry  3 }

vmvcAimStatVCOSType OBJECT-TYPE
    SYNTAX SnmpAdminString
    ACCESS read-only
    STATUS mandatory
    DESCRIPTION
        "Type of the OS this VC instance is running on."
    ::= { vmvcAimStatVCEntry  4 }

vmvcAimStatVCVer OBJECT-TYPE
    SYNTAX SnmpAdminString
    ACCESS read-only
    STATUS mandatory
    DESCRIPTION
        "This VC instance version."
    ::= { vmvcAimStatVCEntry  5 }

vmvcAimStatVCAPIVer OBJECT-TYPE
    SYNTAX SnmpAdminString
    ACCESS read-only
    STATUS mandatory
    DESCRIPTION
        "Version of the VI SDK for this instance."
    ::= { vmvcAimStatVCEntry  6 }

vmvcAimStatVCBuild OBJECT-TYPE
    SYNTAX SnmpAdminString
    ACCESS read-only
    STATUS mandatory
    DESCRIPTION
        "Build of this VC server instance."
    ::= { vmvcAimStatVCEntry  7 }

vmvcAimStatVCProdLine OBJECT-TYPE
    SYNTAX SnmpAdminString
    ACCESS read-only
    STATUS mandatory
    DESCRIPTION
        "Product Identifier for this VC instance."
    ::= { vmvcAimStatVCEntry  8 }

vmvcAimStatVCStatusAlert OBJECT-TYPE
    SYNTAX INTEGER{
        not-running-warn(1),
        not-running-crit(2)
        }
    ACCESS read-write
    STATUS mandatory
    DESCRIPTION
        "Type of alert for this VC server status, based on the value of 
         vmvcAimConfigVCRowStatus."
    DEFVAL { 2 }
    ::= { vmvcAimStatVCEntry  9 }

vmvcAimStatVCStatusMonitor OBJECT-TYPE
    SYNTAX INTEGER{
        do-not-monitor(1),
        monitor(2)
        }
    ACCESS read-write
    STATUS mandatory
    DESCRIPTION
        "Monitor state of this VC Service Status."
    DEFVAL { 2 }
    ::= { vmvcAimStatVCEntry 10 }

vmvcAimStatVCState OBJECT-TYPE
    SYNTAX INTEGER {
        unknown(1),
        ok(2),
        warning(3),
        critical(4)
    }
    ACCESS read-only
    STATUS mandatory
    DESCRIPTION
        "State of this VirtualCenter service status, based on the values 
         of vmvcAimConfigVCRowStatus and vmvcAimConfigVCDataStatus."
    ::= { vmvcAimStatVCEntry 11 }

vmvcAimStatVCLocalCPUUsage OBJECT-TYPE
    SYNTAX INTEGER
    ACCESS read-only
    STATUS mandatory
    DESCRIPTION
        "CPU Usage of the local VirtualCenter Server.  Is always set to 
         zero(0) if the AIM is not installed on the VirtualCenter Server."
    ::= { vmvcAimStatVCEntry  12 }

vmvcAimStatVCLocalCPUUsageWarn OBJECT-TYPE
    SYNTAX INTEGER
    ACCESS read-write
    STATUS mandatory
    DESCRIPTION
        "Warning threshold for the CPU usage of the Local VC server."
    DEFVAL { 60 }
    ::= { vmvcAimStatVCEntry  13 }

vmvcAimStatVCLocalCPUUsageCrit OBJECT-TYPE
    SYNTAX INTEGER
    ACCESS read-write
    STATUS mandatory
    DESCRIPTION
        "Critical threshold for the CPU usage of the Local VC server."
    DEFVAL { 80 }
    ::= { vmvcAimStatVCEntry  14 }

vmvcAimStatVCLocalCPUUsageAlert OBJECT-TYPE
    SYNTAX INTEGER{
        warning-only(1),
        critical-only(2),
        both(3)
        }
    ACCESS read-write
    STATUS mandatory
    DESCRIPTION
        "Type of alert for the CPU usage of the Local VC server."
    DEFVAL { 3 }
    ::= { vmvcAimStatVCEntry  15 }

vmvcAimStatVCLocalCPUState OBJECT-TYPE
    SYNTAX INTEGER {
        unknown(1),
        ok(2),
        warning(3),
        critical(4)
    }
    ACCESS read-only
    STATUS mandatory
    DESCRIPTION
        "State for the CPU usage of the Local VC server."
    ::= { vmvcAimStatVCEntry  16 }

vmvcAimStatVCLocalMemUsage OBJECT-TYPE
    SYNTAX INTEGER
    ACCESS read-only
    STATUS mandatory
    DESCRIPTION
        "Memory Usage of the local VirtualCenter Server.  Is always set to 
         zero(0) if the AIM is not installed on the VirtualCenter Server."
    ::= { vmvcAimStatVCEntry  17 }

vmvcAimStatVCLocalTotalPhysMem OBJECT-TYPE
    SYNTAX INTEGER
    ACCESS read-only
    STATUS mandatory
    DESCRIPTION
        "The total physical memory (in MB) of the local VirtualCenter Server.
         Is always set to zero(0) if the AIM is not installed on the VirtualCenter Server."
    ::= { vmvcAimStatVCEntry  18 }

vmvcAimStatVCLocalUsedPhysMem OBJECT-TYPE
    SYNTAX INTEGER
    ACCESS read-only
    STATUS mandatory
    DESCRIPTION
        "The physical memory used (in MB) of the local VirtualCenter Server.
         Is always set to zero(0) if the AIM is not installed on the VirtualCenter Server."
    ::= { vmvcAimStatVCEntry  19 }

vmvcAimStatVCLocalMemWarn OBJECT-TYPE
    SYNTAX INTEGER
    ACCESS read-write
    STATUS mandatory
    DESCRIPTION
        "Warning threshold for the memory usage of the Local VC server."
    DEFVAL { 60 }
    ::= { vmvcAimStatVCEntry  20 }

vmvcAimStatVCLocalMemCrit OBJECT-TYPE
    SYNTAX INTEGER
    ACCESS read-write
    STATUS mandatory
    DESCRIPTION
        "Critical threshold for the memory usage of the Local VC server."
    DEFVAL { 80 }
    ::= { vmvcAimStatVCEntry  21 }

vmvcAimStatVCLocalMemAlert OBJECT-TYPE
    SYNTAX INTEGER{
        warning-only(1),
        critical-only(2),
        both(3)
        }
    ACCESS read-write
    STATUS mandatory
    DESCRIPTION
        "Type of alert for the memory usage of the Local VC server."
    DEFVAL { 3 }
    ::= { vmvcAimStatVCEntry  22 }

vmvcAimStatVCLocalMemState OBJECT-TYPE
    SYNTAX INTEGER {
        unknown(1),
        ok(2),
        warning(3),
        critical(4)
    }
    ACCESS read-only
    STATUS mandatory
    DESCRIPTION
        "State for the memory usage of the Local VC server."
    ::= { vmvcAimStatVCEntry  23 }

vmvcAimStatVCTotalCPUUsage OBJECT-TYPE
    SYNTAX INTEGER
    ACCESS read-only
    STATUS mandatory
    DESCRIPTION
        "Aggregation of CPU Usage of all Hosts running under the VC."
    ::= { vmvcAimStatVCEntry  24 }

vmvcAimStatVCTotalCPUUsageWarn OBJECT-TYPE
    SYNTAX INTEGER
    ACCESS read-write
    STATUS mandatory
    DESCRIPTION
        "Warning threshold  for Total CPU usage."
    DEFVAL { 60 }
    ::= { vmvcAimStatVCEntry  25 }

vmvcAimStatVCTotalCPUUsageCrit OBJECT-TYPE
    SYNTAX INTEGER
    ACCESS read-write
    STATUS mandatory
    DESCRIPTION
        "Critical threshold  for Total CPU usage."
    DEFVAL { 80 }
    ::= { vmvcAimStatVCEntry  26 }

vmvcAimStatVCTotalCPUState OBJECT-TYPE
    SYNTAX INTEGER {
        unknown(1),
        ok(2),
        warning(3),
        critical(4)
    }
    ACCESS read-only
    STATUS mandatory
    DESCRIPTION
        "Total CPU State of VC."
    ::= { vmvcAimStatVCEntry  27 }

vmvcAimStatVCTotalMemUsage OBJECT-TYPE
    SYNTAX INTEGER
    ACCESS read-only
    STATUS mandatory
    DESCRIPTION 
        "The percentage of Total Physical Memory Usage of all hosts running under the VC."
    ::= { vmvcAimStatVCEntry 28 }

vmvcAimStatVCTotalMemWarn OBJECT-TYPE
    SYNTAX INTEGER
    ACCESS read-write
    STATUS mandatory
    DESCRIPTION 
        "Sets the Memory warning threshold value.  Must be lower than the Memory critical threshold value."
    DEFVAL { 60 }
    ::= { vmvcAimStatVCEntry 29 }

vmvcAimStatVCTotalMemCrit OBJECT-TYPE
    SYNTAX INTEGER
    ACCESS read-write
    STATUS mandatory
    DESCRIPTION 
        "Sets the Memory critical threshold value.  Must be higher than the Memory warning threshold value."
    DEFVAL { 80 }
    ::= { vmvcAimStatVCEntry 30 }

vmvcAimStatVCTotalMemState OBJECT-TYPE
    SYNTAX INTEGER {
        unknown(1),
        ok(2),
        warning(3),
        critical(4)
    }
    ACCESS read-only
    STATUS mandatory
    DESCRIPTION 
        "The State of the Total Memory Usage of the Server(ok, warning, critical)."
    ::= { vmvcAimStatVCEntry 31 }

vmvcAimStatVCTotalDatastoreCapacity OBJECT-TYPE
    SYNTAX INTEGER
    ACCESS read-only
    STATUS mandatory
    DESCRIPTION
        "Total Capacity of all datastores for this VC."
    ::= { vmvcAimStatVCEntry 32 }

vmvcAimStatVCTotalDatastoreFreeSpace OBJECT-TYPE
    SYNTAX INTEGER
    ACCESS read-only
    STATUS mandatory
    DESCRIPTION
        "Total Free space of all datastores in MB for this VC."
    ::= { vmvcAimStatVCEntry 33 }

vmvcAimStatVCTotalDatastoreFreeSpacePct OBJECT-TYPE
    SYNTAX INTEGER
    ACCESS read-only
    STATUS mandatory
    DESCRIPTION
        "Total Free space Percentage of all datastores for this VC."
    ::= { vmvcAimStatVCEntry 34 }

vmvcAimStatVCTotalDatastoreFreeSpaceWarn OBJECT-TYPE
    SYNTAX INTEGER
    ACCESS read-write
    STATUS mandatory
    DESCRIPTION
        "Warning threshold for datastore free space for this VC."
    DEFVAL { 40 }
    ::= { vmvcAimStatVCEntry 35 }

vmvcAimStatVCTotalDatastoreFreeSpaceCrit OBJECT-TYPE
    SYNTAX INTEGER
    ACCESS read-write
    STATUS mandatory
    DESCRIPTION
        "Critical threshold for datastore free space for this VC."
    DEFVAL { 20 }
    ::= { vmvcAimStatVCEntry 36 }

vmvcAimStatVCTotalDatastoreFreeSpaceState OBJECT-TYPE
    SYNTAX INTEGER {
        unknown(1),
        ok(2),
        warning(3),
        critical(4)
    }
    ACCESS read-only
    STATUS mandatory
    DESCRIPTION
        "Datastore Free Space State for this VC.  Can be ok,warning or critical."
    ::= { vmvcAimStatVCEntry 37 }

vmvcAimStatVCLocalCPUMonitor OBJECT-TYPE
    SYNTAX INTEGER{
        do-not-monitor(1),
        monitor(2)
        }
    ACCESS read-write
    STATUS mandatory
    DESCRIPTION
        "Type of monitoring for the CPU usage of the Local VC server."
    DEFVAL { 2 }
    ::= { vmvcAimStatVCEntry  38 }

vmvcAimStatVCLocalCPULagSetting OBJECT-TYPE
    SYNTAX INTEGER
    ACCESS read-write
    STATUS mandatory
    DESCRIPTION
        "The number of times the threshold should be breached before
         the status change occurs for the CPU usage of the Local VC server."
    DEFVAL { 3 }
    ::= { vmvcAimStatVCEntry  39 }

vmvcAimStatVCLocalCPULagValue OBJECT-TYPE
    SYNTAX INTEGER
    ACCESS read-only
    STATUS mandatory
    DESCRIPTION
        "The current running count of the number of consecutive times the 
         state is in the current state for the CPU usage of the Local VC server."
    ::= { vmvcAimStatVCEntry  40 }

vmvcAimStatVCLocalCPUAggregateState OBJECT-TYPE
    SYNTAX INTEGER {
        unknown(1),
        ok(2),
        warning(3),
        critical(4)
    }
    ACCESS read-only
    STATUS mandatory
    DESCRIPTION
        "The current aggregate state for the CPU usage of the Local VC server
         (using lag)."
    ::= { vmvcAimStatVCEntry  41 }

vmvcAimStatVCLocalMemoryMonitor OBJECT-TYPE
    SYNTAX INTEGER{
        do-not-monitor(1),
        monitor(2)
        }
    ACCESS read-write
    STATUS mandatory
    DESCRIPTION
        "Type of monitoring for the memory usage of the Local VC server."
    DEFVAL { 2 }
    ::= { vmvcAimStatVCEntry  42 }

vmvcAimStatVCIPAddress OBJECT-TYPE
    SYNTAX SnmpAdminString
    ACCESS read-only
    STATUS mandatory
    DESCRIPTION
        "The IP Address of this Virtual Center Server."
    ::= { vmvcAimStatVCEntry 43 }
    
vmvcAimStatVCMAC OBJECT-TYPE
    SYNTAX SnmpAdminString
    ACCESS read-only
    STATUS mandatory
    DESCRIPTION
        "The MAC address of the network adapter for this Virtual Center Server."
    ::= { vmvcAimStatVCEntry 44 }

vmvcAimStatVCUUID OBJECT-TYPE
    SYNTAX SnmpAdminString
    ACCESS read-only
    STATUS mandatory
    DESCRIPTION
        "The vCenter specified UUID of this Virtual Center Server."
    ::= { vmvcAimStatVCEntry 45 }

-- *****************************************************************************
-- Status Customization Specification Group
-- *****************************************************************************

vmvcAimStatCustSpecCount OBJECT-TYPE
    SYNTAX INTEGER
    ACCESS read-only
    STATUS mandatory
    DESCRIPTION
        "Number of Customization Specification in vmvcAimStatCustSpecTable."
    ::= { vmvcAimStatCustSpecGroup 1}

vmvcAimStatCustSpecTable OBJECT-TYPE
    SYNTAX SEQUENCE OF VmvcAimStatCustSpecRow
    ACCESS not-accessible
    STATUS mandatory
    DESCRIPTION
        "Customization Specification table."
    ::= { vmvcAimStatCustSpecGroup 2 }

vmvcAimStatCustSpecEntry OBJECT-TYPE
    SYNTAX VmvcAimStatCustSpecRow
    ACCESS not-accessible
    STATUS mandatory
    DESCRIPTION
        "The table entry."
    INDEX { vmvcAimStatCustomizationSpecUID }
    ::= { vmvcAimStatCustSpecTable 1 }

VmvcAimStatCustSpecRow ::=
    SEQUENCE {
        vmvcAimStatCustomizationSpecUID                 INTEGER,
        vmvcAimStatCustomizationSpecName                SnmpAdminString,
        vmvcAimStatCustomizationSpecType                SnmpAdminString,
        vmvcAimStatCustomizationSpecLastUpdated         SnmpAdminString,
        vmvcAimStatCustomizationSpecChgVer              SnmpAdminString,
        vmvcAimStatCustomizationSpecHostName            SnmpAdminString,
        vmvcAimStatCustomizationSpecPrimaryDNSServer    SnmpAdminString,
        vmvcAimStatCustomizationSpecSecondaryDNSServer  SnmpAdminString,
        vmvcAimStatCustomizationSpecTertiaryDNSServer   SnmpAdminString,
        vmvcAimStatCustomizationSpecDomainName          SnmpAdminString,
        vmvcAimStatCustomizationSpecDNSSearchSuffixes   SnmpAdminString,
        vmvcAimStatCustomizationSpecVCUID               INTEGER,
        vmvcAimStatCustomizationSpecVCName              SnmpAdminString,
        vmvcAimStatCustomizationSpecLastUpdateTimeSec   INTEGER,
        vmvcAimStatCustomizationSpecVCUUID              SnmpAdminString
    }
    
vmvcAimStatCustomizationSpecUID OBJECT-TYPE
    SYNTAX INTEGER (1..2147483647)
    ACCESS read-only
    STATUS mandatory
    DESCRIPTION
        "Integer UID of the customization specification."
    ::= { vmvcAimStatCustSpecEntry  1}

vmvcAimStatCustomizationSpecName OBJECT-TYPE
    SYNTAX SnmpAdminString
    ACCESS read-only
    STATUS mandatory
    DESCRIPTION
        "Name of the customization specification."
    ::= { vmvcAimStatCustSpecEntry  2}

vmvcAimStatCustomizationSpecType OBJECT-TYPE
    SYNTAX SnmpAdminString
    ACCESS read-only
    STATUS mandatory
    DESCRIPTION
        "Guest operating system for this specification (Linux or Windows)."
    ::= { vmvcAimStatCustSpecEntry  3}

vmvcAimStatCustomizationSpecLastUpdated OBJECT-TYPE
    SYNTAX SnmpAdminString
    ACCESS read-only
    STATUS mandatory
    DESCRIPTION
        "Time when the specification was last modified.
         DEPRECATED!  This attribute no longer returns any data, due to
         Internationalization standards involving Data/Time Formatting.
         Refer to vmvcAimStatCustomizationSpecLastUpdateTimeSec for new value."
    ::= { vmvcAimStatCustSpecEntry  4}

vmvcAimStatCustomizationSpecChgVer OBJECT-TYPE
    SYNTAX SnmpAdminString
    ACCESS read-only
    STATUS mandatory
    DESCRIPTION
        "The changeVersion is a unique identifier for a given version of the configuration."
    ::= { vmvcAimStatCustSpecEntry  5}

vmvcAimStatCustomizationSpecHostName OBJECT-TYPE
    SYNTAX SnmpAdminString
    ACCESS read-only
    STATUS mandatory
    DESCRIPTION
        "Fixed host name defined in the custom specification."
    ::= { vmvcAimStatCustSpecEntry  6}

vmvcAimStatCustomizationSpecPrimaryDNSServer OBJECT-TYPE
    SYNTAX SnmpAdminString
    ACCESS read-only
    STATUS mandatory
    DESCRIPTION
        "Primary DNS Server defined in the custom specification. This only applies to Linux specification."
    ::= { vmvcAimStatCustSpecEntry  7}

vmvcAimStatCustomizationSpecSecondaryDNSServer OBJECT-TYPE
    SYNTAX SnmpAdminString
    ACCESS read-only
    STATUS mandatory
    DESCRIPTION
        "Secondary DNS Server defined in the custom specification. This only applies to Linux specification."
    ::= { vmvcAimStatCustSpecEntry  8}

vmvcAimStatCustomizationSpecTertiaryDNSServer OBJECT-TYPE
    SYNTAX SnmpAdminString
    ACCESS read-only
    STATUS mandatory
    DESCRIPTION
        "Tertiary DNS Server defined in the custom specification. This only applies to Linux specification."
    ::= { vmvcAimStatCustSpecEntry  9}
        
vmvcAimStatCustomizationSpecDomainName OBJECT-TYPE
    SYNTAX SnmpAdminString
    ACCESS read-only
    STATUS mandatory
    DESCRIPTION
        "Domain Name defined in the custom specification. This only applies to Linux specification."
    ::= { vmvcAimStatCustSpecEntry  10}
        
vmvcAimStatCustomizationSpecDNSSearchSuffixes OBJECT-TYPE
    SYNTAX SnmpAdminString
    ACCESS read-only
    STATUS mandatory
    DESCRIPTION
        "DNS Search Suffixes defined in the custom specification. This only applies to Linux specification."
    ::= { vmvcAimStatCustSpecEntry  11}

vmvcAimStatCustomizationSpecVCUID OBJECT-TYPE
    SYNTAX INTEGER
    ACCESS read-only
    STATUS mandatory
    DESCRIPTION
        "VC Instance SNMP UID where this Customization Spec resides."
    ::= { vmvcAimStatCustSpecEntry  12}

vmvcAimStatCustomizationSpecVCName OBJECT-TYPE
    SYNTAX SnmpAdminString
    ACCESS read-only
    STATUS mandatory
    DESCRIPTION
        "VC Instance where this Customization Spec resides."
    ::= { vmvcAimStatCustSpecEntry  13}

vmvcAimStatCustomizationSpecLastUpdateTimeSec OBJECT-TYPE
    SYNTAX INTEGER
    ACCESS read-only
    STATUS mandatory
    DESCRIPTION
        "Time (in seconds from the Epoch) when the specification was last modified."
    ::= { vmvcAimStatCustSpecEntry  14}

vmvcAimStatCustomizationSpecVCUUID OBJECT-TYPE
    SYNTAX SnmpAdminString
    ACCESS read-only
    STATUS mandatory
    DESCRIPTION
        "The vCenter-specified UUID where this Customization Spec resides."
    ::= { vmvcAimStatCustSpecEntry  15}


-- *****************************************************************************
-- Status DC Folder Group
-- *****************************************************************************
vmvcAimStatDCFolderCount OBJECT-TYPE
    SYNTAX INTEGER
    ACCESS read-only
    STATUS mandatory
    DESCRIPTION
        "Number of Datacenter folders in vmvcAimStatDCFolderTable."
    ::= { vmvcAimStatDCFolderGroup 1}

vmvcAimStatDCFolderTable OBJECT-TYPE
    SYNTAX SEQUENCE OF VmvcAimStatDCFolderRow
    ACCESS not-accessible
    STATUS mandatory
    DESCRIPTION
        "Datacenter folder table."
    ::= { vmvcAimStatDCFolderGroup 2 }

vmvcAimStatDCFolderEntry OBJECT-TYPE
    SYNTAX VmvcAimStatDCFolderRow
    ACCESS not-accessible
    STATUS mandatory
    DESCRIPTION
        "The table entry."
    INDEX { vmvcAimStatDatacenterFolderUID }
    ::= { vmvcAimStatDCFolderTable 1 }

VmvcAimStatDCFolderRow ::=
    SEQUENCE {
        vmvcAimStatDatacenterFolderUID          INTEGER,
        vmvcAimStatDatacenterFolderIndex        SnmpAdminString,
        vmvcAimStatDatacenterFolderName         SnmpAdminString,
        vmvcAimStatDatacenterFolderParentId     SnmpAdminString,
        vmvcAimStatDatacenterFolderParentPath   SnmpAdminString,
        vmvcAimStatDatacenterFolderVCUID        INTEGER,
        vmvcAimStatDatacenterFolderVCName       SnmpAdminString,
        vmvcAimStatDatacenterFolderVCUUID       SnmpAdminString
    }

vmvcAimStatDatacenterFolderUID OBJECT-TYPE
    SYNTAX INTEGER  (1..2147483647)
    ACCESS read-only
    STATUS mandatory
    DESCRIPTION
        "Integer UID of Datacenter Folder."
    ::= { vmvcAimStatDCFolderEntry  1}

vmvcAimStatDatacenterFolderIndex OBJECT-TYPE
    SYNTAX SnmpAdminString
    ACCESS read-only
    STATUS mandatory
    DESCRIPTION
        "Identifier of Datacenter Folder."
    ::= { vmvcAimStatDCFolderEntry  2}

vmvcAimStatDatacenterFolderName OBJECT-TYPE
    SYNTAX SnmpAdminString
    ACCESS read-only
    STATUS mandatory
    DESCRIPTION
        "Name of the Datacenter Folder."
    ::= { vmvcAimStatDCFolderEntry  3}


vmvcAimStatDatacenterFolderParentId OBJECT-TYPE
    SYNTAX SnmpAdminString
    ACCESS read-only
    STATUS mandatory
    DESCRIPTION
        "Immediate parent identifier."
    ::= { vmvcAimStatDCFolderEntry  4}

vmvcAimStatDatacenterFolderParentPath OBJECT-TYPE
    SYNTAX SnmpAdminString
    ACCESS read-only
    STATUS mandatory
    DESCRIPTION
        "Full path to the Datacenter folder."
    ::= { vmvcAimStatDCFolderEntry  5}

vmvcAimStatDatacenterFolderVCUID OBJECT-TYPE
    SYNTAX INTEGER
    ACCESS read-only
    STATUS mandatory
    DESCRIPTION
         "VC Instance SNMP UID where this Datacenter Folder resides."
    ::= { vmvcAimStatDCFolderEntry  6}

vmvcAimStatDatacenterFolderVCName OBJECT-TYPE
    SYNTAX SnmpAdminString
    ACCESS read-only
    STATUS mandatory
    DESCRIPTION
         "VC Instance where this Datacenter Folder resides."
    ::= { vmvcAimStatDCFolderEntry  7}

vmvcAimStatDatacenterFolderVCUUID OBJECT-TYPE
    SYNTAX SnmpAdminString
    ACCESS read-only
    STATUS mandatory
    DESCRIPTION
         "The vCenter-specified UUID where this Datacenter Folder resides."
    ::= { vmvcAimStatDCFolderEntry  8}


-- *****************************************************************************
-- Status Network Folder Group
-- *****************************************************************************
vmvcAimStatNetFolderCount OBJECT-TYPE
    SYNTAX INTEGER
    ACCESS read-only
    STATUS mandatory
    DESCRIPTION
        "Number of Network folders in vmvcAimStatNetFolderTable."
    ::= { vmvcAimStatDCFolderGroup 3}

vmvcAimStatNetFolderTable OBJECT-TYPE
    SYNTAX SEQUENCE OF VmvcAimStatNetFolderRow
    ACCESS not-accessible
    STATUS mandatory
    DESCRIPTION
        "Network folder table."
    ::= { vmvcAimStatDCFolderGroup 4 }

vmvcAimStatNetFolderEntry OBJECT-TYPE
    SYNTAX VmvcAimStatNetFolderRow
    ACCESS not-accessible
    STATUS mandatory
    DESCRIPTION
        "The table entry."
    INDEX { vmvcAimStatNetworkFolderUID }
    ::= { vmvcAimStatNetFolderTable 1 }

VmvcAimStatNetFolderRow ::=
    SEQUENCE {
        vmvcAimStatNetworkFolderUID         INTEGER,
        vmvcAimStatNetworkFolderIndex       SnmpAdminString,
        vmvcAimStatNetworkFolderName        SnmpAdminString,
        vmvcAimStatNetworkFolderVCUID       INTEGER,
        vmvcAimStatNetworkFolderVCName      SnmpAdminString,
        vmvcAimStatNetworkFolderParentId    SnmpAdminString,
        vmvcAimStatNetworkFolderParentPath  SnmpAdminString,
        vmvcAimStatNetworkFolderVCUUID      SnmpAdminString
    }

vmvcAimStatNetworkFolderUID OBJECT-TYPE
    SYNTAX INTEGER  (1..2147483647)
    ACCESS read-only
    STATUS mandatory
    DESCRIPTION
        "Integer UID of Network Folder."
    ::= { vmvcAimStatNetFolderEntry  1}

vmvcAimStatNetworkFolderIndex OBJECT-TYPE
    SYNTAX SnmpAdminString
    ACCESS read-only
    STATUS mandatory
    DESCRIPTION
        "Identifier of Network Folder."
    ::= { vmvcAimStatNetFolderEntry  2}

vmvcAimStatNetworkFolderName OBJECT-TYPE
    SYNTAX SnmpAdminString
    ACCESS read-only
    STATUS mandatory
    DESCRIPTION
        "Name of the Network Folder."
    ::= { vmvcAimStatNetFolderEntry  3}


vmvcAimStatNetworkFolderVCUID OBJECT-TYPE
    SYNTAX INTEGER
    ACCESS read-only
    STATUS mandatory
    DESCRIPTION
         "VC Instance SNMP UID where this Network Folder resides."
    ::= { vmvcAimStatNetFolderEntry  4}

vmvcAimStatNetworkFolderVCName OBJECT-TYPE
    SYNTAX SnmpAdminString
    ACCESS read-only
    STATUS mandatory
    DESCRIPTION
         "VC Instance where this Network Folder resides."
    ::= { vmvcAimStatNetFolderEntry  5}

vmvcAimStatNetworkFolderParentId OBJECT-TYPE
    SYNTAX SnmpAdminString
    ACCESS read-only
    STATUS mandatory
    DESCRIPTION
        "Immediate parent identifier."
    ::= { vmvcAimStatNetFolderEntry  6}

vmvcAimStatNetworkFolderParentPath OBJECT-TYPE
    SYNTAX SnmpAdminString
    ACCESS read-only
    STATUS mandatory
    DESCRIPTION
        "Full path to the Network folder."
    ::= { vmvcAimStatNetFolderEntry  7}

vmvcAimStatNetworkFolderVCUUID OBJECT-TYPE
    SYNTAX SnmpAdminString
    ACCESS read-only
    STATUS mandatory
    DESCRIPTION
         "The vCenter-specified UUID where this Network Folder resides."
    ::= { vmvcAimStatNetFolderEntry  8}


-- *****************************************************************************
-- Status DC Group
-- *****************************************************************************
vmvcAimStatDCCount OBJECT-TYPE
    SYNTAX INTEGER
    ACCESS read-only
    STATUS mandatory
    DESCRIPTION
        "Number of Datacenters in vmvcAimStatDCTable."
    ::= { vmvcAimStatDCGroup 1}

vmvcAimStatDCTable OBJECT-TYPE
    SYNTAX SEQUENCE OF VmvcAimStatDCRow
    ACCESS not-accessible
    STATUS mandatory
    DESCRIPTION
        "Datacenter folder table."
    ::= { vmvcAimStatDCGroup 2 }

vmvcAimStatDCEntry OBJECT-TYPE
    SYNTAX VmvcAimStatDCRow
    ACCESS not-accessible
    STATUS mandatory
    DESCRIPTION
        "The table entry."
    INDEX { vmvcAimStatDatacenterUID }
    ::= { vmvcAimStatDCTable 1 }

VmvcAimStatDCRow ::=
    SEQUENCE {
        vmvcAimStatDatacenterUID                        INTEGER,
        vmvcAimStatDatacenterIndex                      SnmpAdminString,
        vmvcAimStatDatacenterName                       SnmpAdminString,
        vmvcAimStatDatacenterDCFolderId                 SnmpAdminString,
        vmvcAimStatDatacenterDCFolderPath               SnmpAdminString,
        vmvcAimStatDatacenterTotalCPUUsage              INTEGER,
        vmvcAimStatDatacenterTotalCPUUsageWarnThresh    INTEGER,
        vmvcAimStatDatacenterTotalCPUUsageCritThresh    INTEGER,
        vmvcAimStatDatacenterTotalCPUState              INTEGER,
        vmvcAimStatDatacenterTotalMemUsage              INTEGER,
        vmvcAimStatDatacenterTotalMemWarnThres          INTEGER,
        vmvcAimStatDatacenterTotalMemCritThres          INTEGER,
        vmvcAimStatDatacenterTotalMemState              INTEGER,
        vmvcAimStatDatacenterOverallState               INTEGER,
        vmvcAimStatDatacenterVCUID                      INTEGER,
        vmvcAimStatDatacenterVCName                     SnmpAdminString,
        vmvcAimStatDatacenterVCUUID                     SnmpAdminString
    }

vmvcAimStatDatacenterUID OBJECT-TYPE
    SYNTAX INTEGER (1..2147483647)
    ACCESS read-only
    STATUS mandatory
    DESCRIPTION
        "Integer UID for datacenter."
    ::= { vmvcAimStatDCEntry  1}

vmvcAimStatDatacenterIndex OBJECT-TYPE
    SYNTAX SnmpAdminString
    ACCESS read-only
    STATUS mandatory
    DESCRIPTION
        "Identifier for datacenter."
    ::= { vmvcAimStatDCEntry  2}

vmvcAimStatDatacenterName OBJECT-TYPE
    SYNTAX SnmpAdminString
    ACCESS read-only
    STATUS mandatory
    DESCRIPTION
        "Name of the Datacenter."
    ::= { vmvcAimStatDCEntry  3}

vmvcAimStatDatacenterDCFolderId OBJECT-TYPE
    SYNTAX SnmpAdminString
    ACCESS read-only
    STATUS mandatory
    DESCRIPTION
        "Immediate parent identifier."
    ::= { vmvcAimStatDCEntry  4}

vmvcAimStatDatacenterDCFolderPath OBJECT-TYPE
    SYNTAX SnmpAdminString
    ACCESS read-only
    STATUS mandatory
    DESCRIPTION
        "Full path to the Datacenter."
    ::= { vmvcAimStatDCEntry  5}

vmvcAimStatDatacenterTotalCPUUsage OBJECT-TYPE
    SYNTAX INTEGER
    ACCESS read-only
    STATUS mandatory
    DESCRIPTION
        "Aggregation of CPU Usage of all Hosts running under the DC."
    ::= { vmvcAimStatDCEntry  6}

vmvcAimStatDatacenterTotalCPUUsageWarnThresh OBJECT-TYPE
    SYNTAX INTEGER
    ACCESS read-write
    STATUS mandatory
    DESCRIPTION
        "Warning threshold  for Total CPU usage."
    DEFVAL { 60 }
    ::= { vmvcAimStatDCEntry  7}

vmvcAimStatDatacenterTotalCPUUsageCritThresh OBJECT-TYPE
    SYNTAX INTEGER
    ACCESS read-write
    STATUS mandatory
    DESCRIPTION
        "Critical threshold  for Total CPU usage."
    DEFVAL { 80 }
    ::= { vmvcAimStatDCEntry  8}

vmvcAimStatDatacenterTotalCPUState OBJECT-TYPE
    SYNTAX INTEGER {
        unknown(1),
        ok(2),
        warning(3),
        critical(4)
    }
    ACCESS read-only
    STATUS mandatory
    DESCRIPTION
        "Total CPU State of DC."
    ::= { vmvcAimStatDCEntry  9}

vmvcAimStatDatacenterTotalMemUsage OBJECT-TYPE
    SYNTAX INTEGER
    ACCESS read-only
    STATUS mandatory
    DESCRIPTION 
        "The percentage of Total Physical Memory Usage of all hosts running under the DC, in megabytes."
    ::= { vmvcAimStatDCEntry 10}

vmvcAimStatDatacenterTotalMemWarnThres OBJECT-TYPE
    SYNTAX INTEGER
    ACCESS read-write
    STATUS mandatory
    DESCRIPTION 
        "Sets the Memory warning threshold value.  Must be lower than the Memory critical threshold value."
    DEFVAL { 60 }
    ::= { vmvcAimStatDCEntry 11}

vmvcAimStatDatacenterTotalMemCritThres OBJECT-TYPE
    SYNTAX INTEGER
    ACCESS read-write
    STATUS mandatory
    DESCRIPTION 
        "Sets the Memory critical threshold value.  Must be higher than the Memory warning threshold value."
    DEFVAL { 80 }
    ::= { vmvcAimStatDCEntry 12}

vmvcAimStatDatacenterTotalMemState OBJECT-TYPE
    SYNTAX INTEGER {
        unknown(1),
        ok(2),
        warning(3),
        critical(4)
    }
    ACCESS read-only
    STATUS mandatory
    DESCRIPTION 
        "The State of the Total Memory Usage of the Server(ok, warning, critical)."
    ::= { vmvcAimStatDCEntry 13}

vmvcAimStatDatacenterOverallState OBJECT-TYPE
    SYNTAX INTEGER {
        unknown(1),
        ok(2),
        warning(3),
        critical(4)
    }
    ACCESS read-only
    STATUS mandatory
    DESCRIPTION 
        "The overall state of the datacenter(ok, warning, critical)."
    ::= { vmvcAimStatDCEntry 14}

vmvcAimStatDatacenterVCUID OBJECT-TYPE
    SYNTAX INTEGER
    ACCESS read-only
    STATUS mandatory
    DESCRIPTION
        "VC Instance SNMP UID where this Datacenter resides."
    ::= { vmvcAimStatDCEntry 15}

vmvcAimStatDatacenterVCName OBJECT-TYPE
    SYNTAX SnmpAdminString
    ACCESS read-only
    STATUS mandatory
    DESCRIPTION
        "VC Instance where this Datacenter resides."
    ::= { vmvcAimStatDCEntry 16}

vmvcAimStatDatacenterVCUUID OBJECT-TYPE
    SYNTAX SnmpAdminString
    ACCESS read-only
    STATUS mandatory
    DESCRIPTION
        "The vCenter-specified UUID where this Datacenter resides."
    ::= { vmvcAimStatDCEntry 17}


-- *****************************************************************************
-- Status Computer Resource Folder Group
-- *****************************************************************************
vmvcAimStatComputeResourceFolderCount OBJECT-TYPE
    SYNTAX INTEGER
    ACCESS read-only
    STATUS mandatory
    DESCRIPTION
        "Number of ComputeResource Folders in vmvcAimStatComputeResourceFolderTable."
    ::= { vmvcAimStatComputeResFolderGroup 1}

vmvcAimStatComputeResourceFolderTable OBJECT-TYPE
    SYNTAX SEQUENCE OF VmvcAimStatComputeResourceFolderRow
    ACCESS not-accessible
    STATUS mandatory
    DESCRIPTION
        "ComputeResource Folders table."
    ::= { vmvcAimStatComputeResFolderGroup 2 }

vmvcAimStatComputeResourceFolderEntry OBJECT-TYPE
    SYNTAX VmvcAimStatComputeResourceFolderRow
    ACCESS not-accessible
    STATUS mandatory
    DESCRIPTION
        "The table entry."
    INDEX { vmvcAimStatComputeResourceFolderUID }
    ::= { vmvcAimStatComputeResourceFolderTable 1 }

VmvcAimStatComputeResourceFolderRow ::=
    SEQUENCE {
        vmvcAimStatComputeResourceFolderUID         INTEGER,
        vmvcAimStatComputeResourceFolderIndex       SnmpAdminString,
        vmvcAimStatComputeResourceFolderName        SnmpAdminString,
        vmvcAimStatComputeResourceFolderId          SnmpAdminString,
        vmvcAimStatComputeResourceFolderPath        SnmpAdminString,
        vmvcAimStatComputeResourceEffectiveCPU      INTEGER,
        vmvcAimStatComputeResourceEffectiveMemory   INTEGER,
        vmvcAimStatComputeResourceTotalCPUUsage     INTEGER,
        vmvcAimStatComputeResourceTotalMemoryUsage  INTEGER,
        vmvcAimStatComputeResourceOverallState      INTEGER,
        vmvcAimStatComputeResourceVCUID             INTEGER,
        vmvcAimStatComputeResourceVCName            SnmpAdminString,
        vmvcAimStatComputeResourceVCUUID            SnmpAdminString
    }

vmvcAimStatComputeResourceFolderUID OBJECT-TYPE
    SYNTAX INTEGER (1..2147483647)
    ACCESS read-only
    STATUS mandatory
    DESCRIPTION
        "UID of ComputeResource folder."
    ::= { vmvcAimStatComputeResourceFolderEntry  1}

vmvcAimStatComputeResourceFolderIndex OBJECT-TYPE
    SYNTAX SnmpAdminString
    ACCESS read-only
    STATUS mandatory
    DESCRIPTION
        "MOID of ComputeResource folder."
    ::= { vmvcAimStatComputeResourceFolderEntry  2}

vmvcAimStatComputeResourceFolderName OBJECT-TYPE
    SYNTAX SnmpAdminString
    ACCESS read-only
    STATUS mandatory
    DESCRIPTION
        "Name of the ComputeResource folder."
    ::= { vmvcAimStatComputeResourceFolderEntry  3}

vmvcAimStatComputeResourceFolderId OBJECT-TYPE
    SYNTAX SnmpAdminString
    ACCESS read-only
    STATUS mandatory
    DESCRIPTION
        "Immediate parent identifier."
    ::= { vmvcAimStatComputeResourceFolderEntry  4}

vmvcAimStatComputeResourceFolderPath OBJECT-TYPE
    SYNTAX SnmpAdminString
    ACCESS read-only
    STATUS mandatory
    DESCRIPTION
        "Full path to the ComputeResource folder."
    ::= { vmvcAimStatComputeResourceFolderEntry  5}

vmvcAimStatComputeResourceEffectiveCPU OBJECT-TYPE
    SYNTAX INTEGER
    ACCESS read-only
    STATUS mandatory
    DESCRIPTION
        "Effective CPU usage of ComputeResource folder"
    ::= { vmvcAimStatComputeResourceFolderEntry 6}
    
vmvcAimStatComputeResourceEffectiveMemory OBJECT-TYPE
    SYNTAX INTEGER
    ACCESS read-only
    STATUS mandatory
    DESCRIPTION
        "Effective Memory (in MB) of ComputeResource folder.  This is
         the aggregated amount from all hosts within this ComputeResource
         folder."
    ::= { vmvcAimStatComputeResourceFolderEntry 7}
    
vmvcAimStatComputeResourceTotalCPUUsage OBJECT-TYPE
    SYNTAX INTEGER
    ACCESS read-only
    STATUS mandatory
    DESCRIPTION
        "Total CPU usage of ComputeResource folder"
    ::= { vmvcAimStatComputeResourceFolderEntry 8}
    
vmvcAimStatComputeResourceTotalMemoryUsage OBJECT-TYPE
    SYNTAX INTEGER
    ACCESS read-only
    STATUS mandatory
    DESCRIPTION
        "Total aggregated memory resources (in MB) of all
         hosts within this ComputeResource folder.  It is NOT
         only the amount used, but is actually:
            amount used + amount available  (i.e. Total Memory)
         (The name of this attribute can be misleading.)"
    ::= { vmvcAimStatComputeResourceFolderEntry 9}

vmvcAimStatComputeResourceOverallState OBJECT-TYPE
    SYNTAX INTEGER {
        gray(1),
        green(2),
        yellow(3),
        red(4)
    }
    ACCESS read-only
    STATUS mandatory
    DESCRIPTION 
        "The overall status of the ComputeResource folder. It can be gray,green,red and yellow and
         follows the direct status from vCenter."
    ::= { vmvcAimStatComputeResourceFolderEntry 10}

vmvcAimStatComputeResourceVCUID OBJECT-TYPE
    SYNTAX INTEGER
    ACCESS read-only
    STATUS mandatory
    DESCRIPTION
        "VC Instance SNMP UID where this ComputeResource folder resides."
    ::= { vmvcAimStatComputeResourceFolderEntry 11}

vmvcAimStatComputeResourceVCName OBJECT-TYPE
    SYNTAX SnmpAdminString
    ACCESS read-only
    STATUS mandatory
    DESCRIPTION
        "VC Instance where this ComputeResource folder resides."
    ::= { vmvcAimStatComputeResourceFolderEntry 12}

vmvcAimStatComputeResourceVCUUID OBJECT-TYPE
    SYNTAX SnmpAdminString
    ACCESS read-only
    STATUS mandatory
    DESCRIPTION
        "The vCenter-specified UUID where this ComputeResource folder resides."
    ::= { vmvcAimStatComputeResourceFolderEntry 13}


-- *****************************************************************************
-- Status Cluster Group
-- *****************************************************************************
vmvcAimStatClusterCount OBJECT-TYPE
    SYNTAX INTEGER
    ACCESS read-only
    STATUS mandatory
    DESCRIPTION
        "Number of clusters in vmvcAimStatClusterTable."
    ::= { vmvcAimStatClusterGroup 1}

vmvcAimStatClusterTable OBJECT-TYPE
    SYNTAX SEQUENCE OF VmvcAimStatClusterRow
    ACCESS not-accessible
    STATUS mandatory
    DESCRIPTION
        "Cluster table."
    ::= { vmvcAimStatClusterGroup 2 }

vmvcAimStatClusterEntry OBJECT-TYPE
    SYNTAX VmvcAimStatClusterRow
    ACCESS not-accessible
    STATUS mandatory
    DESCRIPTION
        "The table entry."
    INDEX { vmvcAimStatClusterUID }
    ::= { vmvcAimStatClusterTable 1 }

VmvcAimStatClusterRow ::=
    SEQUENCE {
        vmvcAimStatClusterUID                       INTEGER,
        vmvcAimStatClusterIndex                     SnmpAdminString,
        vmvcAimStatClusterName                      SnmpAdminString,
        vmvcAimStatClusterComputeResourceFolderID   SnmpAdminString,
        vmvcAimStatClusterComputeResourceFolderPath SnmpAdminString,
        vmvcAimStatClusterDRSEnabled                INTEGER,
        vmvcAimStatClusterHAEnabled                 INTEGER,
        vmvcAimStatClusterDCName                    SnmpAdminString,
        vmvcAimStatClusterDCIndex                   SnmpAdminString,
        vmvcAimStatClusterVMBehaviour               SnmpAdminString,
        vmvcAimStatClusterVMotionrate               INTEGER,
        vmvcAimStatClusterCPUFairness               INTEGER,
        vmvcAimStatClusterMemoryFairness            INTEGER,
        vmvcAimStatClusterEffectiveCPU              INTEGER,
        vmvcAimStatClusterEffectiveMemory           INTEGER,
        vmvcAimStatClusterFailoverTolerance         INTEGER,
        vmvcAimStatClusterVCUID                     INTEGER,
        vmvcAimStatClusterVCName                    SnmpAdminString,
        vmvcAimStatClusterVCUUID                    SnmpAdminString
    }

vmvcAimStatClusterUID OBJECT-TYPE
    SYNTAX INTEGER (1..2147483647)
    ACCESS read-only
    STATUS mandatory
    DESCRIPTION
        "UID of Cluster."
    ::= { vmvcAimStatClusterEntry  1}

vmvcAimStatClusterIndex OBJECT-TYPE
    SYNTAX SnmpAdminString
    ACCESS read-only
    STATUS mandatory
    DESCRIPTION
        "MOID of Cluster."
    ::= { vmvcAimStatClusterEntry  2}

vmvcAimStatClusterName OBJECT-TYPE
    SYNTAX SnmpAdminString
    ACCESS read-only
    STATUS mandatory
    DESCRIPTION
        "Name of the Cluster."
    ::= { vmvcAimStatClusterEntry  3}

vmvcAimStatClusterComputeResourceFolderID OBJECT-TYPE
    SYNTAX SnmpAdminString
    ACCESS read-only
    STATUS mandatory
    DESCRIPTION
        "Immediate parent identifier."
    ::= { vmvcAimStatClusterEntry  4}

vmvcAimStatClusterComputeResourceFolderPath OBJECT-TYPE
    SYNTAX SnmpAdminString
    ACCESS read-only
    STATUS mandatory
    DESCRIPTION
        "Full path to the object."
    ::= { vmvcAimStatClusterEntry  5}

vmvcAimStatClusterDRSEnabled OBJECT-TYPE
    SYNTAX INTEGER
    ACCESS read-only
    STATUS mandatory
    DESCRIPTION
        "Flag indicating if DRS is enabled"
    ::= { vmvcAimStatClusterEntry  6}

vmvcAimStatClusterHAEnabled OBJECT-TYPE
    SYNTAX INTEGER
    ACCESS read-only
    STATUS mandatory
    DESCRIPTION
        "Flag indicating if HA is enabled"
    ::= { vmvcAimStatClusterEntry  7}

vmvcAimStatClusterDCName OBJECT-TYPE
    SYNTAX SnmpAdminString
    ACCESS read-only
    STATUS mandatory
    DESCRIPTION
        "Name of the cluster Datacenter."
    ::= { vmvcAimStatClusterEntry  8}

vmvcAimStatClusterDCIndex OBJECT-TYPE
    SYNTAX SnmpAdminString
    ACCESS read-only
    STATUS mandatory
    DESCRIPTION
        "Moid of the clusters Datacenter"
    ::= { vmvcAimStatClusterEntry  9}

vmvcAimStatClusterVMBehaviour OBJECT-TYPE
    SYNTAX SnmpAdminString
    ACCESS read-only
    STATUS mandatory
    DESCRIPTION
        "DR VM Behaviour in a cluster"
    ::= { vmvcAimStatClusterEntry 10}

vmvcAimStatClusterVMotionrate OBJECT-TYPE
    SYNTAX INTEGER
    ACCESS read-only
    STATUS mandatory
    DESCRIPTION
        "Migration thresholds for DR"
    ::= { vmvcAimStatClusterEntry 11}

vmvcAimStatClusterCPUFairness OBJECT-TYPE
    SYNTAX INTEGER
    ACCESS read-only
    STATUS mandatory
    DESCRIPTION
        "CPU Fairness of Cluster.  NOTE: Depending upon the configuration of vCenter, this attribute
         may not always be available.  When not available, this value is set to zero(0)."
    ::= { vmvcAimStatClusterEntry 12}
    
vmvcAimStatClusterMemoryFairness OBJECT-TYPE
    SYNTAX INTEGER
    ACCESS read-only
    STATUS mandatory
    DESCRIPTION
        "Memory Fairness of Cluster  NOTE: Depending upon the configuration of vCenter, this attribute
         may not always be available.  When not available, this value is set to zero(0)."
    ::= { vmvcAimStatClusterEntry 13}
    
vmvcAimStatClusterEffectiveCPU OBJECT-TYPE
    SYNTAX INTEGER
    ACCESS read-only
    STATUS mandatory
    DESCRIPTION
        "CPU Efffectiveness of the Cluster  NOTE: Depending upon the configuration of vCenter, this attribute
         may not always be available.  When not available, this value is set to zero(0)."
    ::= { vmvcAimStatClusterEntry 14}
    
vmvcAimStatClusterEffectiveMemory OBJECT-TYPE
    SYNTAX INTEGER
    ACCESS read-only
    STATUS mandatory
    DESCRIPTION
        "Effective KB Memory of Cluster  NOTE: Depending upon the configuration of vCenter, this attribute
         may not always be available.  When not available, this value is set to zero(0)."
    ::= { vmvcAimStatClusterEntry 15}
    
vmvcAimStatClusterFailoverTolerance OBJECT-TYPE
    SYNTAX INTEGER
    ACCESS read-only
    STATUS mandatory
    DESCRIPTION
        "Failover tolerance of Cluster  NOTE: Depending upon the configuration of vCenter, this attribute
         may not always be available.  When not available, this value is set to zero(0)."
    ::= { vmvcAimStatClusterEntry 16}

vmvcAimStatClusterVCUID OBJECT-TYPE
    SYNTAX INTEGER
    ACCESS read-only
    STATUS mandatory
    DESCRIPTION
        "VC Instance SNMP UID where this Cluster resides."
    ::= { vmvcAimStatClusterEntry 17}

vmvcAimStatClusterVCName OBJECT-TYPE
    SYNTAX SnmpAdminString
    ACCESS read-only
    STATUS mandatory
    DESCRIPTION
        "VC Instance where this Cluster resides."
    ::= { vmvcAimStatClusterEntry 18}

vmvcAimStatClusterVCUUID OBJECT-TYPE
    SYNTAX SnmpAdminString
    ACCESS read-only
    STATUS mandatory
    DESCRIPTION
        "The vCenter-specific UUID where this Cluster resides."
    ::= { vmvcAimStatClusterEntry 19}


-- *****************************************************************************
-- Status Host Group
-- *****************************************************************************
vmvcAimStatHostCount OBJECT-TYPE
    SYNTAX INTEGER
    ACCESS read-only
    STATUS mandatory
    DESCRIPTION
        "Number of Hosts in vmvcAimStatHostTable."
    ::= { vmvcAimStatHostGroup 1}

vmvcAimStatHostTable OBJECT-TYPE
    SYNTAX SEQUENCE OF VmvcAimStatHostRow
    ACCESS not-accessible
    STATUS mandatory
    DESCRIPTION
        "Host table."
    ::= { vmvcAimStatHostGroup 2 }

vmvcAimStatHostEntry OBJECT-TYPE
    SYNTAX VmvcAimStatHostRow
    ACCESS not-accessible
    STATUS mandatory
    DESCRIPTION
        "The table entry."
    INDEX { vmvcAimStatHostUID }
    ::= { vmvcAimStatHostTable 1 }

VmvcAimStatHostRow ::=
    SEQUENCE {
        vmvcAimStatHostUID                              INTEGER,
        vmvcAimStatHostID                               SnmpAdminString,
        vmvcAimStatHostName                             SnmpAdminString,
        vmvcAimStatHostComputeResourceFolderId          SnmpAdminString,
        vmvcAimStatHostClusterId                        SnmpAdminString,
        vmvcAimStatHostComputeResourceFolderName        SnmpAdminString,
        vmvcAimStatHostClusterName                      SnmpAdminString,
        vmvcAimStatHostDCName                           SnmpAdminString,
        vmvcAimStatHostDCIndex                          SnmpAdminString,
        vmvcAimStatHostFullPath                         SnmpAdminString,
        vmvcAimStatHostOSType                           SnmpAdminString,
        vmvcAimStatHostProd                             SnmpAdminString,
        vmvcAimStatHostProdBuildVer                     SnmpAdminString,
        vmvcAimStatHostProdVer                          SnmpAdminString,
        vmvcAimStatHostProdAPIType                      SnmpAdminString,
        vmvcAimStatHostProdAPIVer                       SnmpAdminString,
        vmvcAimStatHostMonitor                          INTEGER,
        vmvcAimStatHostNumCPU                           INTEGER,
        vmvcAimStatHostLogNumCPU                        INTEGER,
        vmvcAimStatHostCPUUsage                         INTEGER,
        vmvcAimStatHostAlertCPUUsageWarnThresh          INTEGER,
        vmvcAimStatHostAlertCPUUsageCritThresh          INTEGER,
        vmvcAimStatHostCPUAlert                         INTEGER,
        vmvcAimStatHostCPUState                         INTEGER,
        vmvcAimStatHostTotalMemory                      INTEGER,
        vmvcAimStatHostVMMemoryAvailable                INTEGER, 
        vmvcAimStatHostMemoryUsage                      INTEGER,
        vmvcAimStatHostAlertMemoryUsageWarnThreshold    INTEGER,
        vmvcAimStatHostAlertMemoryUsageCritThreshold    INTEGER,
        vmvcAimStatHostMemoryAlert                      INTEGER,
        vmvcAimStatHostMemoryState                      INTEGER,
        vmvcAimStatHostDiskHTL                          SnmpAdminString,
        vmvcAimStatHostNetAdapters                      SnmpAdminString, 
        vmvcAimStatHostTotalVMCPU                       INTEGER,
        vmvcAimStatHostTotalVMCPUWarnThreshold          INTEGER,
        vmvcAimStatHostTotalVMCPUCritThreshold          INTEGER,
        vmvcAimStatHostTotalVMCPUState                  INTEGER,
        vmvcAimStatHostTotalCPU                         INTEGER,
        vmvcAimStatHostTotalCPUWarnThreshold            INTEGER,
        vmvcAimStatHostTotalCPUCritThreshold            INTEGER,
        vmvcAimStatHostTotalCPUState                    INTEGER, 
        vmvcAimStatHostTotalVMMemory                    INTEGER,
        vmvcAimStatHostTotalVMMemoryWarnThreshold       INTEGER,
        vmvcAimStatHostTotalVMMemoryCritThreshold       INTEGER,
        vmvcAimStatHostTotalVMMemoryState               INTEGER,
        vmvcAimStatHostMemoryOther                      INTEGER,
        vmvcAimStatHostMemoryOtherWarnThreshold         INTEGER,
        vmvcAimStatHostMemoryOtherCritThreshold         INTEGER,
        vmvcAimStatHostMemoryOtherState                 INTEGER,
        vmvcAimStatHostMemoryTotal                      INTEGER,
        vmvcAimStatHostMemoryTotalWarnThreshold         INTEGER,
        vmvcAimStatHostMemoryTotalCritThreshold         INTEGER,
        vmvcAimStatHostMemoryTotalState                 INTEGER,
        vmvcAimStatHostTotalMachineMemory               INTEGER,
        vmvcAimStatHostCPUMonitor                       INTEGER,
        vmvcAimStatHostCPULagSetting                    INTEGER,
        vmvcAimStatHostCPULagValue                      INTEGER, 
        vmvcAimStatHostCPUAggregateStatus               INTEGER,
        vmvcAimStatHostMemoryMonitor                    INTEGER,
        vmvcAimStatHostDatastore                        SnmpAdminString,
        vmvcAimStatHostNetwork                          SnmpAdminString,
        vmvcAimStatHostVMotionEnabled                   INTEGER,
        vmvcAimStatHostConnectionState                  INTEGER,
        vmvcAimStatHostConsoleIPv4Address               SnmpAdminString,
        vmvcAimStatHostConsoleIPv6Address               SnmpAdminString,
        vmvcAimStatHostRunningVMCount                   INTEGER,
        vmvcAimStatHostRegisteredVMCount                INTEGER,
        vmvcAimStatHostUpTime                           TimeTicks,
        vmvcAimStatHostCPUIdleSec                       INTEGER,
        vmvcAimStatHostCPUUsedSec                       INTEGER,
        vmvcAimStatHostCPUUsagePerCPU                   SnmpAdminString,
        vmvcAimStatHostCPUShares                        INTEGER,
        vmvcAimStatHostCPUConfiguredMin                 INTEGER,
        vmvcAimStatHostCPUConfiguredMax                 INTEGER,
        vmvcAimStatHostMemoryAvailable                  INTEGER,
        vmvcAimStatHostMemoryUsed                       INTEGER,
        vmvcAimStatHostMemoryFree                       INTEGER,
        vmvcAimStatHostMemoryConfigured                 INTEGER,
        vmvcAimStatHostMemoryBalloon                    INTEGER,
        vmvcAimStatHostInMaintenance                    INTEGER,
        vmvcAimStatHostPowerStatus                      INTEGER,
        vmvcAimStatHostVMKernelIPv4Address              SnmpAdminString,
        vmvcAimStatHostVMKernelIPv6Address              SnmpAdminString,
        vmvcAimStatHostMaxSupportedVCPUs                INTEGER,
        vmvcAimStatHostVCUID                            INTEGER,
        vmvcAimStatHostVCName                           SnmpAdminString,
        vmvcAimStatHostHardwareUUID                     SnmpAdminString,
        vmvcAimStatHostFaultToleranceConf               INTEGER,
        vmvcAimStatHostFaultToleranceVersion            SnmpAdminString,
        vmvcAimStatHostTotalFTPrimaryVM                 INTEGER,
        vmvcAimStatHostPoweredOnFTPrimaryVM             INTEGER,
        vmvcAimStatHostTotalFTSecondaryVM               INTEGER,
        vmvcAimStatHostPoweredOnFTSecondaryVM           INTEGER,
        vmvcAimStatHostCPUAvailableForVM                INTEGER,
        vmvcAimStatHostTotalVMCPUUsage                  INTEGER,
        vmvcAimStatHostVCUUID                           SnmpAdminString
    }

vmvcAimStatHostUID OBJECT-TYPE
    SYNTAX INTEGER (1..2147483647)
    ACCESS read-only
    STATUS mandatory
    DESCRIPTION
        "Hosts UID."
    ::= { vmvcAimStatHostEntry  1}

vmvcAimStatHostID OBJECT-TYPE
    SYNTAX SnmpAdminString
    ACCESS read-only
    STATUS mandatory
    DESCRIPTION
        "Hosts MOID."
    ::= { vmvcAimStatHostEntry  2}

vmvcAimStatHostName OBJECT-TYPE
    SYNTAX SnmpAdminString
    ACCESS read-only
    STATUS mandatory
    DESCRIPTION
        "Name of ESX host."
    ::= { vmvcAimStatHostEntry  3}

vmvcAimStatHostComputeResourceFolderId OBJECT-TYPE
    SYNTAX SnmpAdminString
    ACCESS read-only
    STATUS mandatory
    DESCRIPTION
        "Immediate parent MOID. This property may be NA, if the Host is part of the cluster."
    ::= { vmvcAimStatHostEntry  4}

vmvcAimStatHostClusterId OBJECT-TYPE
    SYNTAX SnmpAdminString
    ACCESS read-only
    STATUS mandatory
    DESCRIPTION
        "Immediate parent MOID. This property may be NA, if the host is not part of a cluster."
    ::= { vmvcAimStatHostEntry  5}

vmvcAimStatHostComputeResourceFolderName OBJECT-TYPE
    SYNTAX SnmpAdminString
    ACCESS read-only
    STATUS mandatory
    DESCRIPTION
        "Name of parent compute resource."
    ::= { vmvcAimStatHostEntry  6}

vmvcAimStatHostClusterName OBJECT-TYPE
    SYNTAX SnmpAdminString
    ACCESS read-only
    STATUS mandatory
    DESCRIPTION
        "Name of the cluster."
    ::= { vmvcAimStatHostEntry  7}

vmvcAimStatHostDCName OBJECT-TYPE
    SYNTAX SnmpAdminString
    ACCESS read-only
    STATUS mandatory
    DESCRIPTION
        "Name of the datacenter."
    ::= { vmvcAimStatHostEntry  8}

vmvcAimStatHostDCIndex OBJECT-TYPE
    SYNTAX SnmpAdminString
    ACCESS read-only
    STATUS mandatory
    DESCRIPTION
        "Moid of the datacenter."
    ::= { vmvcAimStatHostEntry  9}

vmvcAimStatHostFullPath OBJECT-TYPE
    SYNTAX SnmpAdminString
    ACCESS read-only
    STATUS mandatory
    DESCRIPTION
        "Full path to Host object."
    ::= { vmvcAimStatHostEntry  10}

vmvcAimStatHostOSType OBJECT-TYPE
    SYNTAX SnmpAdminString
    ACCESS read-only
    STATUS mandatory
    DESCRIPTION
        "Host OS."
    ::= { vmvcAimStatHostEntry  11}

vmvcAimStatHostProd OBJECT-TYPE
    SYNTAX SnmpAdminString
    ACCESS read-only
    STATUS mandatory
    DESCRIPTION
        "Product name."
    ::= { vmvcAimStatHostEntry  12}

vmvcAimStatHostProdBuildVer OBJECT-TYPE
    SYNTAX SnmpAdminString
    ACCESS read-only
    STATUS mandatory
    DESCRIPTION
        "Product build version."
    ::= { vmvcAimStatHostEntry  13}

vmvcAimStatHostProdVer OBJECT-TYPE
    SYNTAX SnmpAdminString
    ACCESS read-only
    STATUS mandatory
    DESCRIPTION
        "Product version."
    ::= { vmvcAimStatHostEntry  14}

vmvcAimStatHostProdAPIType OBJECT-TYPE
    SYNTAX SnmpAdminString
    ACCESS read-only
    STATUS mandatory
    DESCRIPTION
        "Product API Type."
    ::= { vmvcAimStatHostEntry  15}

vmvcAimStatHostProdAPIVer OBJECT-TYPE
    SYNTAX SnmpAdminString
    ACCESS read-only
    STATUS mandatory
    DESCRIPTION
        "Product API Version."
    ::= { vmvcAimStatHostEntry  16}

vmvcAimStatHostMonitor OBJECT-TYPE
    SYNTAX INTEGER{
                do-not-monitor(1),
                monitor(2)
         }
    ACCESS read-write
    STATUS mandatory
    DESCRIPTION
        " status of the host if it is monitored or not monitored. "
    DEFVAL {2}
    ::= { vmvcAimStatHostEntry  17}

vmvcAimStatHostNumCPU OBJECT-TYPE
    SYNTAX INTEGER
    ACCESS read-only
    STATUS mandatory
    DESCRIPTION
        "Number of physical cpus."
    ::= { vmvcAimStatHostEntry  18}

vmvcAimStatHostLogNumCPU OBJECT-TYPE
    SYNTAX INTEGER
    ACCESS read-only
    STATUS mandatory
    DESCRIPTION
        "Number of logical cpus."
    ::= { vmvcAimStatHostEntry  19}

vmvcAimStatHostCPUUsage OBJECT-TYPE
    SYNTAX INTEGER
    ACCESS read-only
    STATUS mandatory
    DESCRIPTION
        "CPU Usage of the Host. This is the difference between the CPU usage of the entire ESX host and the CPU usage of the sum of virtual machines."
    ::= { vmvcAimStatHostEntry  20}

vmvcAimStatHostAlertCPUUsageWarnThresh OBJECT-TYPE
    SYNTAX INTEGER
    ACCESS read-write
    STATUS mandatory
    DESCRIPTION
        "Warning threshold  for CPU usage."
    DEFVAL { 60 }
    ::= { vmvcAimStatHostEntry  21}

vmvcAimStatHostAlertCPUUsageCritThresh OBJECT-TYPE
    SYNTAX INTEGER
    ACCESS read-write
    STATUS mandatory
    DESCRIPTION
        "Critical threshold  for CPU usage."
    DEFVAL { 80 }
    ::= { vmvcAimStatHostEntry  22}

vmvcAimStatHostCPUAlert OBJECT-TYPE
    SYNTAX INTEGER{
        warning-only(1),
        critical-only(2),
        both(3)    
        }
    ACCESS read-write
    STATUS mandatory
    DESCRIPTION
        "Alert of the cpu status. "
    DEFVAL { 3 }
    ::= { vmvcAimStatHostEntry  23}

vmvcAimStatHostCPUState OBJECT-TYPE
    SYNTAX INTEGER {
        unknown(1),
        ok(2),
        warning(3),
        critical(4)
    }
    ACCESS read-only
    STATUS mandatory
    DESCRIPTION
        "CPU State of host."
    ::= { vmvcAimStatHostEntry  24}

vmvcAimStatHostTotalMemory OBJECT-TYPE
    SYNTAX INTEGER
    ACCESS read-only
    STATUS mandatory
    DESCRIPTION
        "Total amount of installed physical memory on the host (in MB)."
    ::= { vmvcAimStatHostEntry  25}

vmvcAimStatHostVMMemoryAvailable OBJECT-TYPE
    SYNTAX INTEGER
    ACCESS read-only
    STATUS mandatory
    DESCRIPTION
        "Total Physical Memory Available for VM use (in MB).  It is smaller than Total Memory due to
         overhead consumption of the hypervisor layer."
    ::= { vmvcAimStatHostEntry  26}

vmvcAimStatHostMemoryUsage OBJECT-TYPE
    SYNTAX INTEGER
    ACCESS read-only
    STATUS mandatory
    DESCRIPTION
        "Percentage of Physical memory usage on the host."
    ::= { vmvcAimStatHostEntry  27}

vmvcAimStatHostAlertMemoryUsageWarnThreshold OBJECT-TYPE
    SYNTAX INTEGER 
    ACCESS read-write
    STATUS mandatory
    DESCRIPTION
        "Warning Threshold for Memory Usage"
    DEFVAL { 60 }
    ::= { vmvcAimStatHostEntry  28}

vmvcAimStatHostAlertMemoryUsageCritThreshold OBJECT-TYPE
    SYNTAX INTEGER
    ACCESS read-write
    STATUS mandatory
    DESCRIPTION
        "Critical Threshold for Memory Usage"
    DEFVAL { 80 }
    ::= { vmvcAimStatHostEntry  29}

vmvcAimStatHostMemoryAlert OBJECT-TYPE
    SYNTAX INTEGER{
        warning(1),
        critical(2),
        both(3)
        }
    ACCESS read-write
    STATUS mandatory
    DESCRIPTION
        " Alert of the memory status. That may be warning(1),critical(2) or both(3)"
    DEFVAL { 3 }
    ::= { vmvcAimStatHostEntry  30}

vmvcAimStatHostMemoryState OBJECT-TYPE
    SYNTAX INTEGER {
        unknown(1),
        ok(2),
        warning(3),
        critical(4)
    }
    ACCESS read-only
    STATUS mandatory
    DESCRIPTION
        "Memory State of the Host"
    ::= { vmvcAimStatHostEntry  31}

vmvcAimStatHostDiskHTL OBJECT-TYPE
    SYNTAX SnmpAdminString
    ACCESS read-only
    STATUS mandatory
    DESCRIPTION
        "The space delimited set of disks specified as sets of host target LUN(HTL) example vmhba0:0:0.."
    ::= { vmvcAimStatHostEntry  32}

vmvcAimStatHostNetAdapters OBJECT-TYPE
    SYNTAX SnmpAdminString
    ACCESS read-only
    STATUS mandatory
    DESCRIPTION
        "The Space delimited set of MAC Addresses corresponding to virtual adapters."
    ::= { vmvcAimStatHostEntry  33}

vmvcAimStatHostTotalVMCPU OBJECT-TYPE
    SYNTAX INTEGER
    ACCESS read-only
    STATUS mandatory
    DESCRIPTION
        "The sum of CPU usage of all the virtual machines on the ESX Server."
    ::= { vmvcAimStatHostEntry  34}

vmvcAimStatHostTotalVMCPUWarnThreshold OBJECT-TYPE
    SYNTAX INTEGER
    ACCESS read-write
    STATUS mandatory
    DESCRIPTION
        "The warning threshold of CPU usage of all the virtual machines on the ESX Server."
    DEFVAL { 60 }
    ::= { vmvcAimStatHostEntry  35}

vmvcAimStatHostTotalVMCPUCritThreshold OBJECT-TYPE
    SYNTAX INTEGER
    ACCESS read-write
    STATUS mandatory
    DESCRIPTION
        "The critical threshold of CPU usage of all the virtual machines on the ESX Server."
    DEFVAL { 80 }
    ::= { vmvcAimStatHostEntry  36}

vmvcAimStatHostTotalVMCPUState OBJECT-TYPE
    SYNTAX INTEGER {
        unknown(1),
        ok(2),
        warning(3),
        critical(4)
    }
    ACCESS read-only
    STATUS mandatory
    DESCRIPTION
        "The state of CPU usage of all the virtual machines on the ESX Server."
    ::= { vmvcAimStatHostEntry  37}

vmvcAimStatHostTotalCPU OBJECT-TYPE
    SYNTAX INTEGER
    ACCESS read-only
    STATUS mandatory
    DESCRIPTION
        "The sum of CPU Usage of the VMs and ESX Console."
    ::= { vmvcAimStatHostEntry  38}

vmvcAimStatHostTotalCPUWarnThreshold OBJECT-TYPE
    SYNTAX INTEGER
    ACCESS read-write
    STATUS mandatory
    DESCRIPTION
        "The warning threshold of CPU Usage of the VMs and ESX Console."
    DEFVAL { 60 }
    ::= { vmvcAimStatHostEntry  39}

vmvcAimStatHostTotalCPUCritThreshold OBJECT-TYPE
    SYNTAX INTEGER
    ACCESS read-write
    STATUS mandatory
    DESCRIPTION
        "The critical threshold of CPU Usage of the VMs and ESX Console."
    DEFVAL { 80 }
    ::= { vmvcAimStatHostEntry  40}

vmvcAimStatHostTotalCPUState OBJECT-TYPE
    SYNTAX INTEGER {
        unknown(1),
        ok(2),
        warning(3),
        critical(4)
    }
    ACCESS read-only
    STATUS mandatory
    DESCRIPTION
        "The state of CPU Usage of the VMs and ESX Console."
    ::= { vmvcAimStatHostEntry  41}

vmvcAimStatHostTotalVMMemory OBJECT-TYPE
    SYNTAX INTEGER
    ACCESS read-only
    STATUS mandatory
    DESCRIPTION
        "The sum of memory usage of all the virtual machines on the ESX Server with respect to Total Machine Memory."
    ::= { vmvcAimStatHostEntry  42}

vmvcAimStatHostTotalVMMemoryWarnThreshold OBJECT-TYPE
    SYNTAX INTEGER
    ACCESS read-write
    STATUS mandatory
    DESCRIPTION
        "The warning threshold of memory usage of all the virtual machines on the ESX Server with respect to Total Machine Memory."
    DEFVAL { 60 }
    ::= { vmvcAimStatHostEntry  43}

vmvcAimStatHostTotalVMMemoryCritThreshold OBJECT-TYPE
    SYNTAX INTEGER
    ACCESS read-write
    STATUS mandatory
    DESCRIPTION
        "The critical threshold of memory usage of all the virtual machines on the ESX Server with respect to Total Machine Memory."
    DEFVAL { 80 }
    ::= { vmvcAimStatHostEntry  44}

vmvcAimStatHostTotalVMMemoryState OBJECT-TYPE
    SYNTAX INTEGER {
        unknown(1),
        ok(2),
        warning(3),
        critical(4)
    }
    ACCESS read-only
    STATUS mandatory
    DESCRIPTION
        "The state of memory usage of all the virtual machines on the ESX Server with respect to Total Machine Memory."
    ::= { vmvcAimStatHostEntry  45}

vmvcAimStatHostMemoryOther OBJECT-TYPE
    SYNTAX INTEGER
    ACCESS read-only
    STATUS mandatory
    DESCRIPTION
        "The memory usage of the ESX Server Console with respect to Total Machine Memory."
    ::= { vmvcAimStatHostEntry  46}

vmvcAimStatHostMemoryOtherWarnThreshold OBJECT-TYPE
    SYNTAX INTEGER
    ACCESS read-write
    STATUS mandatory
    DESCRIPTION
        "The warning threshold for memory usage of the ESX Server Console with respect to Total Machine Memory."
    DEFVAL { 60 }
    ::= { vmvcAimStatHostEntry  47}

vmvcAimStatHostMemoryOtherCritThreshold OBJECT-TYPE
    SYNTAX INTEGER
    ACCESS read-write
    STATUS mandatory
    DESCRIPTION
        "The critical threshold for memory usage of the ESX Server Console with respect to Total Machine Memory."
    DEFVAL { 80 }
    ::= { vmvcAimStatHostEntry  48}

vmvcAimStatHostMemoryOtherState OBJECT-TYPE
    SYNTAX INTEGER {
        unknown(1),
        ok(2),
        warning(3),
        critical(4)
    }
    ACCESS read-only
    STATUS mandatory
    DESCRIPTION
        "The state of memory usage of the ESX Server Console with respect to Total Machine Memory."
    ::= { vmvcAimStatHostEntry  49}

vmvcAimStatHostMemoryTotal OBJECT-TYPE
    SYNTAX INTEGER
    ACCESS read-only
    STATUS mandatory
    DESCRIPTION
        "The total memory usage ( sum of ESX Server Console and all VMs ) with respect to Total Machine Memory."
    ::= { vmvcAimStatHostEntry  50}

vmvcAimStatHostMemoryTotalWarnThreshold OBJECT-TYPE
    SYNTAX INTEGER
    ACCESS read-write
    STATUS mandatory
    DESCRIPTION
        "The warning threshold for the total memory usage ( sum of ESX Server Console and all VMs ) with respect to Total Machine Memory."
    DEFVAL { 60 }
    ::= { vmvcAimStatHostEntry  51}

vmvcAimStatHostMemoryTotalCritThreshold OBJECT-TYPE
    SYNTAX INTEGER
    ACCESS read-write
    STATUS mandatory
    DESCRIPTION
        "The critical threshold for the total memory usage ( sum of ESX Server Console and all VMs ) with respect to Total Machine Memory."
    DEFVAL { 80 }
    ::= { vmvcAimStatHostEntry  52}

vmvcAimStatHostMemoryTotalState OBJECT-TYPE
    SYNTAX INTEGER {
        unknown(1),
        ok(2),
        warning(3),
        critical(4)
    }
    ACCESS read-only
    STATUS mandatory
    DESCRIPTION
        "The state of the total memory usage ( sum of ESX Server Console and all VMs ) with respect to Total Machine Memory."
    ::= { vmvcAimStatHostEntry  53}

vmvcAimStatHostTotalMachineMemory OBJECT-TYPE
    SYNTAX INTEGER
    ACCESS read-only
    STATUS mandatory
    DESCRIPTION
        "The Total Physical memory of the machine on which ESX Server is running, in megabytes."
    ::= { vmvcAimStatHostEntry  54}

vmvcAimStatHostCPUMonitor OBJECT-TYPE
    SYNTAX INTEGER {
         do-not-monitor(1),
        monitor(2)
    }
    ACCESS read-write
    STATUS mandatory
    DESCRIPTION    
        "Flag indicating whether the CPU usage for node to be monitored(2) or not(1)."
    DEFVAL { 2 }
    ::= { vmvcAimStatHostEntry  55}

vmvcAimStatHostCPULagSetting OBJECT-TYPE
    SYNTAX  INTEGER
    ACCESS  read-write
    STATUS  mandatory
    DESCRIPTION 
        "The number of consecutive times the threshold should be breached before the status change occurs."
    DEFVAL { 3 }
    ::= { vmvcAimStatHostEntry  56}

vmvcAimStatHostCPULagValue OBJECT-TYPE
    SYNTAX  INTEGER
    ACCESS  read-only
    STATUS  mandatory
    DESCRIPTION 
        "The current running count of the number of consecutive times the status is in the current status."
    ::= { vmvcAimStatHostEntry  57}

vmvcAimStatHostCPUAggregateStatus OBJECT-TYPE
    SYNTAX INTEGER {
        unknown(1),
        ok(2),
        warning(3),
        critical(4)
    }
    ACCESS  read-only
    STATUS  mandatory
    DESCRIPTION
        "The current aggregate CPU Status (ok, warning, critical)."
    ::= { vmvcAimStatHostEntry  58}

vmvcAimStatHostMemoryMonitor OBJECT-TYPE
    SYNTAX INTEGER {
        do-not-monitor(1),
        monitor(2)
    }
    ACCESS read-write
    STATUS mandatory
    DESCRIPTION    
        "Flag indicating whether the Memory usage for host to be monitored(2) or not(1)."
    DEFVAL { 2 }
    ::= { vmvcAimStatHostEntry  59}

vmvcAimStatHostDatastore OBJECT-TYPE
    SYNTAX SnmpAdminString (SIZE(0..2048))
    ACCESS read-only
    STATUS mandatory
    DESCRIPTION
        "Delimited list of Datastore names related to this host"
    ::= { vmvcAimStatHostEntry  60}

vmvcAimStatHostNetwork OBJECT-TYPE
    SYNTAX SnmpAdminString
    ACCESS read-only
    STATUS mandatory
    DESCRIPTION
        "Network related to this host"
    ::= { vmvcAimStatHostEntry  61}

vmvcAimStatHostVMotionEnabled  OBJECT-TYPE
    SYNTAX INTEGER
    ACCESS read-only
    STATUS mandatory
    DESCRIPTION
        "Flag indicating whether VMotion is enabled or not"
    ::= { vmvcAimStatHostEntry  62}

vmvcAimStatHostConnectionState OBJECT-TYPE
    SYNTAX INTEGER {
        disconnected(1),
        connected(2),
        notResponding(3),
        unknown(4)
    }
    ACCESS read-only
    STATUS mandatory
    DESCRIPTION
        "Connection Status of the Host."
    ::= { vmvcAimStatHostEntry  63}

vmvcAimStatHostConsoleIPv4Address OBJECT-TYPE
    SYNTAX SnmpAdminString (SIZE(0..1024))
    ACCESS read-only
    STATUS mandatory
    DESCRIPTION
        "Service Console IPv4 Addresses of the Host. This is a delimited list of IP Addresses for this host Console."
    ::= { vmvcAimStatHostEntry  64}

vmvcAimStatHostConsoleIPv6Address OBJECT-TYPE
    SYNTAX SnmpAdminString (SIZE(0..2048))
    ACCESS read-only
    STATUS mandatory
    DESCRIPTION
        "Service Console IPv6 Addresses of the Host. This is a delimited list of IP Addresses for this host Console."
    ::= { vmvcAimStatHostEntry  65}

vmvcAimStatHostRunningVMCount  OBJECT-TYPE
    SYNTAX INTEGER
    ACCESS read-only
    STATUS mandatory
    DESCRIPTION
        "The Number of Running VM's"
    ::= { vmvcAimStatHostEntry  66}

vmvcAimStatHostRegisteredVMCount  OBJECT-TYPE
    SYNTAX INTEGER
    ACCESS read-only
    STATUS mandatory
    DESCRIPTION
        "The Number of Registered VM's"
    ::= { vmvcAimStatHostEntry  67}

vmvcAimStatHostUpTime OBJECT-TYPE
    SYNTAX TimeTicks
    ACCESS read-only
    STATUS mandatory
    DESCRIPTION
        " The timestamp when the Host machine was most recently powered on."
    ::= { vmvcAimStatHostEntry  68}

vmvcAimStatHostCPUIdleSec  OBJECT-TYPE
    SYNTAX INTEGER
    ACCESS read-only
    STATUS mandatory
    DESCRIPTION
        "Host CPU Idle time, converted to percentage.  This is not in seconds."
    ::= { vmvcAimStatHostEntry  69}

vmvcAimStatHostCPUUsedSec  OBJECT-TYPE
    SYNTAX INTEGER
    ACCESS read-only
    STATUS mandatory
    DESCRIPTION
        "Host CPU Used time, converted to percentage.  This is not in seconds."
    ::= { vmvcAimStatHostEntry  70}

vmvcAimStatHostCPUUsagePerCPU  OBJECT-TYPE
    SYNTAX SnmpAdminString
    ACCESS read-only
    STATUS mandatory
    DESCRIPTION
        "Host CPU Usage per CPU"
    ::= { vmvcAimStatHostEntry  71}

vmvcAimStatHostCPUShares  OBJECT-TYPE
    SYNTAX INTEGER
    ACCESS read-only
    STATUS mandatory
    DESCRIPTION
        "CPU Shares assigned to Host"
    ::= { vmvcAimStatHostEntry  72}

vmvcAimStatHostCPUConfiguredMin  OBJECT-TYPE
    SYNTAX INTEGER
    ACCESS read-only
    STATUS mandatory
    DESCRIPTION
        "Minimum CPU Configured"
    ::= { vmvcAimStatHostEntry  73}

vmvcAimStatHostCPUConfiguredMax  OBJECT-TYPE
    SYNTAX INTEGER
    ACCESS read-only
    STATUS mandatory
    DESCRIPTION
        "Maximum CPU Configured.  This is effectively the sum of all configured CPUs on the Host (in MHz)."
    ::= { vmvcAimStatHostEntry  74}

vmvcAimStatHostMemoryAvailable  OBJECT-TYPE
    SYNTAX INTEGER
    ACCESS read-only
    STATUS mandatory
    DESCRIPTION
        "Available Memory on Host"
    ::= { vmvcAimStatHostEntry  75}

vmvcAimStatHostMemoryUsed  OBJECT-TYPE
    SYNTAX INTEGER
    ACCESS read-only
    STATUS mandatory
    DESCRIPTION
        "Memory Used by Host"
    ::= { vmvcAimStatHostEntry  76}

vmvcAimStatHostMemoryFree  OBJECT-TYPE
    SYNTAX INTEGER
    ACCESS read-only
    STATUS mandatory
    DESCRIPTION
        "Host Memory Free Space"
    ::= { vmvcAimStatHostEntry  77}

vmvcAimStatHostMemoryConfigured  OBJECT-TYPE
    SYNTAX INTEGER
    ACCESS read-only
    STATUS mandatory
    DESCRIPTION
        "Host Memory Configured"
    ::= { vmvcAimStatHostEntry  78}

vmvcAimStatHostMemoryBalloon  OBJECT-TYPE
    SYNTAX INTEGER
    ACCESS read-only
    STATUS mandatory
    DESCRIPTION
        "Memory Balloon space on Host"
    ::= { vmvcAimStatHostEntry  79}

vmvcAimStatHostInMaintenance  OBJECT-TYPE
    SYNTAX INTEGER{
        true(1),
        false(2)
    }
    ACCESS read-only
    STATUS mandatory
    DESCRIPTION
        "Flag indicates whether the host is in maintenance mode or normal mode"
    ::= { vmvcAimStatHostEntry  80}

vmvcAimStatHostPowerStatus OBJECT-TYPE
    SYNTAX INTEGER {
        poweredOff(1),
        poweredOn(2),
        standBy(3),
        unknown(4)
    }
    ACCESS read-only
    STATUS mandatory
    DESCRIPTION
        "Power Status of the Host."
    ::= { vmvcAimStatHostEntry  81}

vmvcAimStatHostVMKernelIPv4Address OBJECT-TYPE
    SYNTAX SnmpAdminString (SIZE(0..1024))
    ACCESS read-only
    STATUS mandatory
    DESCRIPTION
        "VMKernel IPv4 Addresses of the Host. This is a delimited list of IP Addresses for this host's VMKernel VNICs."
    ::= { vmvcAimStatHostEntry  82}

vmvcAimStatHostVMKernelIPv6Address OBJECT-TYPE
    SYNTAX SnmpAdminString (SIZE(0..2048))
    ACCESS read-only
    STATUS mandatory
    DESCRIPTION
        "VMKernel IPv6 Addresses of the Host. This is a delimited list of IP Addresses for this host's VMKernel VNICs."
    ::= { vmvcAimStatHostEntry  83}

vmvcAimStatHostMaxSupportedVCPUs OBJECT-TYPE
    SYNTAX INTEGER
    ACCESS read-only
    STATUS mandatory
    DESCRIPTION
        "Maximum number of Virutal CPUs that can be assigned to VMs on this Host."
    ::= { vmvcAimStatHostEntry  84}

vmvcAimStatHostVCUID OBJECT-TYPE
    SYNTAX INTEGER
    ACCESS read-only
    STATUS mandatory
    DESCRIPTION
        "VC Instance SNMP UID where this Host resides."
    ::= { vmvcAimStatHostEntry  85}

vmvcAimStatHostVCName OBJECT-TYPE
    SYNTAX SnmpAdminString
    ACCESS read-only
    STATUS mandatory
    DESCRIPTION
        "VC Instance where this Host resides."
    ::= { vmvcAimStatHostEntry  86}

vmvcAimStatHostHardwareUUID OBJECT-TYPE
    SYNTAX SnmpAdminString
    ACCESS read-only
    STATUS mandatory
    DESCRIPTION
        "Hardware UUID for this Host."
    ::= { vmvcAimStatHostEntry  87}

vmvcAimStatHostFaultToleranceConf  OBJECT-TYPE
    SYNTAX INTEGER{
        true(1),
        false(2)
    }
    ACCESS read-only
    STATUS mandatory
    DESCRIPTION
        "Flag indicating whether this Host has been configured for Fault Tolerance."
    ::= { vmvcAimStatHostEntry  88}

vmvcAimStatHostFaultToleranceVersion OBJECT-TYPE
    SYNTAX SnmpAdminString
    ACCESS read-only
    STATUS mandatory
    DESCRIPTION
        "Fault Tolerance Version for this Host, if Fault Tolerance is enabled."
    ::= { vmvcAimStatHostEntry  89}

vmvcAimStatHostTotalFTPrimaryVM OBJECT-TYPE
    SYNTAX INTEGER
    ACCESS read-only
    STATUS mandatory
    DESCRIPTION
        "Number of Fault Tolerance Primary VMs on this Host."
    ::= { vmvcAimStatHostEntry  90}

vmvcAimStatHostPoweredOnFTPrimaryVM OBJECT-TYPE
    SYNTAX INTEGER
    ACCESS read-only
    STATUS mandatory
    DESCRIPTION
        "Number of Fault Tolerance Powered-on Primary VMs currently on this Host."
    ::= { vmvcAimStatHostEntry  91}

vmvcAimStatHostTotalFTSecondaryVM OBJECT-TYPE
    SYNTAX INTEGER
    ACCESS read-only
    STATUS mandatory
    DESCRIPTION
        "Number of Fault Tolerance Secondary VMs on this Host."
    ::= { vmvcAimStatHostEntry  92}

vmvcAimStatHostPoweredOnFTSecondaryVM OBJECT-TYPE
    SYNTAX INTEGER
    ACCESS read-only
    STATUS mandatory
    DESCRIPTION
        "Number of Fault Tolerance Powered-on Secondary VMs currently on this Host."
    ::= { vmvcAimStatHostEntry  93}

vmvcAimStatHostCPUAvailableForVM OBJECT-TYPE
    SYNTAX INTEGER
    ACCESS read-only
    STATUS mandatory
    DESCRIPTION
        "The total amount of CPU Available for VM use (in MHz).  This is smaller than Total Configured
         CPU, due to the overhead consumption of the hypervisor layer."
    ::= { vmvcAimStatHostEntry  94}

vmvcAimStatHostTotalVMCPUUsage OBJECT-TYPE
    SYNTAX INTEGER
    ACCESS read-only
    STATUS mandatory
    DESCRIPTION
        "The total amount of CPU used by the VMs under the host (in MHz)."
    ::= { vmvcAimStatHostEntry  95}

vmvcAimStatHostVCUUID OBJECT-TYPE
    SYNTAX SnmpAdminString
    ACCESS read-only
    STATUS mandatory
    DESCRIPTION
        "The vCenter-specific UUID where this Host resides."
    ::= { vmvcAimStatHostEntry  96}


-- *****************************************************************************
-- Status Resource Pool Group
-- *****************************************************************************
vmvcAimStatResourcePoolCount OBJECT-TYPE
    SYNTAX INTEGER
    ACCESS read-only
    STATUS mandatory
    DESCRIPTION
        "Number of Resource Pools in vmvcAimStatResourcePoolTable."
    ::= { vmvcAimStatResPoolGroup 1}

vmvcAimStatResourcePoolTable OBJECT-TYPE
    SYNTAX SEQUENCE OF VmvcAimStatResourcePoolRow
    ACCESS not-accessible
    STATUS mandatory
    DESCRIPTION
        "ResourcePool table."
    ::= { vmvcAimStatResPoolGroup 2 }

vmvcAimStatResourcePoolEntry OBJECT-TYPE
    SYNTAX VmvcAimStatResourcePoolRow
    ACCESS not-accessible
    STATUS mandatory
    DESCRIPTION
        "The table entry."
    INDEX { vmvcAimStatResourcePoolUID  }
    ::= { vmvcAimStatResourcePoolTable 1 }

VmvcAimStatResourcePoolRow ::=
    SEQUENCE {
        vmvcAimStatResourcePoolUID                  INTEGER,
        vmvcAimStatResourcePoolIndex                SnmpAdminString,
        vmvcAimStatResourcePoolName                 SnmpAdminString,
        vmvcAimStatResourcePoolParentId             SnmpAdminString,
        vmvcAimStatResourcePoolParentPath           SnmpAdminString,
        vmvcAimStatResourcePoolIndexPath            SnmpAdminString,
        vmvcAimStatResourcePoolComputeResourceId    SnmpAdminString,
        vmvcAimStatResourcePoolComputeResourceName  SnmpAdminString,
        vmvcAimStatResourcePoolComputeResourcePath  SnmpAdminString,
        vmvcAimStatResourcePoolCPUExpandReservation INTEGER,
        vmvcAimStatResourcePoolCPUMax               INTEGER,
        vmvcAimStatResourcePoolCPUMin               INTEGER,
        vmvcAimStatResourcePoolCPUShares            INTEGER,
        vmvcAimStatResourcePoolMemExpandReservation INTEGER,
        vmvcAimStatResourcePoolMemMax               INTEGER,
        vmvcAimStatResourcePoolMemMin               INTEGER,
        vmvcAimStatResourcePoolMemShares            INTEGER,
        vmvcAimStatResourcePoolCfgChgVersion        SnmpAdminString,
        vmvcAimStatResourcePoolCPUMaxUsage          INTEGER,
        vmvcAimStatResourcePoolCPUOverAllUsage      INTEGER,
        vmvcAimStatResourcePoolCPUUsagePct          INTEGER,
        vmvcAimStatResourcePoolCPUUsageWarn         INTEGER,
        vmvcAimStatResourcePoolCPUUsageCrit         INTEGER,
        vmvcAimStatResourcePoolCPUAlert             INTEGER,
        vmvcAimStatResourcePoolCPUState             INTEGER,
        vmvcAimStatResourcePoolCPUReserveUsed       INTEGER,
        vmvcAimStatResourcePoolCPUReserveUsedForVM  INTEGER,
        vmvcAimStatResourcePoolCPUUnReserveForPool  INTEGER,
        vmvcAimStatResourcePoolCPUUnReserveForVM    INTEGER,
        vmvcAimStatResourcePoolMemMaxUsage          INTEGER,
        vmvcAimStatResourcePoolMemOverAllUsage      INTEGER, 
        vmvcAimStatResourcePoolMemUsagePct          INTEGER, 
        vmvcAimStatResourcePoolMemUsageWarn         INTEGER, 
        vmvcAimStatResourcePoolMemUsageCrit         INTEGER, 
        vmvcAimStatResourcePoolMemAlert             INTEGER, 
        vmvcAimStatResourcePoolMemState             INTEGER, 
        vmvcAimStatResourcePoolMemReserveUsed       INTEGER,
        vmvcAimStatResourcePoolMemReserveUsedForVM  INTEGER,
        vmvcAimStatResourcePoolMemUnReserveForPool  INTEGER,
        vmvcAimStatResourcePoolMemUnReserveForVM    INTEGER,
        vmvcAimStatResourcePoolStatus               INTEGER,
        vmvcAimStatResourcePoolMonitor              INTEGER,
        vmvcAimStatResourcePoolAlert                INTEGER,
        vmvcAimStatResourcePoolState                INTEGER,
        vmvcAimStatResourcePoolType                 INTEGER,
        vmvcAimStatResourcePoolVCUID                INTEGER,
        vmvcAimStatResourcePoolVCName               SnmpAdminString,
        vmvcAimStatResourcePoolVCUUID               SnmpAdminString
    }

vmvcAimStatResourcePoolUID OBJECT-TYPE
    SYNTAX INTEGER (1..2147483647)
    ACCESS read-only
    STATUS mandatory
    DESCRIPTION
        "UID of the ResourcePool"
    ::= { vmvcAimStatResourcePoolEntry  1}

vmvcAimStatResourcePoolIndex OBJECT-TYPE
    SYNTAX SnmpAdminString
    ACCESS read-only
    STATUS mandatory
    DESCRIPTION
        "Indentifier of the ResourcePool"
    ::= { vmvcAimStatResourcePoolEntry  2}

vmvcAimStatResourcePoolName OBJECT-TYPE
    SYNTAX SnmpAdminString
    ACCESS read-only
    STATUS mandatory
    DESCRIPTION
        "Name of the ResourcePool"
    ::= { vmvcAimStatResourcePoolEntry  3}

vmvcAimStatResourcePoolParentId OBJECT-TYPE
    SYNTAX SnmpAdminString
    ACCESS read-only
    STATUS mandatory
    DESCRIPTION
        "Immediate parent identifier"
    ::= { vmvcAimStatResourcePoolEntry  4}

vmvcAimStatResourcePoolParentPath OBJECT-TYPE
    SYNTAX SnmpAdminString
    ACCESS read-only
    STATUS mandatory
    DESCRIPTION
        "Full path to the parent"
    ::= { vmvcAimStatResourcePoolEntry  5}

vmvcAimStatResourcePoolIndexPath  OBJECT-TYPE
    SYNTAX SnmpAdminString
    ACCESS read-only
    STATUS mandatory
    DESCRIPTION
        "Index Path of resource pool from Host or cluster"
    ::= { vmvcAimStatResourcePoolEntry  6}

vmvcAimStatResourcePoolComputeResourceId OBJECT-TYPE
    SYNTAX SnmpAdminString
    ACCESS read-only
    STATUS mandatory
    DESCRIPTION
        "ResourcePools ComputeResource Identifier"
    ::= { vmvcAimStatResourcePoolEntry  7}

vmvcAimStatResourcePoolComputeResourceName OBJECT-TYPE
    SYNTAX SnmpAdminString
    ACCESS read-only
    STATUS mandatory
    DESCRIPTION
        "ResourcePools ComputeResource Name"
    ::= { vmvcAimStatResourcePoolEntry  8}

vmvcAimStatResourcePoolComputeResourcePath OBJECT-TYPE
    SYNTAX SnmpAdminString
    ACCESS read-only
    STATUS mandatory
    DESCRIPTION
        "Full path to the ComputeResource"
    ::= { vmvcAimStatResourcePoolEntry  9}

vmvcAimStatResourcePoolCPUExpandReservation OBJECT-TYPE
    SYNTAX INTEGER
    ACCESS read-only
    STATUS mandatory
    DESCRIPTION
        " In a resource pool with an expandable reservation(1), 
        the reservation on a resource pool can grow beyond the specified value, 
        if the parent resource pool has unreserved resources. A non-expandable(0) 
        reservation is called a fixed reservation. "
    ::= { vmvcAimStatResourcePoolEntry  10}

vmvcAimStatResourcePoolCPUMax OBJECT-TYPE
    SYNTAX INTEGER
    ACCESS read-only
    STATUS mandatory
    DESCRIPTION
        "Maximum CPU ( MHz ) for the resource pool"
    ::= { vmvcAimStatResourcePoolEntry  11}

vmvcAimStatResourcePoolCPUMin OBJECT-TYPE
    SYNTAX INTEGER
    ACCESS read-only
    STATUS mandatory
    DESCRIPTION
        "Minimum CPU ( MHz ) for the resource pool"
    ::= { vmvcAimStatResourcePoolEntry  12}

vmvcAimStatResourcePoolCPUShares OBJECT-TYPE
    SYNTAX INTEGER
    ACCESS read-only
    STATUS mandatory
    DESCRIPTION
        "CPU Shares assigned to the resource pool"
    ::= { vmvcAimStatResourcePoolEntry  13}

vmvcAimStatResourcePoolMemExpandReservation OBJECT-TYPE
    SYNTAX INTEGER
    ACCESS read-only
    STATUS mandatory
    DESCRIPTION
        " In a resource pool with an expandable reservation(1), 
        the reservation on a resource pool can grow beyond the specified value, 
        if the parent resource pool has unreserved resources. A non-expandable(0) 
        reservation is called a fixed reservation. "
    ::= { vmvcAimStatResourcePoolEntry  14}

vmvcAimStatResourcePoolMemMax OBJECT-TYPE
    SYNTAX INTEGER
    ACCESS read-only
    STATUS mandatory
    DESCRIPTION
        "Maximum Memory ( MB ) for the resource pool"
    ::= { vmvcAimStatResourcePoolEntry  15}

vmvcAimStatResourcePoolMemMin OBJECT-TYPE
    SYNTAX INTEGER
    ACCESS read-only
    STATUS mandatory
    DESCRIPTION
        "Minimun Memory ( MB ) for the resource pool"
    ::= { vmvcAimStatResourcePoolEntry  16}

vmvcAimStatResourcePoolMemShares OBJECT-TYPE
    SYNTAX INTEGER
    ACCESS read-only
    STATUS mandatory
    DESCRIPTION
        "Memory Shares assigned to the resource pool"
    ::= { vmvcAimStatResourcePoolEntry  17}

vmvcAimStatResourcePoolCfgChgVersion OBJECT-TYPE
    SYNTAX SnmpAdminString
    ACCESS read-only
    STATUS mandatory
    DESCRIPTION
        "The changeVersion is a unique identifier for a given version of the configuration"
    ::= { vmvcAimStatResourcePoolEntry  18}

vmvcAimStatResourcePoolCPUMaxUsage OBJECT-TYPE
    SYNTAX INTEGER
    ACCESS read-only
    STATUS mandatory
    DESCRIPTION
        "Current upper-bound on cpu usage"
    ::= { vmvcAimStatResourcePoolEntry  19}

vmvcAimStatResourcePoolCPUOverAllUsage OBJECT-TYPE
    SYNTAX INTEGER
    ACCESS read-only
    STATUS mandatory
    DESCRIPTION
        " CPU overall usage/consumption of all running child Virtual machines (in MHz), including virtual machines in the 
         child resource pools."
    ::= { vmvcAimStatResourcePoolEntry  20}

vmvcAimStatResourcePoolCPUUsagePct OBJECT-TYPE
    SYNTAX INTEGER
    ACCESS read-only
    STATUS mandatory
    DESCRIPTION
        "Resource Pool CPU Usage Percentage"
    ::= { vmvcAimStatResourcePoolEntry  21}

vmvcAimStatResourcePoolCPUUsageWarn OBJECT-TYPE
    SYNTAX INTEGER
    ACCESS read-write
    STATUS mandatory
    DESCRIPTION
        "Resource Pool CPU Warning Threshold"
    DEFVAL { 60 }
    ::= { vmvcAimStatResourcePoolEntry  22}

vmvcAimStatResourcePoolCPUUsageCrit OBJECT-TYPE
    SYNTAX INTEGER
    ACCESS read-write
    STATUS mandatory
    DESCRIPTION
        "Critical Threshold for Resource Pool CPU usage"
    DEFVAL { 80 }
    ::= { vmvcAimStatResourcePoolEntry  23}

vmvcAimStatResourcePoolCPUAlert OBJECT-TYPE
    SYNTAX INTEGER{
        warning-only(1),
        critical-only(2),
        both(3)    
        }
    ACCESS read-write
    STATUS mandatory
    DESCRIPTION
        "Resource Pool CPU Alert "
    DEFVAL { 3 }
    ::= { vmvcAimStatResourcePoolEntry  24}

vmvcAimStatResourcePoolCPUState OBJECT-TYPE
    SYNTAX INTEGER {
        unknown(1),
        ok(2),
        warning(3),
        critical(4)
    }
    ACCESS read-only
    STATUS mandatory
    DESCRIPTION
        " Resource Pool CPU State"
    ::= { vmvcAimStatResourcePoolEntry  25}

vmvcAimStatResourcePoolCPUReserveUsed OBJECT-TYPE
    SYNTAX INTEGER
    ACCESS read-only
    STATUS mandatory
    DESCRIPTION
        " Reserve CPU used for the resource pool."
    ::= { vmvcAimStatResourcePoolEntry  26}

vmvcAimStatResourcePoolCPUReserveUsedForVM OBJECT-TYPE
    SYNTAX INTEGER
    ACCESS read-only
    STATUS mandatory
    DESCRIPTION
        " CPU Reserve Used for running VM in this resource pool or any of its child resource pools"
    ::= { vmvcAimStatResourcePoolEntry  27}

vmvcAimStatResourcePoolCPUUnReserveForPool OBJECT-TYPE
    SYNTAX INTEGER
    ACCESS read-only
    STATUS mandatory
    DESCRIPTION
        " CPU UnReserved for a child resource pool "
    ::= { vmvcAimStatResourcePoolEntry  28}

vmvcAimStatResourcePoolCPUUnReserveForVM OBJECT-TYPE
    SYNTAX INTEGER
    ACCESS read-only
    STATUS mandatory
    DESCRIPTION
        " CPU UnReserved for a child Virtual Memory."
    ::= { vmvcAimStatResourcePoolEntry  29}

vmvcAimStatResourcePoolMemMaxUsage OBJECT-TYPE
    SYNTAX INTEGER
    ACCESS read-only
    STATUS mandatory
    DESCRIPTION
        " Maximum memory usage of Resource pool, in megabytes."
    ::= { vmvcAimStatResourcePoolEntry  30}

vmvcAimStatResourcePoolMemOverAllUsage OBJECT-TYPE
    SYNTAX INTEGER
    ACCESS read-only
    STATUS mandatory
    DESCRIPTION
        "Memory overall usage/consumption of all running child Virtual machines (in MB), including 
         virtual machines in the child resource pools."
    ::= { vmvcAimStatResourcePoolEntry  31}

vmvcAimStatResourcePoolMemUsagePct OBJECT-TYPE
    SYNTAX INTEGER
    ACCESS read-only
    STATUS mandatory
    DESCRIPTION
        "Resource Pool Memory usage Percentage."
    ::= { vmvcAimStatResourcePoolEntry  32}

vmvcAimStatResourcePoolMemUsageWarn OBJECT-TYPE
    SYNTAX INTEGER
    ACCESS read-write
    STATUS mandatory
    DESCRIPTION
        "Resource Pool Memory Warning Threshold."
    DEFVAL { 60 }
    ::= { vmvcAimStatResourcePoolEntry  33}

vmvcAimStatResourcePoolMemUsageCrit OBJECT-TYPE
    SYNTAX INTEGER
    ACCESS read-write
    STATUS mandatory
    DESCRIPTION
        "Resource Pool Memory Critical Threshold."
    DEFVAL { 80 }
    ::= { vmvcAimStatResourcePoolEntry  34}

vmvcAimStatResourcePoolMemAlert OBJECT-TYPE
    SYNTAX INTEGER{
        warning-only(1),
        critical-only(2),
        both(3)    
        }
    ACCESS read-write
    STATUS mandatory
    DESCRIPTION
        "Resource Pool Memory Alert "
    DEFVAL { 3 }
    ::= { vmvcAimStatResourcePoolEntry  35}

vmvcAimStatResourcePoolMemState OBJECT-TYPE
    SYNTAX INTEGER {
        unknown(1),
        ok(2),
        warning(3),
        critical(4)
    }
    ACCESS read-only
    STATUS mandatory
    DESCRIPTION
        " Resource Pool Memory State"
    ::= { vmvcAimStatResourcePoolEntry  36}

vmvcAimStatResourcePoolMemReserveUsed OBJECT-TYPE
    SYNTAX INTEGER
    ACCESS read-only
    STATUS mandatory
    DESCRIPTION
        " memory reserved for all the children of resource pool."
    ::= { vmvcAimStatResourcePoolEntry  37}

vmvcAimStatResourcePoolMemReserveUsedForVM OBJECT-TYPE
    SYNTAX INTEGER
    ACCESS read-only
    STATUS mandatory
    DESCRIPTION
        " reserved Memory used for running VM in this resource pool or any of its child resource pool."
    ::= { vmvcAimStatResourcePoolEntry  38}

vmvcAimStatResourcePoolMemUnReserveForPool OBJECT-TYPE
    SYNTAX INTEGER
    ACCESS read-only
    STATUS mandatory
    DESCRIPTION
        "memory unreserved for Resource pool "
    ::= { vmvcAimStatResourcePoolEntry  39}

vmvcAimStatResourcePoolMemUnReserveForVM OBJECT-TYPE
    SYNTAX INTEGER
    ACCESS read-only
    STATUS mandatory
    DESCRIPTION
        "memory unreserved for a child VM"
    ::= { vmvcAimStatResourcePoolEntry  40}

vmvcAimStatResourcePoolStatus OBJECT-TYPE
    SYNTAX INTEGER {
        gray(1),
        green(2),
        yellow(3),
        red(4)
    }
    ACCESS read-only
    STATUS mandatory
    DESCRIPTION
        "Resource Pool Status.It can be grey,green,red and yellow"
    ::= { vmvcAimStatResourcePoolEntry  41}

vmvcAimStatResourcePoolMonitor OBJECT-TYPE
    SYNTAX INTEGER{
        do-not-monitor(1),
        monitor(2)
        }
    ACCESS read-write
    STATUS mandatory
    DESCRIPTION
        "Flag to indicate whether Resource Pool to be monitered(2) or not(1) "
    DEFVAL { 2 }
    ::= { vmvcAimStatResourcePoolEntry  42}

vmvcAimStatResourcePoolAlert OBJECT-TYPE
    SYNTAX INTEGER{
        not-green-warning(1),
        not-green-critical(2)
        }
    ACCESS read-write
    STATUS mandatory
    DESCRIPTION
        "Resource Pool Alert whether warning or critical."
    DEFVAL { 2 }
    ::= { vmvcAimStatResourcePoolEntry  43}

vmvcAimStatResourcePoolState OBJECT-TYPE
    SYNTAX INTEGER {
        unknown(1),
        ok(2),
        warning(3),
        critical(4)
    }
    ACCESS read-only
    STATUS mandatory
    DESCRIPTION
        "Resource Pool State.It can be ok,warning or critical"
    ::= { vmvcAimStatResourcePoolEntry  44}

vmvcAimStatResourcePoolType OBJECT-TYPE
    SYNTAX INTEGER {
        vcCreatedResPool(1),
        userCreatedResPool(2),
        userCreatedvApp(3)
    }
    ACCESS read-only
    STATUS mandatory
    DESCRIPTION
        "The type of Resource Pool.  Possible values include vCenter-created ResPool (1),
         end-user-created ResPool (2), or end-user-created vApp (3)."
    ::= { vmvcAimStatResourcePoolEntry  45}

vmvcAimStatResourcePoolVCUID OBJECT-TYPE
    SYNTAX INTEGER
    ACCESS read-only
    STATUS mandatory
    DESCRIPTION
        "VC Instance SNMP UID where this Resource Pool resides."
    ::= { vmvcAimStatResourcePoolEntry 46}

vmvcAimStatResourcePoolVCName OBJECT-TYPE
    SYNTAX SnmpAdminString
    ACCESS read-only
    STATUS mandatory
    DESCRIPTION
        "VC Instance where this Resource Pool resides."
    ::= { vmvcAimStatResourcePoolEntry 47}

vmvcAimStatResourcePoolVCUUID OBJECT-TYPE
    SYNTAX SnmpAdminString
    ACCESS read-only
    STATUS mandatory
    DESCRIPTION
        "The vCenter-specific UUID where this Resource Pool resides."
    ::= { vmvcAimStatResourcePoolEntry 48}


-- *****************************************************************************
-- Status ResPool vApp Group
-- *****************************************************************************
vmvcAimStatVAppCount OBJECT-TYPE
    SYNTAX INTEGER
    ACCESS read-only
    STATUS mandatory
    DESCRIPTION
        "Number of vApps in vmvcAimStatVAppTable."
    ::= { vmvcAimStatResPoolGroup 3}

vmvcAimStatVAppTable OBJECT-TYPE
    SYNTAX SEQUENCE OF VmvcAimStatVAppRow
    ACCESS not-accessible
    STATUS mandatory
    DESCRIPTION
        "vApp extension table.  This table will have a subset of the Resource Pool table
         within it, as it only shows the vApp extension information for those Resource
         Pools which are also Vapps.  Correlation data between these two tables are:
            UID             ->  Consistent between both tables
            Index + VCName  ->  Consistent & Unique"
    ::= { vmvcAimStatResPoolGroup 4 }

vmvcAimStatVAppEntry OBJECT-TYPE
    SYNTAX VmvcAimStatVAppRow
    ACCESS not-accessible
    STATUS mandatory
    DESCRIPTION
        "The table entry."
    INDEX { vmvcAimStatVAppUID  }
    ::= { vmvcAimStatVAppTable 1 }

VmvcAimStatVAppRow ::=
    SEQUENCE {
        vmvcAimStatVAppUID                   INTEGER,
        vmvcAimStatVAppIndex                 SnmpAdminString,
        vmvcAimStatVAppName                  SnmpAdminString,
        vmvcAimStatVAppVCUID                 INTEGER,
        vmvcAimStatVAppVCName                SnmpAdminString,
        vmvcAimStatVAppParentVApp            SnmpAdminString,
        vmvcAimStatVAppOperatingStatus       INTEGER,
        vmvcAimStatVAppInstallBootRequired   INTEGER,
        vmvcAimStatVAppIpAllocationPolicy    INTEGER,
        vmvcAimStatVAppSupportedIpProtocol   SnmpAdminString,
        vmvcAimStatVAppIpProtocol            SnmpAdminString,
        vmvcAimStatVAppProductAppURL         SnmpAdminString,
        vmvcAimStatVAppProductVersion        SnmpAdminString,
        vmvcAimStatVAppProductFullVersion    SnmpAdminString,
        vmvcAimStatVAppProductName           SnmpAdminString,
        vmvcAimStatVAppProductURL            SnmpAdminString,
        vmvcAimStatVAppProductVendor         SnmpAdminString,
        vmvcAimStatVAppProductVendorURL      SnmpAdminString,
        vmvcAimStatVAppStartAction           INTEGER,
        vmvcAimStatVAppStartOrder            INTEGER,
        vmvcAimStatVAppStopAction            INTEGER,
        vmvcAimStatVAppVCUUID                SnmpAdminString
    }

vmvcAimStatVAppUID OBJECT-TYPE
    SYNTAX INTEGER (1..2147483647)
    ACCESS read-only
    STATUS mandatory
    DESCRIPTION
        "UID of the vApp"
    ::= { vmvcAimStatVAppEntry  1}

vmvcAimStatVAppIndex OBJECT-TYPE
    SYNTAX SnmpAdminString
    ACCESS read-only
    STATUS mandatory
    DESCRIPTION
        "Indentifier of the vApp"
    ::= { vmvcAimStatVAppEntry  2}

vmvcAimStatVAppName OBJECT-TYPE
    SYNTAX SnmpAdminString
    ACCESS read-only
    STATUS mandatory
    DESCRIPTION
        "Name of the vApp"
    ::= { vmvcAimStatVAppEntry  3}

vmvcAimStatVAppVCUID OBJECT-TYPE
    SYNTAX INTEGER
    ACCESS read-only
    STATUS mandatory
    DESCRIPTION
        "VC Instance SNMP UID where this vApp resides."
    ::= { vmvcAimStatVAppEntry  4}

vmvcAimStatVAppVCName OBJECT-TYPE
    SYNTAX SnmpAdminString
    ACCESS read-only
    STATUS mandatory
    DESCRIPTION
        "VC Instance where this vApp resides."
    ::= { vmvcAimStatVAppEntry  5}

vmvcAimStatVAppParentVApp OBJECT-TYPE
    SYNTAX SnmpAdminString
    ACCESS read-only
    STATUS mandatory
    DESCRIPTION
        "vApp (MOID) that this vApp is a primary member of."
    ::= { vmvcAimStatVAppEntry  6}

vmvcAimStatVAppOperatingStatus OBJECT-TYPE
    SYNTAX INTEGER{
        started(1),
        stopped(2),
        starting(3),
        stopping(4),
        notApplicable(5)
    }
    ACCESS read-only
    STATUS mandatory
    DESCRIPTION
        "Inidicates the current execution status of this vApp. notApplicable indicates that
         this vApp has no children, so the operating status cannot be validly specified."
    ::= { vmvcAimStatVAppEntry  7}

vmvcAimStatVAppInstallBootRequired OBJECT-TYPE
    SYNTAX INTEGER{
        false(1),
        true(2)
    }
    ACCESS read-only
    STATUS mandatory
    DESCRIPTION
        "Indicates whether one or more VMs in this vApp require a reboot to finish installation. "
    ::= { vmvcAimStatVAppEntry  8}

vmvcAimStatVAppIpAllocationPolicy OBJECT-TYPE
    SYNTAX INTEGER{
        fixed(1),
        transient(2),
        dhcp(3)
    }
    ACCESS read-only
    STATUS mandatory
    DESCRIPTION
        "Specifies how IP allocation should be managed by the VI platform.
            fixed     - IP addresses are manually configured. No automatic allocation is performed.
            transient - IP addresses are automatically allocated from the vCenter managed IP network range
                        at power-on, and released at power-off.
            dhcp      - A DHCP server is used for IP allocation."
    ::= { vmvcAimStatVAppEntry  9}

vmvcAimStatVAppSupportedIpProtocol OBJECT-TYPE
    SYNTAX SnmpAdminString
    ACCESS read-only
    STATUS mandatory
    DESCRIPTION
        "Specifies the IP protocols supported by the guest software."
    ::= { vmvcAimStatVAppEntry 10}

vmvcAimStatVAppIpProtocol OBJECT-TYPE
    SYNTAX SnmpAdminString
    ACCESS read-only
    STATUS mandatory
    DESCRIPTION
        "Specifies the chosen IP protocol for this deployment."
    ::= { vmvcAimStatVAppEntry 11}

vmvcAimStatVAppProductAppURL OBJECT-TYPE
    SYNTAX SnmpAdminString
    ACCESS read-only
    STATUS mandatory
    DESCRIPTION
        "Entry point URL for application."
    ::= { vmvcAimStatVAppEntry 12}

vmvcAimStatVAppProductVersion OBJECT-TYPE
    SYNTAX SnmpAdminString
    ACCESS read-only
    STATUS mandatory
    DESCRIPTION
        "Short version of the product, e.g., 1.0."
    ::= { vmvcAimStatVAppEntry 13}

vmvcAimStatVAppProductFullVersion OBJECT-TYPE
    SYNTAX SnmpAdminString
    ACCESS read-only
    STATUS mandatory
    DESCRIPTION
        "Full-version of the product, e.g., 1.0-build 12323."
    ::= { vmvcAimStatVAppEntry 14}

vmvcAimStatVAppProductName OBJECT-TYPE
    SYNTAX SnmpAdminString
    ACCESS read-only
    STATUS mandatory
    DESCRIPTION
        "Name of the product."
    ::= { vmvcAimStatVAppEntry 15}

vmvcAimStatVAppProductURL OBJECT-TYPE
    SYNTAX SnmpAdminString
    ACCESS read-only
    STATUS mandatory
    DESCRIPTION
        "Product Homepage URL."
    ::= { vmvcAimStatVAppEntry 16}

vmvcAimStatVAppProductVendor OBJECT-TYPE
    SYNTAX SnmpAdminString
    ACCESS read-only
    STATUS mandatory
    DESCRIPTION
        "Product Vendor."
    ::= { vmvcAimStatVAppEntry 17}

vmvcAimStatVAppProductVendorURL OBJECT-TYPE
    SYNTAX SnmpAdminString
    ACCESS read-only
    STATUS mandatory
    DESCRIPTION
        "Vendor Homepage URL."
    ::= { vmvcAimStatVAppEntry 18}

vmvcAimStatVAppStartAction OBJECT-TYPE
    SYNTAX INTEGER{
        none(1),
        powerOn(2)
    }
    ACCESS read-only
    STATUS mandatory
    DESCRIPTION
        "Start action for this vApp. Valid settings are none or powerOn. If set to none, then the
         entity does not participate in auto-start."
    ::= { vmvcAimStatVAppEntry 19}

vmvcAimStatVAppStartOrder OBJECT-TYPE
    SYNTAX INTEGER
    ACCESS read-only
    STATUS mandatory
    DESCRIPTION
        "Specifies the start order for this vApp. Entities are started from lower numbers to
         higher-numbers and reverse on shutdown. Multiple entities with the same start-order can
         be started in parallel and the order is unspecified. This value must be 0 or higher."
    ::= { vmvcAimStatVAppEntry 20}

vmvcAimStatVAppStopAction OBJECT-TYPE
    SYNTAX INTEGER{
        none(1),
        powerOff(2)
    }
    ACCESS read-only
    STATUS mandatory
    DESCRIPTION
        "Stop action for the vApp. Can be set to none or powerOff. If set to none,
         then the entity does not participate in auto-stop."
    ::= { vmvcAimStatVAppEntry 21}
    
vmvcAimStatVAppVCUUID OBJECT-TYPE
    SYNTAX SnmpAdminString
    ACCESS read-only
    STATUS mandatory
    DESCRIPTION
        "The vCenter-specific UUID where this vApp resides."
    ::= { vmvcAimStatVAppEntry  22}


-- *****************************************************************************
-- Status Virtual Machine Group
-- *****************************************************************************
vmvcAimStatVMCount OBJECT-TYPE
    SYNTAX INTEGER
    ACCESS read-only
    STATUS mandatory
    DESCRIPTION
        "Number of VMs in vmvcAimStatVMTable."
    ::= { vmvcAimStatVMGroup 1}

vmvcAimStatVMTable OBJECT-TYPE
    SYNTAX SEQUENCE OF VmvcAimStatVMRow
    ACCESS not-accessible
    STATUS mandatory
    DESCRIPTION
        "VM table."
    ::= { vmvcAimStatVMGroup 2 }

vmvcAimStatVMEntry OBJECT-TYPE
    SYNTAX VmvcAimStatVMRow
    ACCESS not-accessible
    STATUS mandatory
    DESCRIPTION
        "The table entry."
    INDEX { vmvcAimStatVMUID }
    ::= { vmvcAimStatVMTable 1 }

VmvcAimStatVMRow ::=
    SEQUENCE {
        vmvcAimStatVMUID                        INTEGER,
        vmvcAimStatVMIndex                      SnmpAdminString,
        vmvcAimStatVMName                       SnmpAdminString,
        vmvcAimStatVMDesc                       SnmpAdminString,
        vmvcAimStatVMConfigFileName             SnmpAdminString,
        vmvcAimStatVMId                         SnmpAdminString,
        vmvcAimStatVMResourcePoolId             SnmpAdminString,
        vmvcAimStatVMResourcePoolName           SnmpAdminString,
        vmvcAimStatVMFullPath                   SnmpAdminString,
        vmvcAimStatVMHostName                   SnmpAdminString,
        vmvcAimStatVMHostID                     SnmpAdminString,
        vmvcAimStatVMClusterName                SnmpAdminString,
        vmvcAimStatVMParentID                   SnmpAdminString,
        vmvcAimStatVMDatacenterName             SnmpAdminString,
        vmvcAimStatVMVMFolderName               SnmpAdminString,
        vmvcAimStatVMIPv4Address                SnmpAdminString,
        vmvcAimStatVMIPv6Address                SnmpAdminString,
        vmvcAimStatVMGuestOS                    SnmpAdminString,
        vmvcAimStatVMUpTime                     TimeTicks,
        vmvcAimStatVMMonitor                    INTEGER,
        vmvcAimStatVMPowerStatus                INTEGER,
        vmvcAimStatVMAlertPowerOffStatus        INTEGER,
        vmvcAimStatVMPowerState                 INTEGER,
        vmvcAimStatVMHeartbeat                  INTEGER,
        vmvcAimStatVMAlertHeartbeatLoss         INTEGER,
        vmvcAimStatVMHeartbeatState             INTEGER,
        vmvcAimStatVMCPUSharesAssigned          INTEGER, 
        vmvcAimStatVMCPUSharesActive            INTEGER,
        vmvcAimStatVMCPUSharesPercentage        INTEGER,
        vmvcAimStatVMCPUSharesWarnThreshold     INTEGER,
        vmvcAimStatVMCPUSharesCritThreshold     INTEGER,
        vmvcAimStatVMCPUAlert                   INTEGER,
        vmvcAimStatVMCPUState                   INTEGER,
        vmvcAimStatVMCPUAffinity                SnmpAdminString,
        vmvcAimStatVMMemorySharesAssigned       INTEGER,
        vmvcAimStatVMMemoryMin                  INTEGER,
        vmvcAimStatVMMemoryMax                  INTEGER,
        vmvcAimStatVMMemoryActual               INTEGER,
        vmvcAimStatVMMemoryActive               INTEGER,
        vmvcAimStatVMMemoryPercentage           INTEGER,
        vmvcAimStatVMMemoryWarnThreshold        INTEGER,
        vmvcAimStatVMMemoryCritThreshold        INTEGER, 
        vmvcAimStatVMMemoryAlert                INTEGER,
        vmvcAimStatVMMemoryState                INTEGER,
        vmvcAimStatVMMemoryCtl                  INTEGER,
        vmvcAimStatVMMemorySwapped              INTEGER,
        vmvcAimStatVMMemoryShared               INTEGER,
        vmvcAimStatVMMemoryOverhead             INTEGER,
        vmvcAimStatVMDatastore                  SnmpAdminString,
        vmvcAimStatVMNetwork                    SnmpAdminString,
        vmvcAimStatVMPctReady                   INTEGER,
        vmvcAimStatVMPctReadyWarnThreshold      INTEGER,
        vmvcAimStatVMPctReadyCritThreshold      INTEGER,
        vmvcAimStatVMPctReadyAlert              INTEGER,
        vmvcAimStatVMPctReadyState              INTEGER,
        vmvcAimStatVMCPUMonitor                 INTEGER,
        vmvcAimStatVMCPULagSetting              INTEGER,
        vmvcAimStatVMCPULagValue                INTEGER,
        vmvcAimStatVMCPUAggregateStatus         INTEGER,
        vmvcAimStatVMMemoryMonitor              INTEGER,
        vmvcAimStatVMBehaviour                  SnmpAdminString,
        vmvcAimStatVMConnectionState            INTEGER,
        vmvcAimStatVMOSState                    INTEGER,
        vmvcAimStatVMNumConnectedUsers          INTEGER,
        vmvcAimStatVMCPUCount                   INTEGER,
        vmvcAimStatVMCPUWaitSec                 INTEGER,
        vmvcAimStatVMCPUExtraSec                INTEGER,
        vmvcAimStatVMCPUUsedSec                 INTEGER,
        vmvcAimStatVMCPUConfiguredMin           INTEGER,
        vmvcAimStatVMCPUConfiguredMax           INTEGER,
        vmvcAimStatVMCPUShares                  INTEGER,
        vmvcAimStatVMCPUReadyPercent            INTEGER,
        vmvcAimStatVMCPUAllocationPercent       INTEGER,
        vmvcAimStatVMAvailableMemory            INTEGER,
        vmvcAimStatVMUsedMemory                 INTEGER,
        vmvcAimStatVMFreeMemory                 INTEGER,
        vmvcAimStatVMConfiguredMemory           INTEGER,
        vmvcAimStatVMMemorySize                 INTEGER,
        vmvcAimStatVMMemoryBallonTarget         INTEGER,
        vmvcAimStatVMToolsStatus                INTEGER,
        vmvcAimStatVMPhyName                    SnmpAdminString,
        vmvcAimStatVMCPUReservation             INTEGER,
        vmvcAimStatVMMemoryReservation          INTEGER,
        vmvcAimStatVMCPUHotPlug                 INTEGER,
        vmvcAimStatVMMemoryHotAdd               INTEGER,
        vmvcAimStatVMMemoryHotAddIncrement      Gauge,
        vmvcAimStatVMMemoryHotAddLimit          Gauge,    
        vmvcAimStatVMSyncTimeWithHost           INTEGER,            
        vmvcAimStatVMVCUID                      INTEGER,
        vmvcAimStatVMVCName                     SnmpAdminString,
        vmvcAimStatVMFaultToleranceStatus       INTEGER,
        vmvcAimStatVMFTActivityState            INTEGER,
        vmvcAimStatVMFaultToleranceRole         INTEGER,
        vmvcAimStatVMFTSiblingIndex             SnmpAdminString,
        vmvcAimStatVMFTSiblingHostIndex         SnmpAdminString,
        vmvcAimStatVMFTSiblingHostName          SnmpAdminString,
        vmvcAimStatVMFTSiblingHostUID           INTEGER,
        vmvcAimStatVMFTTotalSiblingCPU          INTEGER,
        vmvcAimStatVMFTTotalSiblingMemory       INTEGER,
        vmvcAimStatVMTotalHostMemoryUsage       INTEGER,
        vmvcAimStatVMVCUUID                     SnmpAdminString
    }

vmvcAimStatVMUID OBJECT-TYPE
    SYNTAX INTEGER (1..2147483647)
    ACCESS read-only
    STATUS mandatory
    DESCRIPTION
        "UID of the VM"
    ::= { vmvcAimStatVMEntry  1}

vmvcAimStatVMIndex OBJECT-TYPE
    SYNTAX SnmpAdminString
    ACCESS read-only
    STATUS mandatory
    DESCRIPTION
        "Moid of the VM"
    ::= { vmvcAimStatVMEntry  2}

vmvcAimStatVMName OBJECT-TYPE
    SYNTAX SnmpAdminString
    ACCESS read-only
    STATUS mandatory
    DESCRIPTION
        "VirtualMachine Display Name"
    ::= { vmvcAimStatVMEntry  3}

vmvcAimStatVMDesc OBJECT-TYPE
    SYNTAX SnmpAdminString
    ACCESS read-write
    STATUS mandatory
    DESCRIPTION
        "VirtualMachine description, stored locally within AIM."
    ::= { vmvcAimStatVMEntry  4}

vmvcAimStatVMConfigFileName OBJECT-TYPE
    SYNTAX SnmpAdminString
    ACCESS read-only
    STATUS mandatory
    DESCRIPTION
        "Complete path of the VMs configuration file."
    ::= { vmvcAimStatVMEntry  5}

vmvcAimStatVMId OBJECT-TYPE
    SYNTAX SnmpAdminString
    ACCESS read-only
    STATUS mandatory
    DESCRIPTION
        "VirtualMachine  MOID"
    ::= { vmvcAimStatVMEntry  6}

vmvcAimStatVMResourcePoolId OBJECT-TYPE
    SYNTAX SnmpAdminString
    ACCESS read-only
    STATUS mandatory
    DESCRIPTION
        "MOID of parent ResourcePool"
    ::= { vmvcAimStatVMEntry  7}

vmvcAimStatVMResourcePoolName OBJECT-TYPE
    SYNTAX SnmpAdminString
    ACCESS read-only
    STATUS mandatory
    DESCRIPTION
        "Name of the resourcepool"
    ::= { vmvcAimStatVMEntry  8}

vmvcAimStatVMFullPath OBJECT-TYPE
    SYNTAX SnmpAdminString
    ACCESS read-only
    STATUS mandatory
    DESCRIPTION
        "Full path to the VM. Related to VC Tree."
    ::= { vmvcAimStatVMEntry  9}

vmvcAimStatVMHostName OBJECT-TYPE
    SYNTAX SnmpAdminString
    ACCESS read-only
    STATUS mandatory
    DESCRIPTION
        "Host name on which VM is running"
    ::= { vmvcAimStatVMEntry  10}

vmvcAimStatVMHostID OBJECT-TYPE
    SYNTAX SnmpAdminString
    ACCESS read-only
    STATUS mandatory
    DESCRIPTION
        "Host moid on which VM is running"
    ::= { vmvcAimStatVMEntry  11}

vmvcAimStatVMClusterName OBJECT-TYPE
    SYNTAX SnmpAdminString
    ACCESS read-only
    STATUS mandatory
    DESCRIPTION
        "If the VM host belongs to a cluster, then name of the cluster"
    ::= { vmvcAimStatVMEntry  12}

vmvcAimStatVMParentID    OBJECT-TYPE
    SYNTAX SnmpAdminString
    ACCESS read-only
    STATUS mandatory
    DESCRIPTION
        "If VM belongs to a user defined respool then resource pool id else host id"
    ::= { vmvcAimStatVMEntry  13}

vmvcAimStatVMDatacenterName OBJECT-TYPE
    SYNTAX SnmpAdminString
    ACCESS read-only
    STATUS mandatory
    DESCRIPTION
        "Name of the datacenter this VM belongs to"
    ::= { vmvcAimStatVMEntry  14}

vmvcAimStatVMVMFolderName OBJECT-TYPE
    SYNTAX SnmpAdminString
    ACCESS read-only
    STATUS mandatory
    DESCRIPTION
        "Name of the folder VM belongs to"
    ::= { vmvcAimStatVMEntry  15}

vmvcAimStatVMIPv4Address OBJECT-TYPE
    SYNTAX SnmpAdminString (SIZE(0..1024))
    ACCESS read-only
    STATUS mandatory
    DESCRIPTION
        "IP address of the VM in IPv4 format"
    ::= { vmvcAimStatVMEntry  16}

vmvcAimStatVMIPv6Address OBJECT-TYPE
    SYNTAX SnmpAdminString (SIZE(0..2048))
    ACCESS read-only
    STATUS mandatory
    DESCRIPTION
        "IP address of the VM in IPv6 format"
    ::= { vmvcAimStatVMEntry  17}

vmvcAimStatVMGuestOS OBJECT-TYPE
    SYNTAX SnmpAdminString
    ACCESS read-only
    STATUS mandatory
    DESCRIPTION
        " Guest operating system name of VM"
    ::= { vmvcAimStatVMEntry  18}

vmvcAimStatVMUpTime OBJECT-TYPE
    SYNTAX TimeTicks
    ACCESS read-only
    STATUS mandatory
    DESCRIPTION
        " The timestamp when the virtual machine was most recently powered on."
    ::= { vmvcAimStatVMEntry  19}

vmvcAimStatVMMonitor OBJECT-TYPE
    SYNTAX INTEGER{
        do-not-monitor(1),
        monitor(2)
        }
    ACCESS read-write
    STATUS mandatory
    DESCRIPTION
        "Flag inidicating whether the virtual machine has to be monitored(2) or not(1) "
    DEFVAL { 2 }
    ::= { vmvcAimStatVMEntry  20}

vmvcAimStatVMPowerStatus OBJECT-TYPE
    SYNTAX INTEGER {
        poweredOff(1),
        poweredOn(2),
        suspended(3)
    }
    ACCESS read-only
    STATUS mandatory
    DESCRIPTION
        "The current power status of the virtual machine."
    ::= { vmvcAimStatVMEntry  21}

vmvcAimStatVMAlertPowerOffStatus OBJECT-TYPE
    SYNTAX INTEGER{
        off-warning(1),
        off-critical(2),
        off-normal(3)
        }
    ACCESS read-write
    STATUS mandatory
    DESCRIPTION
        "VM Poweroff status alert."
    DEFVAL { 3 }
    ::= { vmvcAimStatVMEntry  22}

vmvcAimStatVMPowerState OBJECT-TYPE
    SYNTAX INTEGER {
        unknown(1),
        ok(2),
        warning(3),
        critical(4)
    }
    ACCESS read-only
    STATUS mandatory
    DESCRIPTION
        "The current power state of the virtual machine. "
    ::= { vmvcAimStatVMEntry  23}

vmvcAimStatVMHeartbeat OBJECT-TYPE
    SYNTAX INTEGER {
        gray(1),
        green(2),
        yellow(3),
        red(4)
    }
    ACCESS read-only
    STATUS mandatory
    DESCRIPTION
        " heart beat"
    ::= { vmvcAimStatVMEntry  24}

vmvcAimStatVMAlertHeartbeatLoss OBJECT-TYPE
    SYNTAX INTEGER{
        no-heartbeat-warning(1),
        no-heartbeat-critical(2),
        no-heartbeat-ok(3)
        }
    ACCESS read-write
    STATUS mandatory
    DESCRIPTION
        "VM Heartbeat Loss alert.  Setting to no-heartbeat-ok(3) effectively
         disables the Heartbeat monitoring."
    DEFVAL { 2 }
    ::= { vmvcAimStatVMEntry  25}

vmvcAimStatVMHeartbeatState OBJECT-TYPE
    SYNTAX INTEGER {
        unknown(1),
        ok(2),
        warning(3),
        critical(4)
    }
    ACCESS read-only
    STATUS mandatory
    DESCRIPTION
        "VM Heartbeat State."
    ::= { vmvcAimStatVMEntry  26}

vmvcAimStatVMCPUSharesAssigned OBJECT-TYPE
    SYNTAX INTEGER
    ACCESS read-only
    STATUS mandatory
    DESCRIPTION
        " The number of CPU Shares allocated of VM"
    ::= { vmvcAimStatVMEntry  27}

vmvcAimStatVMCPUSharesActive OBJECT-TYPE
    SYNTAX INTEGER
    ACCESS read-only
    STATUS mandatory
    DESCRIPTION
        "Total amount of Host CPU utilization thias VM is using (in MHz).  This is different from the
         amount of CPU Utilization being used within the Guest O/S layer of the VM, and can be used for
         capacity planning statistics, etc."
    ::= { vmvcAimStatVMEntry  28}

vmvcAimStatVMCPUSharesPercentage OBJECT-TYPE
    SYNTAX INTEGER
    ACCESS read-only
    STATUS mandatory
    DESCRIPTION
        "Percentage of CPU performance statistics of VM."
    ::= { vmvcAimStatVMEntry  29}

vmvcAimStatVMCPUSharesWarnThreshold OBJECT-TYPE
    SYNTAX INTEGER
    ACCESS read-write
    STATUS mandatory
    DESCRIPTION
        "VM CPU Shares Warning Threshold"
    DEFVAL { 60 }
    ::= { vmvcAimStatVMEntry  30}

vmvcAimStatVMCPUSharesCritThreshold OBJECT-TYPE
    SYNTAX INTEGER
    ACCESS read-write
    STATUS mandatory
    DESCRIPTION
        "VM CPU Shares Critical Threshold "
    DEFVAL { 80 }
    ::= { vmvcAimStatVMEntry  31}

vmvcAimStatVMCPUAlert OBJECT-TYPE
    SYNTAX INTEGER{
        warning(1),
        critical(2),
        both(3)
        }
    ACCESS read-write
    STATUS mandatory
    DESCRIPTION
        " VM CPU usage Alert. That may be warning,critical or both."
    DEFVAL { 3 }
    ::= { vmvcAimStatVMEntry  32}

vmvcAimStatVMCPUState OBJECT-TYPE
    SYNTAX INTEGER {
        unknown(1),
        ok(2),
        warning(3),
        critical(4)
    }
    ACCESS read-only
    STATUS mandatory
    DESCRIPTION
        "status of VM CPU State "
    ::= { vmvcAimStatVMEntry  33}

vmvcAimStatVMCPUAffinity OBJECT-TYPE
    SYNTAX SnmpAdminString
    ACCESS read-only
    STATUS mandatory
    DESCRIPTION
        "status of VM CPU Affinity "
    ::= { vmvcAimStatVMEntry  34}

vmvcAimStatVMMemorySharesAssigned OBJECT-TYPE
    SYNTAX INTEGER
    ACCESS read-only
    STATUS mandatory
    DESCRIPTION
        "status of VM Memory Shares Assigned "
    ::= { vmvcAimStatVMEntry  35}

vmvcAimStatVMMemoryMin OBJECT-TYPE
    SYNTAX INTEGER
    ACCESS read-only
    STATUS mandatory
    DESCRIPTION
        " Current lower-bound on memory usage of VM, in megabytes."
    ::= { vmvcAimStatVMEntry  36}

vmvcAimStatVMMemoryMax OBJECT-TYPE
    SYNTAX INTEGER
    ACCESS read-only
    STATUS mandatory
    DESCRIPTION
        "Current upper-bound on memory usage of VM, in megabytes."
    ::= { vmvcAimStatVMEntry  37}

vmvcAimStatVMMemoryActual OBJECT-TYPE
    SYNTAX INTEGER
    ACCESS read-only
    STATUS mandatory
    DESCRIPTION
        "VM Memory size of the virtual machine, in megabytes."
    ::= { vmvcAimStatVMEntry  38}

vmvcAimStatVMMemoryActive OBJECT-TYPE
    SYNTAX INTEGER
    ACCESS read-only
    STATUS mandatory
    DESCRIPTION
        "VM Active Memory Status, in megabytes."
    ::= { vmvcAimStatVMEntry  39}

vmvcAimStatVMMemoryPercentage OBJECT-TYPE
    SYNTAX INTEGER
    ACCESS read-only
    STATUS mandatory
    DESCRIPTION
        " status of Vm memory Percentage."
    ::= { vmvcAimStatVMEntry  40}

vmvcAimStatVMMemoryWarnThreshold OBJECT-TYPE
    SYNTAX INTEGER
    ACCESS read-write
    STATUS mandatory
    DESCRIPTION
        "VM Memory Warning Threshold "
    DEFVAL { 60 }
    ::= { vmvcAimStatVMEntry  41}

vmvcAimStatVMMemoryCritThreshold OBJECT-TYPE
    SYNTAX INTEGER
    ACCESS read-write
    STATUS mandatory
    DESCRIPTION
        " VM Memory critical Threshold "
    DEFVAL { 80 }
    ::= { vmvcAimStatVMEntry  42}

vmvcAimStatVMMemoryAlert OBJECT-TYPE
    SYNTAX INTEGER{
        warning(1),
        critical(2),
        both(3)
        }
    ACCESS read-write
    STATUS mandatory
    DESCRIPTION
        "VM memory Alert. That may be warning, critical or both."
    DEFVAL { 3 }
    ::= { vmvcAimStatVMEntry  43}

vmvcAimStatVMMemoryState OBJECT-TYPE
    SYNTAX INTEGER {
        unknown(1),
        ok(2),
        warning(3),
        critical(4)
    }
    ACCESS read-only
    STATUS mandatory
    DESCRIPTION
        "VM memory state "
    ::= { vmvcAimStatVMEntry  44}

vmvcAimStatVMMemoryCtl OBJECT-TYPE
    SYNTAX INTEGER
    ACCESS read-only
    STATUS mandatory
    DESCRIPTION
        "VM memory control, in megabytes."
    ::= { vmvcAimStatVMEntry  45}

vmvcAimStatVMMemorySwapped OBJECT-TYPE
    SYNTAX INTEGER
    ACCESS read-only
    STATUS mandatory
    DESCRIPTION
        "swapped VM memory, in megabytes."
    ::= { vmvcAimStatVMEntry  46}

vmvcAimStatVMMemoryShared OBJECT-TYPE
    SYNTAX INTEGER
    ACCESS read-only
    STATUS mandatory
    DESCRIPTION
        "shared VM memory, in megabytes."
    ::= { vmvcAimStatVMEntry  47}

vmvcAimStatVMMemoryOverhead OBJECT-TYPE
    SYNTAX INTEGER
    ACCESS read-only
    STATUS mandatory
    DESCRIPTION
        "VM Memory overhead, in megabytes."
    ::= { vmvcAimStatVMEntry  48}

vmvcAimStatVMDatastore OBJECT-TYPE
    SYNTAX SnmpAdminString
    ACCESS read-only
    STATUS mandatory
    DESCRIPTION
        " The Datastore the VM is associated with."
    ::= { vmvcAimStatVMEntry  49}

vmvcAimStatVMNetwork OBJECT-TYPE
    SYNTAX SnmpAdminString
    ACCESS read-only
    STATUS mandatory
    DESCRIPTION
        " The Network VM is associated with"
    ::= { vmvcAimStatVMEntry  50}

vmvcAimStatVMPctReady OBJECT-TYPE
    SYNTAX INTEGER
    ACCESS read-only
    STATUS mandatory
    DESCRIPTION
        "percentage of time that the VM was ready but could 
                           not get scheduled to run on a physical CPU. "
    ::= { vmvcAimStatVMEntry  51}

vmvcAimStatVMPctReadyWarnThreshold OBJECT-TYPE
    SYNTAX INTEGER
    ACCESS read-write
    STATUS mandatory
    DESCRIPTION
        "Warning threshold for the VMPctReadyWarnThreshold variable."
    DEFVAL { 5 }
    ::= { vmvcAimStatVMEntry  52}

vmvcAimStatVMPctReadyCritThreshold OBJECT-TYPE
    SYNTAX INTEGER
    ACCESS read-write
    STATUS mandatory
    DESCRIPTION
        "critical threshold for the VMPctReadyCritThreshold variable."
    DEFVAL { 15 }
    ::= { vmvcAimStatVMEntry  53}

vmvcAimStatVMPctReadyAlert OBJECT-TYPE
    SYNTAX INTEGER{
        warning(1),
        critical(2),
        both(3)
        }
    ACCESS read-write
    STATUS mandatory
    DESCRIPTION
        " The level of alert to raise, That may be warning, critical or both."
    DEFVAL { 3 }
    ::= { vmvcAimStatVMEntry  54}

vmvcAimStatVMPctReadyState OBJECT-TYPE
    SYNTAX INTEGER {
        unknown(1),
        ok(2),
        warning(3),
        critical(4)
    }
    ACCESS read-only
    STATUS mandatory
    DESCRIPTION
        "The percent ready state of the virtual machine. "
    ::= { vmvcAimStatVMEntry  55}

vmvcAimStatVMCPUMonitor OBJECT-TYPE
    SYNTAX INTEGER{
        do-not-monitor(1),
        monitor(2)
        }
    ACCESS read-write
    STATUS mandatory
    DESCRIPTION
        "Flag inidicating whether the virtual machine CPU has to be monitored(2) or not(1) "
    DEFVAL { 2 }
    ::= { vmvcAimStatVMEntry  56}

vmvcAimStatVMCPULagSetting OBJECT-TYPE
    SYNTAX INTEGER
    ACCESS read-write
    STATUS mandatory
    DESCRIPTION 
        "VM CPU lag setting "
    DEFVAL { 3 }
    ::= { vmvcAimStatVMEntry  57}

vmvcAimStatVMCPULagValue OBJECT-TYPE
    SYNTAX INTEGER
    ACCESS read-only
    STATUS mandatory
    DESCRIPTION
        " VM CPU lag Value "
    ::= { vmvcAimStatVMEntry  58}

vmvcAimStatVMCPUAggregateStatus OBJECT-TYPE
    SYNTAX INTEGER {
        unknown(1),
        ok(2),
        warning(3),
        critical(4)
    }
    ACCESS read-only
    STATUS mandatory
    DESCRIPTION
        "VM CPU Aggregate Status "
    ::= { vmvcAimStatVMEntry  59}

vmvcAimStatVMMemoryMonitor OBJECT-TYPE
    SYNTAX INTEGER{
        do-not-monitor(1),
        monitor(2)
        }
    ACCESS read-write
    STATUS mandatory
    DESCRIPTION
        "Flag inidicating whether the virtual machine Memory has to be monitored(2) or not(1) "
    DEFVAL { 2 }
    ::= { vmvcAimStatVMEntry  60}

vmvcAimStatVMBehaviour    OBJECT-TYPE
    SYNTAX SnmpAdminString
    ACCESS read-only
    STATUS mandatory
    DESCRIPTION
        "DR VM Behaviour"
    ::= { vmvcAimStatVMEntry  61}

vmvcAimStatVMConnectionState OBJECT-TYPE
    SYNTAX INTEGER {
        notConnected(1),
        connected(2),
        orphaned(3)
    }
    ACCESS read-only
    STATUS mandatory
    DESCRIPTION
        "VM Connection State"
    ::= { vmvcAimStatVMEntry  62}

vmvcAimStatVMOSState OBJECT-TYPE
    SYNTAX INTEGER {
        running(1),
        shuttingdown(2),
        resetting(3),
        standby(4),
        notrunning(5),
        unknown(6)
    }
    ACCESS read-only
    STATUS mandatory
    DESCRIPTION
        "VM OS State"
    ::= { vmvcAimStatVMEntry  63}

vmvcAimStatVMNumConnectedUsers OBJECT-TYPE
    SYNTAX INTEGER 
    ACCESS read-only
    STATUS mandatory
    DESCRIPTION
        "Number of connected users on this VM"
    ::= { vmvcAimStatVMEntry  64}
    
vmvcAimStatVMCPUCount OBJECT-TYPE
    SYNTAX INTEGER
    ACCESS read-only
    STATUS mandatory
    DESCRIPTION
        "Number of CPU's on this VM"
    ::= { vmvcAimStatVMEntry  65}
    
vmvcAimStatVMCPUWaitSec OBJECT-TYPE
    SYNTAX INTEGER
    ACCESS read-only
    STATUS mandatory
    DESCRIPTION
        "VM CPU wait Percentage"
    ::= { vmvcAimStatVMEntry  66}
    
vmvcAimStatVMCPUExtraSec OBJECT-TYPE
    SYNTAX INTEGER
    ACCESS read-only
    STATUS mandatory
    DESCRIPTION
        "VM CPU extra Percentage"
    ::= { vmvcAimStatVMEntry  67}
    
vmvcAimStatVMCPUUsedSec OBJECT-TYPE
    SYNTAX INTEGER
    ACCESS read-only
    STATUS mandatory
    DESCRIPTION
        "VM CPU used Percentage"
    ::= { vmvcAimStatVMEntry  68}
    
vmvcAimStatVMCPUConfiguredMin OBJECT-TYPE
    SYNTAX INTEGER
    ACCESS read-only
    STATUS mandatory
    DESCRIPTION
        "Minimum CPU configured on VM"
    ::= { vmvcAimStatVMEntry  69}
    
vmvcAimStatVMCPUConfiguredMax OBJECT-TYPE
    SYNTAX INTEGER
    ACCESS read-only
    STATUS mandatory
    DESCRIPTION
        "Maximum CPU configured on VM"
    ::= { vmvcAimStatVMEntry  70}
    
vmvcAimStatVMCPUShares OBJECT-TYPE
    SYNTAX INTEGER
    ACCESS read-only
    STATUS mandatory
    DESCRIPTION
        "VM CPU shares"
    ::= { vmvcAimStatVMEntry  71}
    
vmvcAimStatVMCPUReadyPercent OBJECT-TYPE
    SYNTAX INTEGER
    ACCESS read-only
    STATUS mandatory
    DESCRIPTION
        "VM CPU Ready Percent"
    ::= { vmvcAimStatVMEntry  72}
    
vmvcAimStatVMCPUAllocationPercent OBJECT-TYPE
    SYNTAX INTEGER
    ACCESS read-only
    STATUS mandatory
    DESCRIPTION
        "VM CPU allocation percent"
    ::= { vmvcAimStatVMEntry  73}
    
vmvcAimStatVMAvailableMemory OBJECT-TYPE
    SYNTAX INTEGER
    ACCESS read-only
    STATUS mandatory
    DESCRIPTION
        "VM Available memory in MB"
    ::= { vmvcAimStatVMEntry  74}
    
vmvcAimStatVMUsedMemory OBJECT-TYPE
    SYNTAX INTEGER
    ACCESS read-only
    STATUS mandatory
    DESCRIPTION
        "VM used memory in MB"
    ::= { vmvcAimStatVMEntry  75}
    
vmvcAimStatVMFreeMemory OBJECT-TYPE
    SYNTAX INTEGER
    ACCESS read-only
    STATUS mandatory
    DESCRIPTION
        "VM free memory in MB"
    ::= { vmvcAimStatVMEntry  76}
    
vmvcAimStatVMConfiguredMemory OBJECT-TYPE
    SYNTAX INTEGER
    ACCESS read-only
    STATUS mandatory
    DESCRIPTION
        "VM configured memory in MB"
    ::= { vmvcAimStatVMEntry  77}
    
vmvcAimStatVMMemorySize OBJECT-TYPE
    SYNTAX INTEGER
    ACCESS read-only
    STATUS mandatory
    DESCRIPTION
        "VM memory size in MB"
    ::= { vmvcAimStatVMEntry  78}
    
vmvcAimStatVMMemoryBallonTarget OBJECT-TYPE
    SYNTAX INTEGER
    ACCESS read-only
    STATUS mandatory
    DESCRIPTION
        "VM memory ballon in MB"
    ::= { vmvcAimStatVMEntry  79}

vmvcAimStatVMToolsStatus OBJECT-TYPE
    SYNTAX INTEGER{
        toolsNotInstalled(1),
        toolsNotRunning(2),
        toolsOk(3),
        toolsOld(4),
        unknown(5)
        }
    ACCESS read-only
    STATUS mandatory
    DESCRIPTION
        "Status of VM Tools"
    ::= { vmvcAimStatVMEntry  80}

vmvcAimStatVMPhyName OBJECT-TYPE
    SYNTAX SnmpAdminString
    ACCESS read-only
    STATUS mandatory
    DESCRIPTION
        "VirtualMachine Name"
    ::= { vmvcAimStatVMEntry  81 }

vmvcAimStatVMCPUReservation OBJECT-TYPE
    SYNTAX INTEGER
    ACCESS read-only
    STATUS mandatory
    DESCRIPTION
        "Configured CPU reservation in MHz"
    ::= { vmvcAimStatVMEntry  82}
    
vmvcAimStatVMMemoryReservation OBJECT-TYPE
    SYNTAX INTEGER
    ACCESS read-only
    STATUS mandatory
    DESCRIPTION
        "Configured Memory reservation in MB"
    ::= { vmvcAimStatVMEntry  83}

vmvcAimStatVMCPUHotPlug OBJECT-TYPE
    SYNTAX INTEGER{
        disabled(1),
        addEnabled(2),
        removeEnabled(3),
        addRemoveEnabled(4)
        }
    ACCESS read-only
    STATUS mandatory
    DESCRIPTION
        "Enumeration indicating if Virtual CPUs can be added while this
         VM is running."
    ::= { vmvcAimStatVMEntry  84}

vmvcAimStatVMMemoryHotAdd OBJECT-TYPE
    SYNTAX INTEGER{
        disabled(1),
        enabled(2)
        }
    ACCESS read-only
    STATUS mandatory
    DESCRIPTION
        "Enumeration indicating if memory can be added while this VM is 
         running."
    ::= { vmvcAimStatVMEntry 85 }

vmvcAimStatVMMemoryHotAddIncrement OBJECT-TYPE
    SYNTAX Gauge
    ACCESS read-only
    STATUS mandatory
    DESCRIPTION
        "Memory (MB) that can be added to this VM must be in increments/multiples
         of this value.  Not applicable if vmvcAimStatVMMemoryHotAdd is disabled(1)."
    ::= { vmvcAimStatVMEntry 86 }

vmvcAimStatVMMemoryHotAddLimit OBJECT-TYPE
    SYNTAX Gauge
    ACCESS read-only
    STATUS mandatory
    DESCRIPTION
        "Maximum memory (MB) that can be added to this running VM.  Not applicable if 
         vmvcAimStatVMMemoryHotAdd is disabled(1)."
    ::= { vmvcAimStatVMEntry 87 }

vmvcAimStatVMSyncTimeWithHost OBJECT-TYPE
    SYNTAX INTEGER
    ACCESS read-only
    STATUS mandatory
    DESCRIPTION
        "Indicates whether or not the tools program will sync time with the host time."
    ::= { vmvcAimStatVMEntry 88 }

vmvcAimStatVMVCUID OBJECT-TYPE
    SYNTAX INTEGER
    ACCESS read-only
    STATUS mandatory
    DESCRIPTION
        "VC Instance SNMP UID where this VM resides."
    ::= { vmvcAimStatVMEntry 89 }

vmvcAimStatVMVCName OBJECT-TYPE
    SYNTAX SnmpAdminString
    ACCESS read-only
    STATUS mandatory
    DESCRIPTION
        "VC Instance where this VM resides."
    ::= { vmvcAimStatVMEntry 90 }

vmvcAimStatVMFaultToleranceStatus OBJECT-TYPE
    SYNTAX INTEGER{
        notConfigured(1),
        disabled(2),
        enabled(3),
        needSecondary(4),
        starting(5),
        running(6)
    }
    ACCESS read-only
    STATUS mandatory
    DESCRIPTION
        "Enumeration indicating the current Fault Tolerance State of this VM.
            notConfigured - Not configured for FT
            disabled      - FT enabled, not protected (disabled mode)
            enabled       - FT enabled, not protected (not running)
            needSecondary - FT enabled, not protected (in need of Secondary VM)
            starting      - FT enabled, not protected (starting)
            running       - FT enabled, protected"
    ::= { vmvcAimStatVMEntry 91 }

vmvcAimStatVMFTActivityState OBJECT-TYPE
    SYNTAX INTEGER{
        recording(1),
        replaying(2),
        inactive(3)
    }
    ACCESS read-only
    STATUS mandatory
    DESCRIPTION
        "Enumeration indicating the current Fault Tolerance Activity State of this VM.
            recording - This FT VM is primary and is caching its activities for the secondary.
            replaying - This FT VM is secondary and is currently receiving the recorded activities of the primary.
            inactive  - This VM is not actively Fault Tolerant."
    ::= { vmvcAimStatVMEntry 92 }

vmvcAimStatVMFaultToleranceRole OBJECT-TYPE
    SYNTAX INTEGER{
        notConfigured(1),
        primary(2),
        secondary(3)
    }
    ACCESS read-only
    STATUS mandatory
    DESCRIPTION
        "Enumeration indicating the current Fault Tolerance Role of this VM.
            notConfigured - This VM is not configured for Fault Tolerance.
            primary   - This VM is the current primary Fault Tolerant VM.
            secondary - This VM is the current secondary Fault Tolerant VM."
    ::= { vmvcAimStatVMEntry 93 }

vmvcAimStatVMFTSiblingIndex OBJECT-TYPE
    SYNTAX SnmpAdminString
    ACCESS read-only
    STATUS mandatory
    DESCRIPTION
        "VM Index (MOID) of this Fault Tolerant VM's Sibling.  This is empty if this VM does 
         not have a Fault Tolerant sibling."
    ::= { vmvcAimStatVMEntry 94 }

vmvcAimStatVMFTSiblingHostIndex OBJECT-TYPE
    SYNTAX SnmpAdminString
    ACCESS read-only
    STATUS mandatory
    DESCRIPTION
        "Host Index (MOID) of this Fault Tolerant VM's Sibling.  This is empty if this VM does 
         not have a Fault Tolerant sibling."
    ::= { vmvcAimStatVMEntry 95 }

vmvcAimStatVMFTSiblingHostName OBJECT-TYPE
    SYNTAX SnmpAdminString
    ACCESS read-only
    STATUS mandatory
    DESCRIPTION
        "Host Name of this Fault Tolerant VM's Sibling.  This is empty if this VM does 
         not have a Fault Tolerant sibling."
    ::= { vmvcAimStatVMEntry 96 }

vmvcAimStatVMFTSiblingHostUID OBJECT-TYPE
    SYNTAX INTEGER
    ACCESS read-only
    STATUS mandatory
    DESCRIPTION
        "Host UID of this Fault Tolerant VM's Sibling.  This is zero(0) if this VM does 
         not have a Fault Tolerant sibling."
    ::= { vmvcAimStatVMEntry 97 }

vmvcAimStatVMFTTotalSiblingCPU OBJECT-TYPE
    SYNTAX INTEGER
    ACCESS read-only
    STATUS mandatory
    DESCRIPTION
        "The CPU Usage (in MHz) of this Fault Tolerant VM's Sibling.  This is zero(0) if this
         VM does not have a Fault Tolerant sibling."
    ::= { vmvcAimStatVMEntry 98 }

vmvcAimStatVMFTTotalSiblingMemory OBJECT-TYPE
    SYNTAX INTEGER
    ACCESS read-only
    STATUS mandatory
    DESCRIPTION
        "The Memory Usage (in MB) of this Fault Tolerant VM's Sibling.  This is zero(0) if this
         VM does not have a Fault Tolerant sibling."
    ::= { vmvcAimStatVMEntry 99 }
    
vmvcAimStatVMTotalHostMemoryUsage OBJECT-TYPE
    SYNTAX INTEGER
    ACCESS read-only
    STATUS mandatory
    DESCRIPTION
        "This is the amount of Host Memory this VM is using.  This is different from the amount of
         memory being used within the Guest O/S layer of the VM, and can be used for capacity planning, 
         statistics, etc."
    ::= { vmvcAimStatVMEntry 100 }

vmvcAimStatVMVCUUID OBJECT-TYPE
    SYNTAX SnmpAdminString
    ACCESS read-only
    STATUS mandatory
    DESCRIPTION
        "The vCenter-specific UUID where this VM resides."
    ::= { vmvcAimStatVMEntry 101 }


-- *****************************************************************************
-- Status VM vApp Group
-- *****************************************************************************
vmvcAimStatVMvAppCount OBJECT-TYPE
    SYNTAX INTEGER
    ACCESS read-only
    STATUS mandatory
    DESCRIPTION
        "Number of VMs in vmvcAimStatVMvAppTable."
    ::= { vmvcAimStatVMGroup  3}

vmvcAimStatVMvAppTable OBJECT-TYPE
    SYNTAX SEQUENCE OF VmvcAimStatVMvAppRow
    ACCESS not-accessible
    STATUS mandatory
    DESCRIPTION
        "VM vApp extension table.  This table will have a subset of the VM Table
         within it, as it only shows the vApp extension information for those VMs that reside within a
         vApp, or has 'vApp configuration' enabled.  Correlation data between these two tables are:
            UID             ->  Consistent between both tables
            Index + VCName  ->  Consistent & Unique"
    ::= { vmvcAimStatVMGroup  4}

vmvcAimStatVMvAppEntry OBJECT-TYPE
    SYNTAX VmvcAimStatVMvAppRow
    ACCESS not-accessible
    STATUS mandatory
    DESCRIPTION
        "The table entry."
    INDEX { vmvcAimStatVMvAppUID }
    ::= { vmvcAimStatVMvAppTable 1 }

VmvcAimStatVMvAppRow ::=
    SEQUENCE {
        vmvcAimStatVMvAppUID                    INTEGER,
        vmvcAimStatVMvAppIndex                  SnmpAdminString,
        vmvcAimStatVMvAppName                   SnmpAdminString,
        vmvcAimStatVMvAppVCUID                  INTEGER,
        vmvcAimStatVMvAppVCName                 SnmpAdminString,
        vmvcAimStatVMvAppOptions  	            INTEGER,
        vmvcAimStatVMvAppParentVApp	            SnmpAdminString,
        vmvcAimStatVMvAppInstallBootRequired    INTEGER,
        vmvcAimStatVMvAppInstallBootStopDelay   INTEGER,
        vmvcAimStatVMvAppIpAllocationPolicy     INTEGER,
        vmvcAimStatVMvAppSupportedIpProtocol    SnmpAdminString,
        vmvcAimStatVMvAppIpProtocol             SnmpAdminString,
        vmvcAimStatVMvAppProductAppURL          SnmpAdminString,
        vmvcAimStatVMvAppProductVersion         SnmpAdminString,
        vmvcAimStatVMvAppProductFullVersion     SnmpAdminString,
        vmvcAimStatVMvAppProductName            SnmpAdminString,
        vmvcAimStatVMvAppProductURL             SnmpAdminString,
        vmvcAimStatVMvAppProductVendor          SnmpAdminString,
        vmvcAimStatVMvAppProductVendorURL       SnmpAdminString,
        vmvcAimStatVMvAppStartAction            INTEGER,
        vmvcAimStatVMvAppStartOrder             INTEGER,
        vmvcAimStatVMvAppStartDelay             INTEGER,
        vmvcAimStatVMvAppStartWaitForGuest      INTEGER,
        vmvcAimStatVMvAppStopAction             INTEGER,
        vmvcAimStatVMvAppStopDelay              INTEGER,
        vmvcAimStatVMvAppVCUUID                 SnmpAdminString
    }

vmvcAimStatVMvAppUID OBJECT-TYPE
    SYNTAX INTEGER (1..2147483647)
    ACCESS read-only
    STATUS mandatory
    DESCRIPTION
        "UID of the VM"
    ::= { vmvcAimStatVMvAppEntry  1}

vmvcAimStatVMvAppIndex OBJECT-TYPE
    SYNTAX SnmpAdminString
    ACCESS read-only
    STATUS mandatory
    DESCRIPTION
        "Moid of the VM"
    ::= { vmvcAimStatVMvAppEntry  2}

vmvcAimStatVMvAppName OBJECT-TYPE
    SYNTAX SnmpAdminString
    ACCESS read-only
    STATUS mandatory
    DESCRIPTION
        "VirtualMachine Display Name"
    ::= { vmvcAimStatVMvAppEntry  3}

vmvcAimStatVMvAppVCUID OBJECT-TYPE
    SYNTAX INTEGER
    ACCESS read-only
    STATUS mandatory
    DESCRIPTION
        "VC Instance SNMP UID where this VM resides."
    ::= { vmvcAimStatVMvAppEntry  4}

vmvcAimStatVMvAppVCName OBJECT-TYPE
    SYNTAX SnmpAdminString
    ACCESS read-only
    STATUS mandatory
    DESCRIPTION
        "VC Instance where this VM resides."
    ::= { vmvcAimStatVMvAppEntry  5}

vmvcAimStatVMvAppOptions OBJECT-TYPE
    SYNTAX INTEGER{
        disabled(1),
        enabled(2)
    }
    ACCESS read-only
    STATUS mandatory
    DESCRIPTION
        "Specifies if vApp Configuration is enabled within Virtual Machine.
         This AIM supports this attribute only for vSphere 4.1 and above."
    ::= { vmvcAimStatVMvAppEntry  6}

vmvcAimStatVMvAppParentVApp OBJECT-TYPE
    SYNTAX SnmpAdminString
    ACCESS read-only
    STATUS mandatory
    DESCRIPTION
        "vApp (MOID) that this VM is a primary member of.
         Only applies to VMs that are members of a vApp."
    ::= { vmvcAimStatVMvAppEntry  7}

vmvcAimStatVMvAppInstallBootRequired OBJECT-TYPE
    SYNTAX INTEGER{
        false(1),
        true(2)
    }
    ACCESS read-only
    STATUS mandatory
    DESCRIPTION
        "Specifies whether the VM needs an initial boot before the deployment is complete.
         Only applies to VMs that are members of a vApp."
    ::= { vmvcAimStatVMvAppEntry  8}

vmvcAimStatVMvAppInstallBootStopDelay OBJECT-TYPE
    SYNTAX INTEGER
    ACCESS read-only
    STATUS mandatory
    DESCRIPTION
        "Specifies the delay in seconds to wait for the VM to power off after the initial
         boot (used only if installBootRequired is true). A value of 0 means wait until
         the VM is powered off by the guest.
         Only applies to VMs that are members of a vApp."
    ::= { vmvcAimStatVMvAppEntry  9}

vmvcAimStatVMvAppIpAllocationPolicy OBJECT-TYPE
    SYNTAX INTEGER{
        fixed(1),
        transient(2),
        dhcp(3)
    }
    ACCESS read-only
    STATUS mandatory
    DESCRIPTION
        "Specifies how IP allocation should be managed by vCenter.
            fixed     -   IP addresses are manually configured. No automatic allocation is performed.
            transient -   IP addresses are automatically allocated from the vCenter managed IP network range
                          at power-on, and released at power-off.
            dhcp      -   A DHCP server is used for IP allocation.
         Only applies to VMs that are members of a vApp.
         This AIM supports this attribute only for vSphere 4.1 and above."
    ::= { vmvcAimStatVMvAppEntry 10}

vmvcAimStatVMvAppSupportedIpProtocol OBJECT-TYPE
    SYNTAX SnmpAdminString
    ACCESS read-only
    STATUS mandatory
    DESCRIPTION
        "Specifies the IP protocols supported by the guest software.
         Only applies to VMs that are members of a vApp.
         This AIM supports this attribute only for vSphere 4.1 and above."
    ::= { vmvcAimStatVMvAppEntry 11}

vmvcAimStatVMvAppIpProtocol OBJECT-TYPE
    SYNTAX SnmpAdminString
    ACCESS read-only
    STATUS mandatory
    DESCRIPTION
        "Specifies the chosen IP protocol for this deployment.
         Only applies to VMs that are members of a vApp.
         This AIM supports this attribute only for vSphere 4.1 and above."
    ::= { vmvcAimStatVMvAppEntry 12}

vmvcAimStatVMvAppProductAppURL OBJECT-TYPE
    SYNTAX SnmpAdminString
    ACCESS read-only
    STATUS mandatory
    DESCRIPTION
        "URL to entry-point for application.
         Only applies to VMs that have vApp Configuration Option enabled.
         This AIM supports this attribute only for vSphere 4.1 and above."
    ::= { vmvcAimStatVMvAppEntry 13}

vmvcAimStatVMvAppProductVersion OBJECT-TYPE
    SYNTAX SnmpAdminString
    ACCESS read-only
    STATUS mandatory
    DESCRIPTION
        "Short version of the product, e.g., 1.0.
         Only applies to VMs that have vApp Configuration Option enabled.
         This AIM supports this attribute only for vSphere 4.1 and above."
    ::= { vmvcAimStatVMvAppEntry 14}

vmvcAimStatVMvAppProductFullVersion OBJECT-TYPE
    SYNTAX SnmpAdminString
    ACCESS read-only
    STATUS mandatory
    DESCRIPTION
        "Full-version of the product, e.g., 1.0-build 12323.
         Only applies to VMs that have vApp Configuration Option enabled.
         This AIM supports this attribute only for vSphere 4.1 and above."
    ::= { vmvcAimStatVMvAppEntry 15}

vmvcAimStatVMvAppProductName OBJECT-TYPE
    SYNTAX SnmpAdminString
    ACCESS read-only
    STATUS mandatory
    DESCRIPTION
        "Name of the product.
         Only applies to VMs that have vApp Configuration Option enabled.
         This AIM supports this attribute only for vSphere 4.1 and above."
    ::= { vmvcAimStatVMvAppEntry 16}

vmvcAimStatVMvAppProductURL OBJECT-TYPE
    SYNTAX SnmpAdminString
    ACCESS read-only
    STATUS mandatory
    DESCRIPTION
        "URL to product homepage.
         Only applies to VMs that have vApp Configuration Option enabled.
         This AIM supports this attribute only for vSphere 4.1 and above."
    ::= { vmvcAimStatVMvAppEntry 17}

vmvcAimStatVMvAppProductVendor OBJECT-TYPE
    SYNTAX SnmpAdminString
    ACCESS read-only
    STATUS mandatory
    DESCRIPTION
        "Vendor of the product.
         Only applies to VMs that have vApp Configuration Option enabled.
         This AIM supports this attribute only for vSphere 4.1 and above."
    ::= { vmvcAimStatVMvAppEntry 18}

vmvcAimStatVMvAppProductVendorURL OBJECT-TYPE
    SYNTAX SnmpAdminString
    ACCESS read-only
    STATUS mandatory
    DESCRIPTION
        "URL to vendor homepage.
         Only applies to VMs that have vApp Configuration Option enabled.
         This AIM supports this attribute only for vSphere 4.1 and above."
    ::= { vmvcAimStatVMvAppEntry 19}

vmvcAimStatVMvAppStartAction OBJECT-TYPE
    SYNTAX INTEGER{
        none(1),
        powerOn(2)
    }
    ACCESS read-only
    STATUS mandatory
    DESCRIPTION
        "The startup action for this VM. Valid settings are none or powerOn. If set to none, then the
         VM does not participate in auto-start.
         Only applies to VMs that are members of a vApp."
    ::= { vmvcAimStatVMvAppEntry 20}

vmvcAimStatVMvAppStartOrder OBJECT-TYPE
    SYNTAX INTEGER
    ACCESS read-only
    STATUS mandatory
    DESCRIPTION
        "Specifies the start order for this VM. Entities are started from lower numbers to
         higher-numbers and reverse on shutdown. Multiple entities with the same start-order may
         be started in parallel and the order is unspecified. This value must be 0 or higher.
         Only applies to VMs that are members of a vApp."
    ::= { vmvcAimStatVMvAppEntry 21}

vmvcAimStatVMvAppStartDelay OBJECT-TYPE
    SYNTAX INTEGER
    ACCESS read-only
    STATUS mandatory
    DESCRIPTION
        "Delay in seconds before continuing with the next entity in the order of entities to
         be started.
         Only applies to VMs that are members of a vApp."
    ::= { vmvcAimStatVMvAppEntry 22}

vmvcAimStatVMvAppStartWaitForGuest OBJECT-TYPE
    SYNTAX INTEGER{
        false(1),
        true(2)
    }
    ACCESS read-only
    STATUS mandatory
    DESCRIPTION
        "Determines if the virtual machine should start after receiving a heartbeat from the
         guest O/S. When a virtual machine is next in the start order, the system either waits a
         specified period of time for a virtual machine to power on or it waits until it receives
         a successful heartbeat from a powered on virtual machine. By default, this is set to false.
         Only applies to VMs that are members of a vApp."
    ::= { vmvcAimStatVMvAppEntry 23}

vmvcAimStatVMvAppStopAction OBJECT-TYPE
    SYNTAX INTEGER{
        none(1),
        powerOff(2),
        guestShutdown(3),
        suspend(4)
    }
    ACCESS read-only
    STATUS mandatory
    DESCRIPTION
        "The stop action for the VM. Can be set to none, powerOff, guestShutdown,
         or suspend. If set to none, then the VM does not participate in auto-stop.
         Only applies to VMs that are members of a vApp."
    ::= { vmvcAimStatVMvAppEntry 24}

vmvcAimStatVMvAppStopDelay OBJECT-TYPE
    SYNTAX INTEGER
    ACCESS read-only
    STATUS mandatory
    DESCRIPTION
        "Delay in seconds before continuing with the next entity in the order sequence. This is
         only used if the stopAction is guestShutdown.
         Only applies to VMs that are members of a vApp."
    ::= { vmvcAimStatVMvAppEntry 25}

vmvcAimStatVMvAppVCUUID OBJECT-TYPE
    SYNTAX SnmpAdminString
    ACCESS read-only
    STATUS mandatory
    DESCRIPTION
        "The vCenter-specific UUID where this VM resides."
    ::= { vmvcAimStatVMvAppEntry 26}


-- *****************************************************************************
-- Status Template Group
-- *****************************************************************************
vmvcAimStatTemplateCount OBJECT-TYPE
    SYNTAX INTEGER
    ACCESS read-only
    STATUS mandatory
    DESCRIPTION
        "Number of Templates in vmvcAimStatTemplateTable."
    ::= { vmvcAimStatTemplateGroup 1}

vmvcAimStatTemplateTable OBJECT-TYPE
    SYNTAX SEQUENCE OF VmvcAimStatTemplateRow
    ACCESS not-accessible
    STATUS mandatory
    DESCRIPTION
        "Template table."
    ::= { vmvcAimStatTemplateGroup 2 }

vmvcAimStatTemplateEntry OBJECT-TYPE
    SYNTAX VmvcAimStatTemplateRow
    ACCESS not-accessible
    STATUS mandatory
    DESCRIPTION
        "The table entry."
    INDEX { vmvcAimStatTemplateUID  }
    ::= { vmvcAimStatTemplateTable 1 }

VmvcAimStatTemplateRow ::=
    SEQUENCE {
        vmvcAimStatTemplateUID              INTEGER,
        vmvcAimStatTemplateIndex            SnmpAdminString,
        vmvcAimStatTemplateName             SnmpAdminString,
        vmvcAimStatTemplateVMFolderId       SnmpAdminString,
        vmvcAimStatTemplateVMFolderName     SnmpAdminString,
        vmvcAimStatTemplateVMFolderFullPath SnmpAdminString,
        vmvcAimStatTemplateHostName         SnmpAdminString,
        vmvcAimStatTemplateHostID           SnmpAdminString,
        vmvcAimStatTemplateDatacenterName   SnmpAdminString,
        vmvcAimStatTemplateOsType           SnmpAdminString,
        vmvcAimStatTemplateNumVCpu          INTEGER,
        vmvcAimStatTemplateMem              SnmpAdminString,
        vmvcAimStatTemplateIPAddress        SnmpAdminString,
        vmvcAimStatTemplateDatastore        SnmpAdminString,
        vmvcAimStatTemplateNetwork          SnmpAdminString,
        vmvcAimStatTemplateConfigFile       SnmpAdminString,
        vmvcAimStatTemplateVCUID            INTEGER,
        vmvcAimStatTemplateVCName           SnmpAdminString,
        vmvcAimStatTemplateVCUUID           SnmpAdminString
    }

vmvcAimStatTemplateUID OBJECT-TYPE
    SYNTAX INTEGER (1..2147483647)
    ACCESS read-only
    STATUS mandatory
    DESCRIPTION
        "UID of template"
    ::= { vmvcAimStatTemplateEntry  1}

vmvcAimStatTemplateIndex OBJECT-TYPE
    SYNTAX SnmpAdminString
    ACCESS read-only
    STATUS mandatory
    DESCRIPTION
        "MOID of  template"
    ::= { vmvcAimStatTemplateEntry  2}

vmvcAimStatTemplateName OBJECT-TYPE
    SYNTAX SnmpAdminString
    ACCESS read-only
    STATUS mandatory
    DESCRIPTION
        "Name of template"
    ::= { vmvcAimStatTemplateEntry  3}

vmvcAimStatTemplateVMFolderId OBJECT-TYPE
    SYNTAX SnmpAdminString
    ACCESS read-only
    STATUS mandatory
    DESCRIPTION
        "VM Folder MOID"
    ::= { vmvcAimStatTemplateEntry  4}

vmvcAimStatTemplateVMFolderName OBJECT-TYPE
    SYNTAX SnmpAdminString
    ACCESS read-only
    STATUS mandatory
    DESCRIPTION
        "Name of VM Folder"
    ::= { vmvcAimStatTemplateEntry  5}

vmvcAimStatTemplateVMFolderFullPath OBJECT-TYPE
    SYNTAX SnmpAdminString
    ACCESS read-only
    STATUS mandatory
    DESCRIPTION
        "Full path to the VM Folder"
    ::= { vmvcAimStatTemplateEntry  6}

vmvcAimStatTemplateHostName OBJECT-TYPE
    SYNTAX SnmpAdminString
    ACCESS read-only
    STATUS mandatory
    DESCRIPTION
        "Name of the host the template resides on"
    ::= { vmvcAimStatTemplateEntry  7}

vmvcAimStatTemplateHostID OBJECT-TYPE
    SYNTAX SnmpAdminString
    ACCESS read-only
    STATUS mandatory
    DESCRIPTION
        "Moid of the host the template resides on"
    ::= { vmvcAimStatTemplateEntry  8}

vmvcAimStatTemplateDatacenterName OBJECT-TYPE
    SYNTAX SnmpAdminString
    ACCESS read-only
    STATUS mandatory
    DESCRIPTION
        "Name of the host datacenter"
    ::= { vmvcAimStatTemplateEntry  9}

vmvcAimStatTemplateOsType OBJECT-TYPE
    SYNTAX SnmpAdminString
    ACCESS read-only
    STATUS mandatory
    DESCRIPTION
        "OS Type of the template"
    ::= { vmvcAimStatTemplateEntry  10}

vmvcAimStatTemplateNumVCpu OBJECT-TYPE
    SYNTAX INTEGER
    ACCESS read-only
    STATUS mandatory
    DESCRIPTION
        "Number of Virtual CPUs"
    ::= { vmvcAimStatTemplateEntry  11}

vmvcAimStatTemplateMem OBJECT-TYPE
    SYNTAX SnmpAdminString
    ACCESS read-only
    STATUS mandatory
    DESCRIPTION
        "Memory settings of the template"
    ::= { vmvcAimStatTemplateEntry  12}

vmvcAimStatTemplateIPAddress OBJECT-TYPE
    SYNTAX SnmpAdminString (SIZE(0..1024))
    ACCESS read-only
    STATUS mandatory
    DESCRIPTION
        "IP Address settings of the template"
    ::= { vmvcAimStatTemplateEntry  13}

vmvcAimStatTemplateDatastore OBJECT-TYPE
    SYNTAX SnmpAdminString
    ACCESS read-only
    STATUS mandatory
    DESCRIPTION
        "Datastore associated with template. "
    ::= { vmvcAimStatTemplateEntry  14}

vmvcAimStatTemplateNetwork OBJECT-TYPE
    SYNTAX SnmpAdminString
    ACCESS read-only
    STATUS mandatory
    DESCRIPTION
        "Network associated with template. "
    ::= { vmvcAimStatTemplateEntry  15}

vmvcAimStatTemplateConfigFile  OBJECT-TYPE
    SYNTAX SnmpAdminString
    ACCESS read-only
    STATUS mandatory
    DESCRIPTION
        "Config File Associated with this Template"
    ::= { vmvcAimStatTemplateEntry  16}

vmvcAimStatTemplateVCUID OBJECT-TYPE
    SYNTAX INTEGER
    ACCESS read-only
    STATUS mandatory
    DESCRIPTION
        "VC Instance SNMP UID where this Template resides."
    ::= { vmvcAimStatTemplateEntry 17 }

vmvcAimStatTemplateVCName OBJECT-TYPE
    SYNTAX SnmpAdminString
    ACCESS read-only
    STATUS mandatory
    DESCRIPTION
        "VC Instance where this Template resides."
    ::= { vmvcAimStatTemplateEntry 18 }

vmvcAimStatTemplateVCUUID OBJECT-TYPE
    SYNTAX SnmpAdminString
    ACCESS read-only
    STATUS mandatory
    DESCRIPTION
        "The vCenter-specific UUID where this Template resides."
    ::= { vmvcAimStatTemplateEntry 19 }


-- *****************************************************************************
-- Status Virtual Switch  Group
-- *****************************************************************************
vmvcAimStatVSwitchCount OBJECT-TYPE
    SYNTAX INTEGER
    ACCESS read-only
    STATUS mandatory
    DESCRIPTION
        "Virtual Switch Group."
    ::= { vmvcAimStatVSwitchGroup 1}

vmvcAimStatVSwitchTable OBJECT-TYPE
    SYNTAX SEQUENCE OF VmvcAimStatVSwitchRow
    ACCESS not-accessible
    STATUS mandatory
    DESCRIPTION
        "Port Group Group."
    ::= { vmvcAimStatVSwitchGroup 2 }

vmvcAimStatVSwitchEntry OBJECT-TYPE
    SYNTAX VmvcAimStatVSwitchRow
    ACCESS not-accessible
    STATUS mandatory
    DESCRIPTION
        "The table entry."
    INDEX { vmvcAimStatSwitchUID }
    ::= { vmvcAimStatVSwitchTable 1 }

VmvcAimStatVSwitchRow ::=
    SEQUENCE {
        vmvcAimStatSwitchUID                            INTEGER,
        vmvcAimStatSwitchIndex                          SnmpAdminString,
        vmvcAimStatSwitchHost                           SnmpAdminString,
        vmvcAimStatSwitchName                           SnmpAdminString,
        vmvcAimStatSwitchNumPorts                       INTEGER,
        vmvcAimStatSwitchNumAvailPorts                  INTEGER,
        vmvcAimStatSwitchPortgroup                      SnmpAdminString,
        vmvcAimStatSwitchBridgeType                     SnmpAdminString,
        vmvcAimStatSwitchBridgePNic                     SnmpAdminString,
        vmvcAimStatSwitchPolicyOffloadCkhSum            INTEGER,
        vmvcAimStatSwitchPolicyOffloadtcpSegmt          INTEGER,
        vmvcAimStatSwitchPolicyOffloadZeroCpyX          INTEGER,
        vmvcAimStatSwitchPolicySecurityAllowPromis      INTEGER,
        vmvcAimStatSwitchPolicySecurityForgedTransmit   INTEGER,
        vmvcAimStatSwitchPolicySecurityMACChanges       INTEGER,
        vmvcAimStatSwitchPolicyShapingAvgBandWidth      INTEGER,
        vmvcAimStatSwitchPolicyShapingBurstSize         INTEGER,
        vmvcAimStatSwitchPolicyShapingEnabled           INTEGER,
        vmvcAimStatSwitchPolicyShapingPeakBandWidth     INTEGER,
        vmvcAimStatSwitchState                          INTEGER,
        vmvcAimStatSwitchNicTeamActiveNic               SnmpAdminString,
        vmvcAimStatSwitchNicTeamStandByNic              SnmpAdminString,
        vmvcAimStatSwitchNicTeamNotifySwitch            INTEGER,
        vmvcAimStatSwitchNicTeamPolicy                  SnmpAdminString,
        vmvcAimStatSwitchNicTeamReversePolicy           INTEGER,
        vmvcAimStatSwitchNicTeamRollingOrder            INTEGER,
        vmvcAimStatSwitchNicTeamFailureChkBeacon        INTEGER,
        vmvcAimStatSwitchNicTeamFailureChkDuplex        INTEGER,
        vmvcAimStatSwitchNicTeamFailureChkErrPct        INTEGER,
        vmvcAimStatSwitchNicTeamFailureChkSpeed         SnmpAdminString,
        vmvcAimStatSwitchNicTeamFailureFullDuplex       INTEGER,
        vmvcAimStatSwitchNicTeamFailurePercentage       INTEGER,
        vmvcAimStatSwitchNicTeamFailureSpeed            INTEGER,
        vmvcAimStatSwitchMonitor                        INTEGER,
        vmvcAimStatSwitchAlert                          INTEGER,
        vmvcAimStatSwitchHostName                       SnmpAdminString,
        vmvcAimStatSwitchVCUID                          INTEGER,
        vmvcAimStatSwitchVCName                         SnmpAdminString,
        vmvcAimStatSwitchVCUUID                         SnmpAdminString
    }

vmvcAimStatSwitchUID OBJECT-TYPE
    SYNTAX INTEGER (1..2147483647)
    ACCESS read-only
    STATUS mandatory
    DESCRIPTION
        "UID of virtual switch"
    ::= { vmvcAimStatVSwitchEntry  1}

vmvcAimStatSwitchIndex OBJECT-TYPE
    SYNTAX SnmpAdminString
    ACCESS read-only
    STATUS mandatory
    DESCRIPTION
        "MOID of virtual switch"
    ::= { vmvcAimStatVSwitchEntry  2}

vmvcAimStatSwitchHost OBJECT-TYPE
    SYNTAX SnmpAdminString
    ACCESS read-only
    STATUS mandatory
    DESCRIPTION
        "The host on which the virtual switch is located."
    ::= { vmvcAimStatVSwitchEntry  3}

vmvcAimStatSwitchName OBJECT-TYPE
    SYNTAX SnmpAdminString
    ACCESS read-only
    STATUS mandatory
    DESCRIPTION
        "The name of virtual switch"
    ::= { vmvcAimStatVSwitchEntry  4}

vmvcAimStatSwitchNumPorts OBJECT-TYPE
    SYNTAX INTEGER
    ACCESS read-only
    STATUS mandatory
    DESCRIPTION
        "The number of ports this virtual switch currently has"
    ::= { vmvcAimStatVSwitchEntry  5}

vmvcAimStatSwitchNumAvailPorts OBJECT-TYPE
    SYNTAX INTEGER
    ACCESS read-only
    STATUS mandatory
    DESCRIPTION
        "The number of ports that are available on this virtual switch"
    ::= { vmvcAimStatVSwitchEntry  6}

vmvcAimStatSwitchPortgroup OBJECT-TYPE
    SYNTAX SnmpAdminString
    ACCESS read-only
    STATUS mandatory
    DESCRIPTION
        "Port groups configured for this virtual switch"
    ::= { vmvcAimStatVSwitchEntry  7}

vmvcAimStatSwitchBridgeType OBJECT-TYPE
    SYNTAX SnmpAdminString
    ACCESS read-only
    STATUS mandatory
    DESCRIPTION
        "The bridge type for virtual Switch. Type can be auto, bond, simple"
    ::= { vmvcAimStatVSwitchEntry  8}

vmvcAimStatSwitchBridgePNic OBJECT-TYPE
    SYNTAX SnmpAdminString
    ACCESS read-only
    STATUS mandatory
    DESCRIPTION
        "Physical nic connected to the bridge. "
    ::= { vmvcAimStatVSwitchEntry  9}

vmvcAimStatSwitchPolicyOffloadCkhSum OBJECT-TYPE
    SYNTAX INTEGER{
        false(1),
        true(2)
    }
    ACCESS read-only
    STATUS mandatory
    DESCRIPTION
        "The flag to indicate whether the checksum offloading is supported(1) ot not(2)."
    ::= { vmvcAimStatVSwitchEntry  10}

vmvcAimStatSwitchPolicyOffloadtcpSegmt OBJECT-TYPE
    SYNTAX INTEGER{
        false(1),
        true(2)
    }
    ACCESS read-only
    STATUS mandatory
    DESCRIPTION
        "The flag to indicate whether or not TCP segmentation offloading (TSO) is supported."
    ::= { vmvcAimStatVSwitchEntry  11}

vmvcAimStatSwitchPolicyOffloadZeroCpyX OBJECT-TYPE
    SYNTAX INTEGER{
        false(1),
        true(2)
    }
    ACCESS read-only
    STATUS mandatory
    DESCRIPTION
        "The flag to indicate whether or not zero copy transmits are supported."
    ::= { vmvcAimStatVSwitchEntry  12}

vmvcAimStatSwitchPolicySecurityAllowPromis OBJECT-TYPE
    SYNTAX INTEGER{
        false(1),
        true(2)
    }
    ACCESS read-only
    STATUS mandatory
    DESCRIPTION
        "The flag to indicate whether or not all traffic is seen on the port."
    ::= { vmvcAimStatVSwitchEntry  13}

vmvcAimStatSwitchPolicySecurityForgedTransmit OBJECT-TYPE
    SYNTAX INTEGER{
        false(1),
        true(2)
    }
    ACCESS read-only
    STATUS mandatory
    DESCRIPTION
        "flag to indicate if different MAC address than that of the virtual network adapter."
    ::= { vmvcAimStatVSwitchEntry  14}

vmvcAimStatSwitchPolicySecurityMACChanges OBJECT-TYPE
    SYNTAX INTEGER{
        false(1),
        true(2)
    }
    ACCESS read-only
    STATUS mandatory
    DESCRIPTION
        "flag to indicate whether or not the Media Access Control (MAC) address can be changed"
    ::= { vmvcAimStatVSwitchEntry  15}

vmvcAimStatSwitchPolicyShapingAvgBandWidth OBJECT-TYPE
    SYNTAX INTEGER
    ACCESS read-only
    STATUS mandatory
    DESCRIPTION
        "The average bandwidth in bits per second if shaping is enabled on the port."
    ::= { vmvcAimStatVSwitchEntry  16}

vmvcAimStatSwitchPolicyShapingBurstSize OBJECT-TYPE
    SYNTAX INTEGER
    ACCESS read-only
    STATUS mandatory
    DESCRIPTION
        "The maximum burst size allowed in bytes if shaping is enabled on the port"
    ::= { vmvcAimStatVSwitchEntry  17}

vmvcAimStatSwitchPolicyShapingEnabled OBJECT-TYPE
    SYNTAX INTEGER{
        false(1),
        true(2)
    }
    ACCESS read-only
    STATUS mandatory
    DESCRIPTION
        "The flag to indicate whether or not traffic shaper is enabled on the port"
    ::= { vmvcAimStatVSwitchEntry  18}

vmvcAimStatSwitchPolicyShapingPeakBandWidth OBJECT-TYPE
    SYNTAX INTEGER
    ACCESS read-only
    STATUS mandatory
    DESCRIPTION
        "The peak bandwidth during bursts in bits per second if traffic shaping is enabled on the port."
    ::= { vmvcAimStatVSwitchEntry  19}

vmvcAimStatSwitchState OBJECT-TYPE
    SYNTAX INTEGER {
        unknown(1),
        ok(2),
        warning(3),
        critical(4)
    }
    ACCESS read-only
    STATUS mandatory
    DESCRIPTION
        "State of the switch is the combined state of the nic(s).Can be ok, warning and critical"
    ::= { vmvcAimStatVSwitchEntry  20}

vmvcAimStatSwitchNicTeamActiveNic OBJECT-TYPE
    SYNTAX SnmpAdminString
    ACCESS read-only
    STATUS mandatory
    DESCRIPTION
        "List of active network adapters used for load balancing."
    ::= { vmvcAimStatVSwitchEntry  21}

vmvcAimStatSwitchNicTeamStandByNic OBJECT-TYPE
    SYNTAX SnmpAdminString
    ACCESS read-only
    STATUS mandatory
    DESCRIPTION
        "Standby network adapters used for failover"
    ::= { vmvcAimStatVSwitchEntry  22}

vmvcAimStatSwitchNicTeamNotifySwitch OBJECT-TYPE
    SYNTAX INTEGER{
        false(1),
        true(2)
    }
    ACCESS read-only
    STATUS mandatory
    DESCRIPTION
        "Flag to specify whether or not to notify the physical switch if a link fails"
    ::= { vmvcAimStatVSwitchEntry  23}

vmvcAimStatSwitchNicTeamPolicy OBJECT-TYPE
    SYNTAX SnmpAdminString
    ACCESS read-only
    STATUS mandatory
    DESCRIPTION
        "Network adapter teaming policy which includes failover and load balancing."
    ::= { vmvcAimStatVSwitchEntry  24}

vmvcAimStatSwitchNicTeamReversePolicy OBJECT-TYPE
    SYNTAX INTEGER{
        false(1),
        true(2)
    }
    ACCESS read-only
    STATUS mandatory
    DESCRIPTION
        "The flag to indicate whether or not the teaming policy is applied to inbound frames as well."
    ::= { vmvcAimStatVSwitchEntry  25}

vmvcAimStatSwitchNicTeamRollingOrder OBJECT-TYPE
    SYNTAX INTEGER{
        false(1),
        true(2)
    }
    ACCESS read-only
    STATUS mandatory
    DESCRIPTION
        "The flag to indicate whether or not to use a rolling policy when restoring links"
    ::= { vmvcAimStatVSwitchEntry  26}

vmvcAimStatSwitchNicTeamFailureChkBeacon OBJECT-TYPE
    SYNTAX INTEGER{
        false(1),
        true(2)
    }
    ACCESS read-only
    STATUS mandatory
    DESCRIPTION
        "flag to enable beacon probing as a method to validate the link status of a physical network  "
    ::= { vmvcAimStatVSwitchEntry  27}

vmvcAimStatSwitchNicTeamFailureChkDuplex OBJECT-TYPE
    SYNTAX INTEGER{
        false(1),
        true(2)
    }
    ACCESS read-only
    STATUS mandatory
    DESCRIPTION
        "flag to indicate whether or not to use the link duplex reported by the driver as link selection criteria"
    ::= { vmvcAimStatVSwitchEntry  28}

vmvcAimStatSwitchNicTeamFailureChkErrPct OBJECT-TYPE
    SYNTAX INTEGER{
        false(1),
        true(2)
    }
    ACCESS read-only
    STATUS mandatory
    DESCRIPTION
        "flag to indicate whether or not to use link error percentage to detect failure."
    ::= { vmvcAimStatVSwitchEntry  29}

vmvcAimStatSwitchNicTeamFailureChkSpeed OBJECT-TYPE
    SYNTAX SnmpAdminString
    ACCESS read-only
    STATUS mandatory
    DESCRIPTION
        "Switch Nic Team Failure Check Speed."
    ::= { vmvcAimStatVSwitchEntry  30}

vmvcAimStatSwitchNicTeamFailureFullDuplex OBJECT-TYPE
    SYNTAX INTEGER{
        false(1),
        true(2)
    }
    ACCESS read-only
    STATUS mandatory
    DESCRIPTION
        "Configured duplexity"
    ::= { vmvcAimStatVSwitchEntry  31}

vmvcAimStatSwitchNicTeamFailurePercentage OBJECT-TYPE
    SYNTAX INTEGER
    ACCESS read-only
    STATUS mandatory
    DESCRIPTION
        "Configured percentage"
    ::= { vmvcAimStatVSwitchEntry  32}

vmvcAimStatSwitchNicTeamFailureSpeed OBJECT-TYPE
    SYNTAX INTEGER
    ACCESS read-only
    STATUS mandatory
    DESCRIPTION
        "Configured speed"
    ::= { vmvcAimStatVSwitchEntry  33}

vmvcAimStatSwitchMonitor OBJECT-TYPE
    SYNTAX INTEGER{
        do-not-monitor(1),
        monitor(2)
        }
    ACCESS read-write
    STATUS mandatory
    DESCRIPTION
        "Flag indicate whether Switch to be Monitored(2) or not(1)."
    DEFVAL {2 }
    ::= { vmvcAimStatVSwitchEntry  34}

vmvcAimStatSwitchAlert OBJECT-TYPE
    SYNTAX INTEGER{
        one-nic-down-warn(1),
        one-nic-down-crit(2),
        all-nic-down-warn(3),
        all-nic-down-crit(4)
        }
    ACCESS read-write
    STATUS mandatory
    DESCRIPTION
        "switch alert status "
    DEFVAL { 2 }
    ::= { vmvcAimStatVSwitchEntry  35}

vmvcAimStatSwitchHostName OBJECT-TYPE
    SYNTAX SnmpAdminString
    ACCESS read-only
    STATUS mandatory
    DESCRIPTION
        "Host Name"
    ::= { vmvcAimStatVSwitchEntry  36}

vmvcAimStatSwitchVCUID OBJECT-TYPE
    SYNTAX INTEGER
    ACCESS read-only
    STATUS mandatory
    DESCRIPTION
        "VC Instance SNMP UID where this Virtual Switch resides."
    ::= { vmvcAimStatVSwitchEntry 37 }

vmvcAimStatSwitchVCName OBJECT-TYPE
    SYNTAX SnmpAdminString
    ACCESS read-only
    STATUS mandatory
    DESCRIPTION
        "VC Instance where this Virtual Switch resides."
    ::= { vmvcAimStatVSwitchEntry 38 }

vmvcAimStatSwitchVCUUID OBJECT-TYPE
    SYNTAX SnmpAdminString
    ACCESS read-only
    STATUS mandatory
    DESCRIPTION
        "The vCenter-specific UUID where this Virtual Switch resides."
    ::= { vmvcAimStatVSwitchEntry 39 }


-- *****************************************************************************
-- Status Port Group
-- *****************************************************************************
vmvcAimStatPortGrpCount OBJECT-TYPE
    SYNTAX INTEGER
    ACCESS read-only
    STATUS mandatory
    DESCRIPTION
        "Port Group count in vmvcAimStatPortGrpTable."
    ::= { vmvcAimStatPortGrpGroup 1}

vmvcAimStatPortGrpTable OBJECT-TYPE
    SYNTAX SEQUENCE OF VmvcAimStatPortGrpRow
    ACCESS not-accessible
    STATUS mandatory
    DESCRIPTION
        "Port Group."
    ::= { vmvcAimStatPortGrpGroup 2 }

vmvcAimStatPortGrpEntry OBJECT-TYPE
    SYNTAX VmvcAimStatPortGrpRow
    ACCESS not-accessible
    STATUS mandatory
    DESCRIPTION
        "The table entry."
    INDEX { vmvcAimStatPGUID }
    ::= { vmvcAimStatPortGrpTable 1 }

VmvcAimStatPortGrpRow ::=
    SEQUENCE {
        vmvcAimStatPGUID                            INTEGER,
        vmvcAimStatPGName                           SnmpAdminString,
        vmvcAimStatPGHostIndex                      SnmpAdminString,
        vmvcAimStatPGVlanId                         SnmpAdminString,
        vmvcAimStatPGVSwitchName                    SnmpAdminString,
        vmvcAimStatPGPorts                          SnmpAdminString,
        vmvcAimStatPGPolicyOffloadCkhSum            INTEGER,
        vmvcAimStatPGPolicyOffloadtcpSegmt          INTEGER,
        vmvcAimStatPGPolicyOffloadZeroCpyX          INTEGER,
        vmvcAimStatPGPolicySecurityAllowPromis      INTEGER,
        vmvcAimStatPGPolicySecurityForgedTransmit   INTEGER,
        vmvcAimStatPGPolicySecurityMACChanges       INTEGER,
        vmvcAimStatPGHostName                       SnmpAdminString,
        vmvcAimStatPGVSwitchUID                     INTEGER,
        vmvcAimStatPGPolicyShapingAvgBandWidth      INTEGER,
        vmvcAimStatPGPolicyShapingBurstSize         INTEGER,
        vmvcAimStatPGPolicyShapingEnabled           INTEGER,
        vmvcAimStatPGPolicyShapingPeakBandWidth     INTEGER,
        vmvcAimStatPGNicTeamAvailableNic            SnmpAdminString,
        vmvcAimStatPGNicTeamActiveNic               SnmpAdminString,
        vmvcAimStatPGNicTeamStandByNic              SnmpAdminString,
        vmvcAimStatPGNicTeamNotifySwitch            INTEGER,
        vmvcAimStatPGNicTeamPolicy                  SnmpAdminString,
        vmvcAimStatPGNicTeamReversePolicy           INTEGER,
        vmvcAimStatPGNicTeamRollingOrder            INTEGER,
        vmvcAimStatPGNicTeamFailureChkBeacon        INTEGER,
        vmvcAimStatPGNicTeamFailureChkDuplex        INTEGER,
        vmvcAimStatPGNicTeamFailureChkErrPct        INTEGER,
        vmvcAimStatPGNicTeamFailureChkSpeed         SnmpAdminString,
        vmvcAimStatPGNicTeamFailureFullDuplex       INTEGER,
        vmvcAimStatPGNicTeamFailurePercentage       INTEGER,
        vmvcAimStatPGNicTeamFailureSpeed            INTEGER,    
        vmvcAimStatPGVCUID                          INTEGER,
        vmvcAimStatPGVCName                         SnmpAdminString,
        vmvcAimStatPGVCUUID                         SnmpAdminString
    }

vmvcAimStatPGUID OBJECT-TYPE
    SYNTAX INTEGER (1..2147483647)
    ACCESS read-only
    STATUS mandatory
    DESCRIPTION
        "UID of the port group"
    ::= { vmvcAimStatPortGrpEntry  1}

vmvcAimStatPGName OBJECT-TYPE
    SYNTAX SnmpAdminString
    ACCESS read-only
    STATUS mandatory
    DESCRIPTION
        "Name of the port group"
    ::= { vmvcAimStatPortGrpEntry  2}

vmvcAimStatPGHostIndex OBJECT-TYPE
    SYNTAX SnmpAdminString
    ACCESS read-only
    STATUS mandatory
    DESCRIPTION
        "Moid of the Host which has this Port Group"
    ::= { vmvcAimStatPortGrpEntry  3}

vmvcAimStatPGVlanId OBJECT-TYPE
    SYNTAX SnmpAdminString
    ACCESS read-only
    STATUS mandatory
    DESCRIPTION
        "The VLAN ID for ports using this port "
    ::= { vmvcAimStatPortGrpEntry  4}

vmvcAimStatPGVSwitchName OBJECT-TYPE
    SYNTAX SnmpAdminString
    ACCESS read-only
    STATUS mandatory
    DESCRIPTION
        "The virtual switch on which this port group is located"
    ::= { vmvcAimStatPortGrpEntry  5}

vmvcAimStatPGPorts OBJECT-TYPE
    SYNTAX SnmpAdminString
    ACCESS read-only
    STATUS mandatory
    DESCRIPTION
        "Array of The ports that currently exist and are used on this port group. "
    ::= { vmvcAimStatPortGrpEntry  6}

vmvcAimStatPGPolicyOffloadCkhSum OBJECT-TYPE
    SYNTAX INTEGER
    ACCESS read-only
    STATUS mandatory
    DESCRIPTION
        "The flag to indicate whether or not checksum offloading is supported."
    ::= { vmvcAimStatPortGrpEntry  7}

vmvcAimStatPGPolicyOffloadtcpSegmt OBJECT-TYPE
    SYNTAX INTEGER
    ACCESS read-only
    STATUS mandatory
    DESCRIPTION
        "The flag to indicate whether or not TCP segmentation offloading (TSO) is supported."
    ::= { vmvcAimStatPortGrpEntry  8}

vmvcAimStatPGPolicyOffloadZeroCpyX OBJECT-TYPE
    SYNTAX INTEGER
    ACCESS read-only
    STATUS mandatory
    DESCRIPTION
        "The flag to indicate whether or not zero copy transmits are supported."
    ::= { vmvcAimStatPortGrpEntry  9}

vmvcAimStatPGPolicySecurityAllowPromis OBJECT-TYPE
    SYNTAX INTEGER
    ACCESS read-only
    STATUS mandatory
    DESCRIPTION
        "The flag to indicate whether or not all traffic is seen on the port."
    ::= { vmvcAimStatPortGrpEntry  10}

vmvcAimStatPGPolicySecurityForgedTransmit OBJECT-TYPE
    SYNTAX INTEGER
    ACCESS read-only
    STATUS mandatory
    DESCRIPTION
        "The flag to indicate whether or not the virtual network adapter should be allowed to send network traffic with a different MAC address than that of the virtual network adapter."
    ::= { vmvcAimStatPortGrpEntry  11}

vmvcAimStatPGPolicySecurityMACChanges OBJECT-TYPE
    SYNTAX INTEGER
    ACCESS read-only
    STATUS mandatory
    DESCRIPTION
        "The flag to indicate whether or not the Media Access Control (MAC) address can be changed"
    ::= { vmvcAimStatPortGrpEntry  12}

vmvcAimStatPGHostName OBJECT-TYPE
    SYNTAX SnmpAdminString
    ACCESS read-only
    STATUS mandatory
    DESCRIPTION
        "Name of the Host which has this Port Group"
    ::= { vmvcAimStatPortGrpEntry  13}

vmvcAimStatPGVSwitchUID OBJECT-TYPE
    SYNTAX INTEGER (1..2147483647)
    ACCESS read-only
    STATUS mandatory
    DESCRIPTION
        "UID of the Virtual Switch this Port Group is associated with."
    ::= { vmvcAimStatPortGrpEntry  14}

vmvcAimStatPGPolicyShapingAvgBandWidth OBJECT-TYPE
    SYNTAX INTEGER
    ACCESS read-only
    STATUS mandatory
    DESCRIPTION
        "The average bandwidth in bits per second if shaping is enabled on the port."
    ::= { vmvcAimStatPortGrpEntry  15}

vmvcAimStatPGPolicyShapingBurstSize OBJECT-TYPE
    SYNTAX INTEGER
    ACCESS read-only
    STATUS mandatory
    DESCRIPTION
        "The maximum burst size allowed in bytes if shaping is enabled on the port"
    ::= { vmvcAimStatPortGrpEntry  16}

vmvcAimStatPGPolicyShapingEnabled OBJECT-TYPE
    SYNTAX INTEGER{
        false(1),
        true(2)
    }
    ACCESS read-only
    STATUS mandatory
    DESCRIPTION
        "The flag to indicate whether or not traffic shaper is enabled on the port"
    ::= { vmvcAimStatPortGrpEntry  17}

vmvcAimStatPGPolicyShapingPeakBandWidth OBJECT-TYPE
    SYNTAX INTEGER
    ACCESS read-only
    STATUS mandatory
    DESCRIPTION
        "The peak bandwidth during bursts in bits per second if traffic shaping is enabled on the port."
    ::= { vmvcAimStatPortGrpEntry  18}

vmvcAimStatPGNicTeamAvailableNic OBJECT-TYPE
    SYNTAX SnmpAdminString
    ACCESS read-only
    STATUS mandatory
    DESCRIPTION
        "List of available network adapters used for load balancing."
    ::= { vmvcAimStatPortGrpEntry  19}

vmvcAimStatPGNicTeamActiveNic OBJECT-TYPE
    SYNTAX SnmpAdminString
    ACCESS read-only
    STATUS mandatory
    DESCRIPTION
        "List of active network adapters used for load balancing."
    ::= { vmvcAimStatPortGrpEntry  20}

vmvcAimStatPGNicTeamStandByNic OBJECT-TYPE
    SYNTAX SnmpAdminString
    ACCESS read-only
    STATUS mandatory
    DESCRIPTION
        "Standby network adapters used for failover"
    ::= { vmvcAimStatPortGrpEntry  21}

vmvcAimStatPGNicTeamNotifySwitch OBJECT-TYPE
    SYNTAX INTEGER{
        false(1),
        true(2)
    }
    ACCESS read-only
    STATUS mandatory
    DESCRIPTION
        "Flag to specify whether or not to notify the physical switch if a link fails"
    ::= { vmvcAimStatPortGrpEntry  22}

vmvcAimStatPGNicTeamPolicy OBJECT-TYPE
    SYNTAX SnmpAdminString
    ACCESS read-only
    STATUS mandatory
    DESCRIPTION
        "Network adapter teaming policy which includes failover and load balancing."
    ::= { vmvcAimStatPortGrpEntry  23}

vmvcAimStatPGNicTeamReversePolicy OBJECT-TYPE
    SYNTAX INTEGER{
        false(1),
        true(2)
    }
    ACCESS read-only
    STATUS mandatory
    DESCRIPTION
        "The flag to indicate whether or not the teaming policy is applied to inbound frames as well."
    ::= { vmvcAimStatPortGrpEntry  24}

vmvcAimStatPGNicTeamRollingOrder OBJECT-TYPE
    SYNTAX INTEGER{
        false(1),
        true(2)
    }
    ACCESS read-only
    STATUS mandatory
    DESCRIPTION
        "The flag to indicate whether or not to use a rolling policy when restoring links"
    ::= { vmvcAimStatPortGrpEntry  25}

vmvcAimStatPGNicTeamFailureChkBeacon OBJECT-TYPE
    SYNTAX INTEGER{
        false(1),
        true(2)
    }
    ACCESS read-only
    STATUS mandatory
    DESCRIPTION
        "flag to enable beacon probing as a method to validate the link status of a physical network  "
    ::= { vmvcAimStatPortGrpEntry  26}

vmvcAimStatPGNicTeamFailureChkDuplex OBJECT-TYPE
    SYNTAX INTEGER{
        false(1),
        true(2)
    }
    ACCESS read-only
    STATUS mandatory
    DESCRIPTION
        "flag to indicate whether or not to use the link duplex reported by the driver as link selection criteria"
    ::= { vmvcAimStatPortGrpEntry  27}

vmvcAimStatPGNicTeamFailureChkErrPct OBJECT-TYPE
    SYNTAX INTEGER{
        false(1),
        true(2)
    }
    ACCESS read-only
    STATUS mandatory
    DESCRIPTION
        "flag to indicate whether or not to use link error percentage to detect failure."
    ::= { vmvcAimStatPortGrpEntry  28}

vmvcAimStatPGNicTeamFailureChkSpeed OBJECT-TYPE
    SYNTAX SnmpAdminString
    ACCESS read-only
    STATUS mandatory
    DESCRIPTION
        "Switch Nic Team Failure Check Speed."
    ::= { vmvcAimStatPortGrpEntry  29}

vmvcAimStatPGNicTeamFailureFullDuplex OBJECT-TYPE
    SYNTAX INTEGER{
        false(1),
        true(2)
    }
    ACCESS read-only
    STATUS mandatory
    DESCRIPTION
        "Configured duplexity"
    ::= { vmvcAimStatPortGrpEntry  30}

vmvcAimStatPGNicTeamFailurePercentage OBJECT-TYPE
    SYNTAX INTEGER
    ACCESS read-only
    STATUS mandatory
    DESCRIPTION
        "Configured percentage"
    ::= { vmvcAimStatPortGrpEntry  31}

vmvcAimStatPGNicTeamFailureSpeed OBJECT-TYPE
    SYNTAX INTEGER
    ACCESS read-only
    STATUS mandatory
    DESCRIPTION
        "Configured speed"
    ::= { vmvcAimStatPortGrpEntry  32}

vmvcAimStatPGVCUID OBJECT-TYPE
    SYNTAX INTEGER
    ACCESS read-only
    STATUS mandatory
    DESCRIPTION
        "VC Instance SNMP UID where this Port Group resides."
    ::= { vmvcAimStatPortGrpEntry 33 }

vmvcAimStatPGVCName OBJECT-TYPE
    SYNTAX SnmpAdminString
    ACCESS read-only
    STATUS mandatory
    DESCRIPTION
        "VC Instance where this Port Group resides."
    ::= { vmvcAimStatPortGrpEntry 34 }

vmvcAimStatPGVCUUID OBJECT-TYPE
    SYNTAX SnmpAdminString
    ACCESS read-only
    STATUS mandatory
    DESCRIPTION
        "The vCenter-specific UUID where this Port Group resides."
    ::= { vmvcAimStatPortGrpEntry 35 }


-- *****************************************************************************
-- Status PNIC Group
-- *****************************************************************************
vmvcAimStatPNICCount OBJECT-TYPE
    SYNTAX INTEGER
    ACCESS read-only
    STATUS mandatory
    DESCRIPTION
        "Physical NIC count in vmvcAimStatPNICTable."
    ::= { vmvcAimStatPNICGroup 1}

vmvcAimStatPNICTable OBJECT-TYPE
    SYNTAX SEQUENCE OF VmvcAimStatPNICRow
    ACCESS not-accessible
    STATUS mandatory
    DESCRIPTION
        "Physical NIC table."
    ::= { vmvcAimStatPNICGroup 2 }

vmvcAimStatPNICEntry OBJECT-TYPE
    SYNTAX VmvcAimStatPNICRow
    ACCESS not-accessible
    STATUS mandatory
    DESCRIPTION
        "The table entry."
    INDEX { vmvcAimStatPNICUID }
    ::= { vmvcAimStatPNICTable 1 }

VmvcAimStatPNICRow ::=
    SEQUENCE {
        vmvcAimStatPNICUID              INTEGER,
        vmvcAimStatPNICIndex            SnmpAdminString,
        vmvcAimStatPNICHost             SnmpAdminString,
        vmvcAimStatPNICName             SnmpAdminString,
        vmvcAimStatPNICPCI              SnmpAdminString,
        vmvcAimStatPNICVendor           SnmpAdminString,
        vmvcAimStatPNICDriver           SnmpAdminString,
        vmvcAimStatPNICIPIsDHCP         INTEGER,
        vmvcAimStatPNICIP               SnmpAdminString,
        vmvcAimStatPNICSubnetmask       SnmpAdminString,
        vmvcAimStatPNICLinkSpeedDuplex  INTEGER,
        vmvcAimStatPNICLinkSpeedSpeedMb INTEGER,
        vmvcAimStatPNICVirtualSwitch    SnmpAdminString,
        vmvcAimStatPNICLinkState        INTEGER,
        vmvcAimStatPNICMonitor          INTEGER,
        vmvcAimStatPNICAlert            INTEGER,
        vmvcAimStatPNICState            INTEGER,
        vmvcAimStatPNICHostName         SnmpAdminString,
        vmvcAimStatPNICPktTxt           INTEGER,
        vmvcAimStatPNICPktTxtPerSec     INTEGER,
        vmvcAimStatPNICPktRcvd          INTEGER,
        vmvcAimStatPNICPktRcvdPerSec    INTEGER,
        vmvcAimStatPNICKBPSTxt          INTEGER,
        vmvcAimStatPNICKBPSTxtPerSec    INTEGER,
        vmvcAimStatPNICKBPSRcvd         INTEGER,
        vmvcAimStatPNICKBPSRcvdPerSec   INTEGER,
        vmvcAimStatPNICMAC              SnmpAdminString,
        vmvcAimStatPNICVSwitchUID       INTEGER,
        vmvcAimStatPNICVCUID            INTEGER,
        vmvcAimStatPNICVCName           SnmpAdminString,
        vmvcAimStatPNICDVUplinkPGIndex  SnmpAdminString,
        vmvcAimStatPNICDVPortGroupUID   INTEGER,
        vmvcAimStatPNICDVPortKey        SnmpAdminString,
        vmvcAimStatPNICDVUplink         SnmpAdminString,
        vmvcAimStatPNICVCUUID           SnmpAdminString
    }

vmvcAimStatPNICUID OBJECT-TYPE
    SYNTAX INTEGER (1..2147483647)
    ACCESS read-only
    STATUS mandatory
    DESCRIPTION
        "UID of PNIC"
    ::= { vmvcAimStatPNICEntry  1}

vmvcAimStatPNICIndex OBJECT-TYPE
    SYNTAX SnmpAdminString
    ACCESS read-only
    STATUS mandatory
    DESCRIPTION
        "MOID of PNIC"
    ::= { vmvcAimStatPNICEntry  2}

vmvcAimStatPNICHost OBJECT-TYPE
    SYNTAX SnmpAdminString
    ACCESS read-only
    STATUS mandatory
    DESCRIPTION
        "PNIC Host"
    ::= { vmvcAimStatPNICEntry  3}

vmvcAimStatPNICName OBJECT-TYPE
    SYNTAX SnmpAdminString
    ACCESS read-only
    STATUS mandatory
    DESCRIPTION
        "Name of the physical nic "
    ::= { vmvcAimStatPNICEntry  4}

vmvcAimStatPNICPCI OBJECT-TYPE
    SYNTAX SnmpAdminString
    ACCESS read-only
    STATUS mandatory
    DESCRIPTION
        "Device hash of the PCI device corresponding to this physical network adapter"
    ::= { vmvcAimStatPNICEntry  5}

vmvcAimStatPNICVendor OBJECT-TYPE
    SYNTAX SnmpAdminString
    ACCESS read-only
    STATUS mandatory
    DESCRIPTION
        "Device vendor.
         Note TCPIP configuration of ESX host PNIC is optional and may be empty."
    ::= { vmvcAimStatPNICEntry  6}

vmvcAimStatPNICDriver OBJECT-TYPE
    SYNTAX SnmpAdminString
    ACCESS read-only
    STATUS mandatory
    DESCRIPTION
        "The name of the driver"
    ::= { vmvcAimStatPNICEntry  7}

vmvcAimStatPNICIPIsDHCP OBJECT-TYPE
    SYNTAX INTEGER
    ACCESS read-only
    STATUS mandatory
    DESCRIPTION
        "The flag to indicate whether or not DHCP (dynamic host control protocol) is enabled"
    ::= { vmvcAimStatPNICEntry  8}

vmvcAimStatPNICIP OBJECT-TYPE
    SYNTAX SnmpAdminString
    ACCESS read-only
    STATUS mandatory
    DESCRIPTION
        "The IP address currently used by the network adapter.
         Note TCPIP configuration of ESX host PNIC is optional and may be empty."
    ::= { vmvcAimStatPNICEntry  9}

vmvcAimStatPNICSubnetmask OBJECT-TYPE
    SYNTAX SnmpAdminString
    ACCESS read-only
    STATUS mandatory
    DESCRIPTION
        "The subnet mask.
         Note TCPIP configuration of ESX host PNIC is optional and maybe empty."
    ::= { vmvcAimStatPNICEntry  10}

vmvcAimStatPNICLinkSpeedDuplex OBJECT-TYPE
    SYNTAX INTEGER
    ACCESS read-only
    STATUS mandatory
    DESCRIPTION
        "The flag to indicate whether or not the link is capable of full-duplex (enabled) or only half-duplex (disabled)."
    ::= { vmvcAimStatPNICEntry  11}

vmvcAimStatPNICLinkSpeedSpeedMb OBJECT-TYPE
    SYNTAX INTEGER
    ACCESS read-only
    STATUS mandatory
    DESCRIPTION
        "The bit rate ( Mhz) on the link"
    ::= { vmvcAimStatPNICEntry  12}

vmvcAimStatPNICVirtualSwitch OBJECT-TYPE
    SYNTAX SnmpAdminString
    ACCESS read-only
    STATUS mandatory
    DESCRIPTION
        "Virtual Switch that PNIC is assigned to.  Only applies to 
         Standard Virtual Switches."
    ::= { vmvcAimStatPNICEntry  13}

vmvcAimStatPNICLinkState OBJECT-TYPE
    SYNTAX INTEGER
    ACCESS read-only
    STATUS mandatory
    DESCRIPTION
        "PNIC Link State.Can be link-down(0), link-up(1)."
    ::= { vmvcAimStatPNICEntry  14}

vmvcAimStatPNICMonitor OBJECT-TYPE
    SYNTAX INTEGER{
        do-not-monitor(1),
        monitor(2)
        }
    ACCESS read-write
    STATUS mandatory
    DESCRIPTION
        "The flag to indicate whether or not PNIC has to be monitored(2) or not(1)."
    DEFVAL {2 }
    ::= { vmvcAimStatPNICEntry  15}

vmvcAimStatPNICAlert OBJECT-TYPE
    SYNTAX INTEGER{
        link-down-warn(1),
        link-down-crit(2)
        }
    ACCESS read-write
    STATUS mandatory
    DESCRIPTION
        "PNIC Alert if it is warning or critical "
    DEFVAL {2 }
    ::= { vmvcAimStatPNICEntry  16}

vmvcAimStatPNICState OBJECT-TYPE
    SYNTAX INTEGER {
        unknown(1),
        ok(2),
        warning(3),
        critical(4)
    }
    ACCESS read-only
    STATUS mandatory
    DESCRIPTION
        "PNIC Link State.Can be link-down, link-up."
    ::= { vmvcAimStatPNICEntry  17}

vmvcAimStatPNICHostName OBJECT-TYPE
    SYNTAX SnmpAdminString
    ACCESS read-only
    STATUS mandatory
    DESCRIPTION
        "PNIC Host Name"
    ::= { vmvcAimStatPNICEntry  18}
    
vmvcAimStatPNICPktTxt OBJECT-TYPE
    SYNTAX INTEGER
    ACCESS read-only
    STATUS mandatory
    DESCRIPTION
        "The number of Packets transmitted."
    ::= { vmvcAimStatPNICEntry 19 }

vmvcAimStatPNICPktTxtPerSec OBJECT-TYPE
    SYNTAX INTEGER
    ACCESS read-only
    STATUS mandatory
    DESCRIPTION
        "Packets transmitted per Second."
    ::= { vmvcAimStatPNICEntry  20}

vmvcAimStatPNICPktRcvd OBJECT-TYPE
    SYNTAX INTEGER
    ACCESS read-only
    STATUS mandatory
    DESCRIPTION
        "The number of Packets recieved."
    ::= { vmvcAimStatPNICEntry 21 }

vmvcAimStatPNICPktRcvdPerSec OBJECT-TYPE
    SYNTAX INTEGER
    ACCESS read-only
    STATUS mandatory
    DESCRIPTION
        "Packets recieved per Second."
    ::= { vmvcAimStatPNICEntry  22}

vmvcAimStatPNICKBPSTxt OBJECT-TYPE
    SYNTAX INTEGER
    ACCESS read-only
    STATUS mandatory
    DESCRIPTION
        "KBPS transmitted"
    ::= { vmvcAimStatPNICEntry 23 }

vmvcAimStatPNICKBPSTxtPerSec OBJECT-TYPE
    SYNTAX INTEGER
    ACCESS read-only
    STATUS mandatory
    DESCRIPTION
        "KBPS transmitted per Second."
    ::= { vmvcAimStatPNICEntry  24}

vmvcAimStatPNICKBPSRcvd OBJECT-TYPE
    SYNTAX INTEGER
    ACCESS read-only
    STATUS mandatory
    DESCRIPTION
        "KBPS recieved."
    ::= { vmvcAimStatPNICEntry 25 }

vmvcAimStatPNICKBPSRcvdPerSec OBJECT-TYPE
    SYNTAX INTEGER
    ACCESS read-only
    STATUS mandatory
    DESCRIPTION
        "KBPS recieved per Second."
    ::= { vmvcAimStatPNICEntry  26}

vmvcAimStatPNICMAC OBJECT-TYPE
    SYNTAX SnmpAdminString
    ACCESS read-only
    STATUS mandatory
    DESCRIPTION
        "The MAC address used by the network adapter."
    ::= { vmvcAimStatPNICEntry  27}

vmvcAimStatPNICVSwitchUID OBJECT-TYPE
    SYNTAX INTEGER (1..2147483647)
    ACCESS read-only
    STATUS mandatory
    DESCRIPTION
        "UID of the Virtual Switch this PNIC is associated with.  Only applies 
         to Standard Virtual Switches (zero otherwise)."
    ::= { vmvcAimStatPNICEntry  28}

vmvcAimStatPNICVCUID OBJECT-TYPE
    SYNTAX INTEGER
    ACCESS read-only
    STATUS mandatory
    DESCRIPTION
        "VC Instance SNMP UID where this PNIC resides."
    ::= { vmvcAimStatPNICEntry 29 }

vmvcAimStatPNICVCName OBJECT-TYPE
    SYNTAX SnmpAdminString
    ACCESS read-only
    STATUS mandatory
    DESCRIPTION
        "VC Instance where this PNIC resides."
    ::= { vmvcAimStatPNICEntry 30 }

vmvcAimStatPNICDVUplinkPGIndex OBJECT-TYPE
    SYNTAX SnmpAdminString
    ACCESS read-only
    STATUS mandatory
    DESCRIPTION
        "DV Uplink Port Group MOID where this PNIC is connected.  Only applies to 
         PNICs connected to Distributed Virtual Switches."
    ::= { vmvcAimStatPNICEntry 31 }

vmvcAimStatPNICDVPortGroupUID OBJECT-TYPE
    SYNTAX INTEGER (1..2147483647)
    ACCESS read-only
    STATUS mandatory
    DESCRIPTION
        "UID of the DV Port Group where this PNIC is connected.  Only applies to 
         Distributed Virtual Switches (zero otherwise)."
    ::= { vmvcAimStatPNICEntry 32 }

vmvcAimStatPNICDVPortKey OBJECT-TYPE
    SYNTAX SnmpAdminString
    ACCESS read-only
    STATUS mandatory
    DESCRIPTION
        "DV Port Key ID where this PNIC is connected.  Only applies to 
         Distributed Virtual Switches."
    ::= { vmvcAimStatPNICEntry 33 }

vmvcAimStatPNICDVUplink OBJECT-TYPE
    SYNTAX SnmpAdminString
    ACCESS read-only
    STATUS mandatory
    DESCRIPTION
        "DV Uplink Name (within the Uplink Port Group) where this PNIC is connected.
         Only applies to Distributed Virtual Switches."
    ::= { vmvcAimStatPNICEntry 34 }

vmvcAimStatPNICVCUUID OBJECT-TYPE
    SYNTAX SnmpAdminString
    ACCESS read-only
    STATUS mandatory
    DESCRIPTION
        "The vCenter-specific UUID where this PNIC resides."
    ::= { vmvcAimStatPNICEntry 35 }


-- *****************************************************************************
-- Status Host VNIC Group
-- *****************************************************************************
vmvcAimStatHostVNICCount OBJECT-TYPE
    SYNTAX INTEGER
    ACCESS read-only
    STATUS mandatory
    DESCRIPTION
        "Host Virtual NIC count in vmvcAimStatVNICTable."
    ::= { vmvcAimStatHostVNICGroup 1}

vmvcAimStatHostVNICTable OBJECT-TYPE
    SYNTAX SEQUENCE OF VmvcAimStatHostVNICRow
    ACCESS not-accessible
    STATUS mandatory
    DESCRIPTION
        "Port Group."
    ::= { vmvcAimStatHostVNICGroup 2 }

vmvcAimStatHostVNICEntry OBJECT-TYPE
    SYNTAX VmvcAimStatHostVNICRow
    ACCESS not-accessible
    STATUS mandatory
    DESCRIPTION
        "The table entry."
    INDEX { vmvcAimStatHostVNICUID }
    ::= { vmvcAimStatHostVNICTable 1 }

VmvcAimStatHostVNICRow ::=
    SEQUENCE {
        vmvcAimStatHostVNICUID              INTEGER,
        vmvcAimStatHostVNICName             SnmpAdminString,
        vmvcAimStatHostVNICHostIndex        SnmpAdminString,
        vmvcAimStatHostVNICPortgroup        SnmpAdminString,
        vmvcAimStatHostVNICMAC              SnmpAdminString,
        vmvcAimStatHostVNICIp               SnmpAdminString,
        vmvcAimStatHostVNICHostName         SnmpAdminString,
        vmvcAimStatHostVNICType             INTEGER,
        vmvcAimStatHostVNICPortGroupUID     INTEGER,
        vmvcAimStatHostVNICIpV6             SnmpAdminString,
        vmvcAimStatHostVNICVCUID            INTEGER,
        vmvcAimStatHostVNICVCName           SnmpAdminString,
        vmvcAimStatHostVNICDVPortGroupIndex SnmpAdminString,
        vmvcAimStatHostVNICDVPortGroupUID   INTEGER,
        vmvcAimStatHostVNICDVPortKey        SnmpAdminString,
        vmvcAimStatHostVNICVCUUID           SnmpAdminString
    }

vmvcAimStatHostVNICUID OBJECT-TYPE
    SYNTAX INTEGER (1..2147483647)
    ACCESS read-only
    STATUS mandatory
    DESCRIPTION
        "UID of the virtual nic"
    ::= { vmvcAimStatHostVNICEntry  1}

vmvcAimStatHostVNICName OBJECT-TYPE
    SYNTAX SnmpAdminString
    ACCESS read-only
    STATUS mandatory
    DESCRIPTION
        "Name of the virtual nic"
    ::= { vmvcAimStatHostVNICEntry  2}

vmvcAimStatHostVNICHostIndex OBJECT-TYPE
    SYNTAX SnmpAdminString
    ACCESS read-only
    STATUS mandatory
    DESCRIPTION
        "Moid of Host which has this VNIC"
    ::= { vmvcAimStatHostVNICEntry  3}

vmvcAimStatHostVNICPortgroup OBJECT-TYPE
    SYNTAX SnmpAdminString
    ACCESS read-only
    STATUS mandatory
    DESCRIPTION
        "The portgroup that is connected.  This applies only to VNICs attached to a standard Virtual Switch."
    ::= { vmvcAimStatHostVNICEntry  4}

vmvcAimStatHostVNICMAC OBJECT-TYPE
    SYNTAX SnmpAdminString
    ACCESS read-only
    STATUS mandatory
    DESCRIPTION
        "The media access control (MAC) address of the virtual network adapter"
    ::= { vmvcAimStatHostVNICEntry  5}

vmvcAimStatHostVNICIp OBJECT-TYPE
    SYNTAX SnmpAdminString
    ACCESS read-only
    STATUS mandatory
    DESCRIPTION
        "The IP address currently used by the network adapter. "
    ::= { vmvcAimStatHostVNICEntry  6}

vmvcAimStatHostVNICHostName OBJECT-TYPE
    SYNTAX SnmpAdminString
    ACCESS read-only
    STATUS mandatory
    DESCRIPTION
        "Name of Host which has this VNIC"
    ::= { vmvcAimStatHostVNICEntry  7}

vmvcAimStatHostVNICType OBJECT-TYPE
    SYNTAX INTEGER {
        unknown(1),
        serviceConsole(2),
        vmKernel(3)
    }
    ACCESS read-only
    STATUS mandatory
    DESCRIPTION
        "Type of Host VNIC.  This is a standard enumeration."
    ::= { vmvcAimStatHostVNICEntry 8 }

vmvcAimStatHostVNICPortGroupUID OBJECT-TYPE
    SYNTAX INTEGER (1..2147483647)
    ACCESS read-only
    STATUS mandatory
    DESCRIPTION
        "UID of the Port Group this Host VNIC is associated with.  This applies only to VNICs attached to a 
         standard Virtual Switch (zero otherwise)."
    ::= { vmvcAimStatHostVNICEntry 9 }

vmvcAimStatHostVNICIpV6 OBJECT-TYPE
    SYNTAX SnmpAdminString
    ACCESS read-only
    STATUS mandatory
    DESCRIPTION
        "The IPV6 address currently used by the network adapter."
    ::= { vmvcAimStatHostVNICEntry 10 }

vmvcAimStatHostVNICVCUID OBJECT-TYPE
    SYNTAX INTEGER
    ACCESS read-only
    STATUS mandatory
    DESCRIPTION
        "VC Instance SNMP UID where this Host VNIC resides."
    ::= { vmvcAimStatHostVNICEntry 11 }

vmvcAimStatHostVNICVCName OBJECT-TYPE
    SYNTAX SnmpAdminString
    ACCESS read-only
    STATUS mandatory
    DESCRIPTION
        "VC Instance where this Host VNIC resides."
    ::= { vmvcAimStatHostVNICEntry 12 }

vmvcAimStatHostVNICDVPortGroupIndex OBJECT-TYPE
    SYNTAX SnmpAdminString
    ACCESS read-only
    STATUS mandatory
    DESCRIPTION
        "The DV Port Group MOID that is connected.  This applies only to VNICs attached 
         to a Distributed Virtual Switch."
    ::= { vmvcAimStatHostVNICEntry 13 }

vmvcAimStatHostVNICDVPortGroupUID OBJECT-TYPE
    SYNTAX INTEGER (1..2147483647)
    ACCESS read-only
    STATUS mandatory
    DESCRIPTION
        "UID of the DV Port Group this Host VNIC is associated with.  This applies only 
         to VNICs attached to a Distributed Virtual Switch (zero otherwise)."
    ::= { vmvcAimStatHostVNICEntry 14 }

vmvcAimStatHostVNICDVPortKey OBJECT-TYPE
    SYNTAX SnmpAdminString
    ACCESS read-only
    STATUS mandatory
    DESCRIPTION
        "The DV Port Key ID that is connected.  This applies only to VNICs attached to a 
         Distributed Virtual Switch."
    ::= { vmvcAimStatHostVNICEntry 15 }

vmvcAimStatHostVNICVCUUID OBJECT-TYPE
    SYNTAX SnmpAdminString
    ACCESS read-only
    STATUS mandatory
    DESCRIPTION
        "The vCenter-specific UUID where this Host VNIC resides."
    ::= { vmvcAimStatHostVNICEntry 16 }


-- *****************************************************************************
-- Status VM VNIC Group
-- *****************************************************************************
vmvcAimStatVMVNICCount OBJECT-TYPE
    SYNTAX INTEGER
    ACCESS read-only
    STATUS mandatory
    DESCRIPTION
        "VM Virtual NIC count in vmvcAimStatVMVNICTable."
    ::= { vmvcAimStatVMVNICGroup 1}

vmvcAimStatVMVNICTable OBJECT-TYPE
    SYNTAX SEQUENCE OF VmvcAimStatVMVNICRow
    ACCESS not-accessible
    STATUS mandatory
    DESCRIPTION
        "VM Virtual NIC table."
    ::= { vmvcAimStatVMVNICGroup 2 }

vmvcAimStatVMVNICEntry OBJECT-TYPE
    SYNTAX VmvcAimStatVMVNICRow
    ACCESS not-accessible
    STATUS mandatory
    DESCRIPTION
        "The table entry."
    INDEX { vmvcAimStatVMVNICUID }
    ::= { vmvcAimStatVMVNICTable 1 }

VmvcAimStatVMVNICRow ::=
    SEQUENCE {
        vmvcAimStatVMVNICUID                INTEGER,
        vmvcAimStatVMVNICDeviceId           SnmpAdminString,
        vmvcAimStatVMVNICVMIndex            SnmpAdminString,
        vmvcAimStatVMVNICVMName             SnmpAdminString,
        vmvcAimStatVMVNICName               SnmpAdminString,
        vmvcAimStatVMVNICPortgroup          SnmpAdminString,
        vmvcAimStatVMVNICMAC                SnmpAdminString,
        vmvcAimStatVMVNICIp                 SnmpAdminString,
        vmvcAimStatVMVNICConnected          INTEGER,
        vmvcAimStatVMVNICPktTxt             Gauge,
        vmvcAimStatVMVNICPktRcvd            Gauge,
        vmvcAimStatVMVNICKBPSTxt            Gauge,
        vmvcAimStatVMVNICKBPSRcvd           Gauge,
        vmvcAimStatVMVNICMonitor            INTEGER,
        vmvcAimStatVMVNICAlert              INTEGER,        
        vmvcAimStatVMVNICState              INTEGER,
        vmvcAimStatVMVNICPktTxtPerSec       Gauge,
        vmvcAimStatVMVNICPktRcvdPerSec      Gauge,
        vmvcAimStatVMVNICKBPSTxtPerSec      Gauge,
        vmvcAimStatVMVNICKBPSRcvdPerSec     Gauge,
        vmvcAimStatVMVNICPortGroupUID       INTEGER,
        vmvcAimStatVMVNICVCUID              INTEGER,
        vmvcAimStatVMVNICVCName             SnmpAdminString,
        vmvcAimStatVMVNICDVPortGroupIndex   SnmpAdminString,
        vmvcAimStatVMVNICDVPortGroupUID     INTEGER,
        vmvcAimStatVMVNICDVPortKey          SnmpAdminString,
        vmvcAimStatVMVNICDeviceSummary      SnmpAdminString,
        vmvcAimStatVMVNICHostName           SnmpAdminString,
        vmvcAimStatVMVNICVCUUID             SnmpAdminString
    }

vmvcAimStatVMVNICUID OBJECT-TYPE
    SYNTAX INTEGER (1..2147483647)
    ACCESS read-only
    STATUS mandatory
    DESCRIPTION
        "VNIC device UID."
    ::= { vmvcAimStatVMVNICEntry 1 }

vmvcAimStatVMVNICDeviceId OBJECT-TYPE
    SYNTAX SnmpAdminString
    ACCESS read-only
    STATUS mandatory
    DESCRIPTION
        "VNIC device ID."
    ::= { vmvcAimStatVMVNICEntry 2 }

vmvcAimStatVMVNICVMIndex OBJECT-TYPE
    SYNTAX SnmpAdminString
    ACCESS read-only
    STATUS mandatory
    DESCRIPTION
        "Moid of the virtual machine this Device is connected to.."
    ::= { vmvcAimStatVMVNICEntry 3 }

vmvcAimStatVMVNICVMName OBJECT-TYPE
    SYNTAX SnmpAdminString
    ACCESS read-only
    STATUS mandatory
    DESCRIPTION
        "Name of the virtual machine this Device is connected to.."
    ::= { vmvcAimStatVMVNICEntry 4 }

vmvcAimStatVMVNICName OBJECT-TYPE
    SYNTAX SnmpAdminString
    ACCESS read-only
    STATUS mandatory
    DESCRIPTION
        "Name of the VMNIC Device "
    ::= { vmvcAimStatVMVNICEntry 5 }

vmvcAimStatVMVNICPortgroup OBJECT-TYPE
    SYNTAX SnmpAdminString
    ACCESS read-only
    STATUS mandatory
    DESCRIPTION
        "The network name to which the device belongs to.  Applies to standard port groups only."
    ::= { vmvcAimStatVMVNICEntry 6 }

vmvcAimStatVMVNICMAC OBJECT-TYPE
    SYNTAX SnmpAdminString
    ACCESS read-only
    STATUS mandatory
    DESCRIPTION
        "The media access control (MAC) address of the virtual network adapter>."
    ::= { vmvcAimStatVMVNICEntry 7 }

vmvcAimStatVMVNICIp OBJECT-TYPE
    SYNTAX SnmpAdminString
    ACCESS read-only
    STATUS mandatory
    DESCRIPTION
        "The IP address currently used by the network adapter. All IP addresses are specified using IPv4 dot notation.."
    ::= { vmvcAimStatVMVNICEntry 8 }

vmvcAimStatVMVNICConnected OBJECT-TYPE
    SYNTAX INTEGER
    ACCESS read-only
    STATUS mandatory
    DESCRIPTION
        "The flag indicating Whether  VNIC is connected or not."
    ::= { vmvcAimStatVMVNICEntry 9 }

vmvcAimStatVMVNICPktTxt OBJECT-TYPE
    SYNTAX Gauge
    ACCESS read-only
    STATUS mandatory
    DESCRIPTION
        "The number of Packets transmitted."
    ::= { vmvcAimStatVMVNICEntry 10 }

vmvcAimStatVMVNICPktRcvd OBJECT-TYPE
    SYNTAX Gauge
    ACCESS read-only
    STATUS mandatory
    DESCRIPTION
        "The number of Packets received."
    ::= { vmvcAimStatVMVNICEntry 11 }

vmvcAimStatVMVNICKBPSTxt OBJECT-TYPE
    SYNTAX Gauge
    ACCESS read-only
    STATUS mandatory
    DESCRIPTION
        "KBPS transmitted."
    ::= { vmvcAimStatVMVNICEntry 12 }

vmvcAimStatVMVNICKBPSRcvd OBJECT-TYPE
    SYNTAX Gauge
    ACCESS read-only
    STATUS mandatory
    DESCRIPTION
        "KBPS received."
    ::= { vmvcAimStatVMVNICEntry 13 }

vmvcAimStatVMVNICMonitor OBJECT-TYPE
    SYNTAX INTEGER {
        do-not-monitor(1),
        monitor(2)
    }
    ACCESS read-write
    STATUS mandatory
    DESCRIPTION
        "The flag indicating Whether to monitor the VNIC or not."
    DEFVAL { 2 }
    ::= { vmvcAimStatVMVNICEntry 14 }

vmvcAimStatVMVNICAlert OBJECT-TYPE
    SYNTAX INTEGER {
        disconnected-warn(1),
        disconnected-critical(2)
    }
    ACCESS read-write
    STATUS mandatory
    DESCRIPTION
        "Level for the alert"
    DEFVAL { 2 }
    ::= { vmvcAimStatVMVNICEntry 15 }

vmvcAimStatVMVNICState OBJECT-TYPE
    SYNTAX INTEGER {
        unknown(1),
        ok(2),
        warning(3),
        critical(4)
    }
    ACCESS read-only
    STATUS mandatory
    DESCRIPTION
        "VNIC State.Can be ok,warning or critical"
    ::= { vmvcAimStatVMVNICEntry 16 }

vmvcAimStatVMVNICPktTxtPerSec OBJECT-TYPE
    SYNTAX Gauge
    ACCESS read-only
    STATUS mandatory
    DESCRIPTION
        "The number of Packets transmitted per sec."
    ::= { vmvcAimStatVMVNICEntry 17 }

vmvcAimStatVMVNICPktRcvdPerSec OBJECT-TYPE
    SYNTAX Gauge
    ACCESS read-only
    STATUS mandatory
    DESCRIPTION
        "The number of Packets received per sec."
    ::= { vmvcAimStatVMVNICEntry 18 }

vmvcAimStatVMVNICKBPSTxtPerSec OBJECT-TYPE
    SYNTAX Gauge
    ACCESS read-only
    STATUS mandatory
    DESCRIPTION
        "KBPS transmitted per sec."
    ::= { vmvcAimStatVMVNICEntry 19 }


vmvcAimStatVMVNICKBPSRcvdPerSec OBJECT-TYPE
    SYNTAX Gauge
    ACCESS read-only
    STATUS mandatory
    DESCRIPTION
        "KBPS received."
    ::= { vmvcAimStatVMVNICEntry 20 }

vmvcAimStatVMVNICPortGroupUID OBJECT-TYPE
    SYNTAX INTEGER (1..2147483647)
    ACCESS read-only
    STATUS mandatory
    DESCRIPTION
        "UID of the Port Group this VM VNIC is associated with.
         Applies to standard port groups only (zero otherwise)."
    ::= { vmvcAimStatVMVNICEntry 21 }

vmvcAimStatVMVNICVCUID OBJECT-TYPE
    SYNTAX INTEGER
    ACCESS read-only
    STATUS mandatory
    DESCRIPTION
        "VC Instance SNMP UID where this VM VNIC resides."
    ::= { vmvcAimStatVMVNICEntry 22 }

vmvcAimStatVMVNICVCName OBJECT-TYPE
    SYNTAX SnmpAdminString
    ACCESS read-only
    STATUS mandatory
    DESCRIPTION
        "VC Instance where this VM VNIC resides."
    ::= { vmvcAimStatVMVNICEntry 23 }

vmvcAimStatVMVNICDVPortGroupIndex OBJECT-TYPE
    SYNTAX SnmpAdminString
    ACCESS read-only
    STATUS mandatory
    DESCRIPTION
        "The DV Port Group MOID that is connected.  This applies only to VNICs attached 
         to a Distributed Virtual Switch."
    ::= { vmvcAimStatVMVNICEntry 24 }

vmvcAimStatVMVNICDVPortGroupUID OBJECT-TYPE
    SYNTAX INTEGER (1..2147483647)
    ACCESS read-only
    STATUS mandatory
    DESCRIPTION
        "UID of the DV Port Group this VM VNIC is associated with.  This applies only 
         to VNICs attached to a Distributed Virtual Switch (zero otherwise)."
    ::= { vmvcAimStatVMVNICEntry 25 }

vmvcAimStatVMVNICDVPortKey OBJECT-TYPE
    SYNTAX SnmpAdminString
    ACCESS read-only
    STATUS mandatory
    DESCRIPTION
        "The DV Port Key ID that is connected.  This applies only to VNICs attached to a 
         Distributed Virtual Switch."
    ::= { vmvcAimStatVMVNICEntry 26 }

vmvcAimStatVMVNICDeviceSummary OBJECT-TYPE
    SYNTAX SnmpAdminString
    ACCESS read-only
    STATUS mandatory
    DESCRIPTION
        "The Device summary for this VNIC, required for provisioning."
    ::= { vmvcAimStatVMVNICEntry 27 }

vmvcAimStatVMVNICHostName OBJECT-TYPE
    SYNTAX SnmpAdminString
    ACCESS read-only
    STATUS mandatory
    DESCRIPTION
        "The ESX(i) Host Name where this device resides."
    ::= { vmvcAimStatVMVNICEntry 28 }

vmvcAimStatVMVNICVCUUID OBJECT-TYPE
    SYNTAX SnmpAdminString
    ACCESS read-only
    STATUS mandatory
    DESCRIPTION
        "The vCenter-specific UUID where this VM VNIC resides."
    ::= { vmvcAimStatVMVNICEntry 29 }


-- *****************************************************************************
-- Status Custom Specification NIC Group
-- *****************************************************************************
vmvcAimStatCustomSpecNICCount OBJECT-TYPE
    SYNTAX INTEGER
    ACCESS read-only
    STATUS mandatory
    DESCRIPTION
        "CustomSpec NIC count in vmvcAimStatCustomSpecNICTable."
    ::= { vmvcAimStatCustomSpecNICGroup 1}

vmvcAimStatCustomSpecNICTable OBJECT-TYPE
    SYNTAX SEQUENCE OF VmvcAimStatCustomSpecNICRow
    ACCESS not-accessible
    STATUS mandatory
    DESCRIPTION
        "CustomSpec NIC table."
    ::= { vmvcAimStatCustomSpecNICGroup 2 }

vmvcAimStatCustomSpecNICEntry OBJECT-TYPE
    SYNTAX VmvcAimStatCustomSpecNICRow
    ACCESS not-accessible
    STATUS mandatory
    DESCRIPTION
        "The table entry."
    INDEX { vmvcAimStatCustomSpecNICUID }
    ::= { vmvcAimStatCustomSpecNICTable 1 }

VmvcAimStatCustomSpecNICRow ::=
    SEQUENCE {
        vmvcAimStatCustomSpecNICUID                 INTEGER,
        vmvcAimStatCustomSpecName                   SnmpAdminString,
        vmvcAimStatCustomSpecNICOrder               INTEGER,
        vmvcAimStatCustomSpecNICType                INTEGER,
        vmvcAimStatCustomSpecNICIPAddress           SnmpAdminString,
        vmvcAimStatCustomSpecNICSubnetMask          SnmpAdminString,
        vmvcAimStatCustomSpecNICGateway             SnmpAdminString,
        vmvcAimStatCustomSpecNICAlternateGateway    SnmpAdminString,
        vmvcAimStatCustomSpecNICDNS                 SnmpAdminString,
        vmvcAimStatCustomSpecNICAlternateDNS        SnmpAdminString,
        vmvcAimStatCustomSpecNICPrimaryWINSServer   SnmpAdminString,
        vmvcAimStatCustomSpecNICSecondaryWINSServer SnmpAdminString,
        vmvcAimStatCustomSpecNICVCUID               INTEGER,
        vmvcAimStatCustomSpecNICVCName              SnmpAdminString,
        vmvcAimStatCustomSpecUID                    INTEGER,
        vmvcAimStatCustomSpecNICVCUUID              SnmpAdminString
        }

vmvcAimStatCustomSpecNICUID OBJECT-TYPE
    SYNTAX INTEGER (1..2147483647)
    ACCESS read-only
    STATUS mandatory
    DESCRIPTION
        "CustomSpec NIC device UID."
    ::= { vmvcAimStatCustomSpecNICEntry 1 }

vmvcAimStatCustomSpecName OBJECT-TYPE
    SYNTAX SnmpAdminString
    ACCESS read-only
    STATUS mandatory
    DESCRIPTION
        "Name of the CustomSpecification this NIC is associated with."
    ::= { vmvcAimStatCustomSpecNICEntry 2 }

vmvcAimStatCustomSpecNICOrder OBJECT-TYPE
    SYNTAX INTEGER
    ACCESS read-only
    STATUS mandatory
    DESCRIPTION
        "The order of the network interface cards for the operating 
         system."
    ::= { vmvcAimStatCustomSpecNICEntry 3 }
    
vmvcAimStatCustomSpecNICType OBJECT-TYPE
    SYNTAX INTEGER {
        static(1),
        dhcp(2)
    }
    ACCESS read-only
    STATUS mandatory
    DESCRIPTION
        "The type of the NIC card."
    ::= { vmvcAimStatCustomSpecNICEntry  4}
    
vmvcAimStatCustomSpecNICIPAddress OBJECT-TYPE
    SYNTAX SnmpAdminString
    ACCESS read-only
    STATUS mandatory
    DESCRIPTION
        "The IP address that is to be assigned to the NIC."
    ::= { vmvcAimStatCustomSpecNICEntry 5 }
    
vmvcAimStatCustomSpecNICSubnetMask OBJECT-TYPE
    SYNTAX SnmpAdminString
    ACCESS read-only
    STATUS mandatory
    DESCRIPTION
        "The IP address that is to be assigned to the NIC."
    ::= { vmvcAimStatCustomSpecNICEntry 6 }
    
vmvcAimStatCustomSpecNICGateway OBJECT-TYPE
    SYNTAX SnmpAdminString
    ACCESS read-only
    STATUS mandatory
    DESCRIPTION
        "The gateway for IP address that is to be assigned to the NIC."
    ::= { vmvcAimStatCustomSpecNICEntry 7 }
    
vmvcAimStatCustomSpecNICAlternateGateway OBJECT-TYPE
    SYNTAX SnmpAdminString
    ACCESS read-only
    STATUS mandatory
    DESCRIPTION
        "The alternate gateway for IP address that is to be assigned 
         to the NIC."
    ::= { vmvcAimStatCustomSpecNICEntry 8 }

vmvcAimStatCustomSpecNICDNS OBJECT-TYPE
    SYNTAX SnmpAdminString
    ACCESS read-only
    STATUS mandatory
    DESCRIPTION
        "The DNS server for IP address that is to be assigned to the NIC."
    ::= { vmvcAimStatCustomSpecNICEntry 9 }
    
vmvcAimStatCustomSpecNICAlternateDNS OBJECT-TYPE
    SYNTAX SnmpAdminString
    ACCESS read-only
    STATUS mandatory
    DESCRIPTION
        "The alternate DNS server for IP address that is to be assigned 
         to the NIC."
    ::= { vmvcAimStatCustomSpecNICEntry 10 }

vmvcAimStatCustomSpecNICPrimaryWINSServer OBJECT-TYPE
    SYNTAX SnmpAdminString
    ACCESS read-only
    STATUS mandatory
    DESCRIPTION
        "The primary WINS server for IP address that is to be assigned 
         to the NIC."
    ::= { vmvcAimStatCustomSpecNICEntry 11 }
    
vmvcAimStatCustomSpecNICSecondaryWINSServer OBJECT-TYPE
    SYNTAX SnmpAdminString
    ACCESS read-only
    STATUS mandatory
    DESCRIPTION
        "The secondary WINS server for IP address that is to be 
         assigned to the NIC."
    ::= { vmvcAimStatCustomSpecNICEntry 12 }

vmvcAimStatCustomSpecNICVCUID OBJECT-TYPE
    SYNTAX INTEGER
    ACCESS read-only
    STATUS mandatory
    DESCRIPTION
        "VC Instance SNMP UID where this Custom Spec NIC resides."
    ::= { vmvcAimStatCustomSpecNICEntry 13 }

vmvcAimStatCustomSpecNICVCName OBJECT-TYPE
    SYNTAX SnmpAdminString
    ACCESS read-only
    STATUS mandatory
    DESCRIPTION
        "VC Instance where this Custom Spec NIC resides."
    ::= { vmvcAimStatCustomSpecNICEntry 14 }

vmvcAimStatCustomSpecUID OBJECT-TYPE
    SYNTAX INTEGER (1..2147483647)
    ACCESS read-only
    STATUS mandatory
    DESCRIPTION
        "UID of the Customization Specification this NIC is associated with."
    ::= { vmvcAimStatCustomSpecNICEntry 15 }

vmvcAimStatCustomSpecNICVCUUID OBJECT-TYPE
    SYNTAX SnmpAdminString
    ACCESS read-only
    STATUS mandatory
    DESCRIPTION
        "The vCenter-specific UUID where this Custom Spec NIC resides."
    ::= { vmvcAimStatCustomSpecNICEntry 16 }


-- *****************************************************************************
-- Status Distributed Virtual Switch Group
-- *****************************************************************************
vmvcAimStatDistribVSwitchCount OBJECT-TYPE
    SYNTAX INTEGER
    ACCESS read-only
    STATUS mandatory
    DESCRIPTION
        "Distributed Virtual Switch count in vmvcAimStatDistribVSwitchTable."
    ::= { vmvcAimStatDistribVSwitchGroup 1}

vmvcAimStatDistribVSwitchTable OBJECT-TYPE
    SYNTAX SEQUENCE OF VmvcAimStatDistribVSwitchRow
    ACCESS not-accessible
    STATUS mandatory
    DESCRIPTION
        "Distributed Virtual Switch Table."
    ::= { vmvcAimStatDistribVSwitchGroup 2 }

vmvcAimStatDistribVSwitchEntry OBJECT-TYPE
    SYNTAX VmvcAimStatDistribVSwitchRow
    ACCESS not-accessible
    STATUS mandatory
    DESCRIPTION
        "The table entry."
    INDEX { vmvcAimStatDVSwitchUID }
    ::= { vmvcAimStatDistribVSwitchTable 1 }

VmvcAimStatDistribVSwitchRow ::=
    SEQUENCE {
        vmvcAimStatDVSwitchUID                              INTEGER,
        vmvcAimStatDVSwitchVCUID                            INTEGER,
        vmvcAimStatDVSwitchVCName                           SnmpAdminString,
        vmvcAimStatDVSwitchIndex                            SnmpAdminString,
        vmvcAimStatDVSwitchName                             SnmpAdminString,
        vmvcAimStatDVSwitchUUID                             SnmpAdminString,
        vmvcAimStatDVSwitchDCName                           SnmpAdminString,
        vmvcAimStatDVSwitchDCIndex                          SnmpAdminString,
        vmvcAimStatDVSwitchParentPath                       SnmpAdminString,
        vmvcAimStatDVSwitchProductClass                     SnmpAdminString,
        vmvcAimStatDVSwitchProductName                      SnmpAdminString,
        vmvcAimStatDVSwitchProductVendor                    SnmpAdminString,
        vmvcAimStatDVSwitchProductVersion                   SnmpAdminString,
        vmvcAimStatDVSwitchHost                             SnmpAdminString,
        vmvcAimStatDVSwitchNumPorts                         INTEGER,
        vmvcAimStatDVSwitchMaxPorts                         INTEGER,
        vmvcAimStatDVSwitchDVPortGroup                      SnmpAdminString,
        vmvcAimStatDVSwitchDVUplinkPortGroup                SnmpAdminString,
        vmvcAimStatDVSwitchOverallStatus                    INTEGER,
        vmvcAimStatDVSwitchMonitor                          INTEGER,
        vmvcAimStatDVSwitchAlert                            INTEGER,
        vmvcAimStatDVSwitchState                            INTEGER,
        vmvcAimStatDVSwitchPolicySecurityAllowPromis        INTEGER,
        vmvcAimStatDVSwitchPolicySecurityForgedTransmit     INTEGER,
        vmvcAimStatDVSwitchPolicySecurityMACChanges         INTEGER,
        vmvcAimStatDVSwitchPolicyShapingInAvgBandWidth      INTEGER,
        vmvcAimStatDVSwitchPolicyShapingInBurstSize         INTEGER,
        vmvcAimStatDVSwitchPolicyShapingInEnabled           INTEGER,
        vmvcAimStatDVSwitchPolicyShapingInPeakBandWidth     INTEGER,
        vmvcAimStatDVSwitchPolicyShapingOutAvgBandWidth     INTEGER,
        vmvcAimStatDVSwitchPolicyShapingOutBurstSize        INTEGER,
        vmvcAimStatDVSwitchPolicyShapingOutEnabled          INTEGER,
        vmvcAimStatDVSwitchPolicyShapingOutPeakBandWidth    INTEGER,
        vmvcAimStatDVSwitchUplinkTeamActivePort             SnmpAdminString,
        vmvcAimStatDVSwitchUplinkTeamStandByPort            SnmpAdminString,
        vmvcAimStatDVSwitchUplinkTeamNotifySwitch           INTEGER,
        vmvcAimStatDVSwitchUplinkTeamPolicy                 SnmpAdminString,
        vmvcAimStatDVSwitchUplinkTeamReversePolicy          INTEGER,
        vmvcAimStatDVSwitchUplinkTeamRollingOrder           INTEGER,
        vmvcAimStatDVSwitchUplinkTeamFailureChkBeacon       INTEGER,
        vmvcAimStatDVSwitchUplinkTeamFailureChkDuplex       INTEGER,
        vmvcAimStatDVSwitchUplinkTeamFailureChkErrPct       INTEGER,
        vmvcAimStatDVSwitchUplinkTeamFailureChkSpeed        SnmpAdminString,
        vmvcAimStatDVSwitchUplinkTeamFailureFullDuplex      INTEGER,
        vmvcAimStatDVSwitchUplinkTeamFailurePercentage      INTEGER,
        vmvcAimStatDVSwitchUplinkTeamFailureSpeed           INTEGER,
        vmvcAimStatDVSwitchVLanID                           INTEGER,
        vmvcAimStatDVSwitchPrivateVLanID                    INTEGER,
        vmvcAimStatDVSwitchVCUUID                           SnmpAdminString
    }

vmvcAimStatDVSwitchUID OBJECT-TYPE
    SYNTAX INTEGER (1..2147483647)
    ACCESS read-only
    STATUS mandatory
    DESCRIPTION
        "UID of Distributed Virtual Switch"
    ::= { vmvcAimStatDistribVSwitchEntry 1 }

vmvcAimStatDVSwitchVCUID OBJECT-TYPE
    SYNTAX INTEGER
    ACCESS read-only
    STATUS mandatory
    DESCRIPTION
        "VC Instance SNMP UID where this Distributed Virtual Switch resides."
    ::= { vmvcAimStatDistribVSwitchEntry 2 }

vmvcAimStatDVSwitchVCName OBJECT-TYPE
    SYNTAX SnmpAdminString
    ACCESS read-only
    STATUS mandatory
    DESCRIPTION
        "VC Instance where this Distributed Virtual Switch resides."
    ::= { vmvcAimStatDistribVSwitchEntry 3 }

vmvcAimStatDVSwitchIndex OBJECT-TYPE
    SYNTAX SnmpAdminString
    ACCESS read-only
    STATUS mandatory
    DESCRIPTION
        "MOID of Distributed Virtual Switch"
    ::= { vmvcAimStatDistribVSwitchEntry 4 }

vmvcAimStatDVSwitchName OBJECT-TYPE
    SYNTAX SnmpAdminString
    ACCESS read-only
    STATUS mandatory
    DESCRIPTION
        "The name of Distributed Virtual Switch"
    ::= { vmvcAimStatDistribVSwitchEntry 5 }

vmvcAimStatDVSwitchUUID OBJECT-TYPE
    SYNTAX SnmpAdminString
    ACCESS read-only
    STATUS mandatory
    DESCRIPTION
        "VC UUID of the Distributed Virtual Switch"
    ::= { vmvcAimStatDistribVSwitchEntry 6 }

vmvcAimStatDVSwitchDCName OBJECT-TYPE
    SYNTAX SnmpAdminString
    ACCESS read-only
    STATUS mandatory
    DESCRIPTION
        "The Datacenter where this Distributed Virtual Switch resides."
    ::= { vmvcAimStatDistribVSwitchEntry 7 }

vmvcAimStatDVSwitchDCIndex OBJECT-TYPE
    SYNTAX SnmpAdminString
    ACCESS read-only
    STATUS mandatory
    DESCRIPTION
        "The Datacenter MOID where this Distributed Virtual Switch resides."
    ::= { vmvcAimStatDistribVSwitchEntry 8 }

vmvcAimStatDVSwitchParentPath OBJECT-TYPE
    SYNTAX SnmpAdminString
    ACCESS read-only
    STATUS mandatory
    DESCRIPTION
        "The full path from the Datacenter to the Distributed Virtual Switch, not
         including the Distributed Virtual Switch."
    ::= { vmvcAimStatDistribVSwitchEntry 9 }

vmvcAimStatDVSwitchProductClass OBJECT-TYPE
    SYNTAX SnmpAdminString
    ACCESS read-only
    STATUS mandatory
    DESCRIPTION
        "The Product Forwarding Class of the Distributed Virtual Switch"
    ::= { vmvcAimStatDistribVSwitchEntry 10 }

vmvcAimStatDVSwitchProductName OBJECT-TYPE
    SYNTAX SnmpAdminString
    ACCESS read-only
    STATUS mandatory
    DESCRIPTION
        "The Product Name of the Distributed Virtual Switch"
    ::= { vmvcAimStatDistribVSwitchEntry 11 }

vmvcAimStatDVSwitchProductVendor OBJECT-TYPE
    SYNTAX SnmpAdminString
    ACCESS read-only
    STATUS mandatory
    DESCRIPTION
        "The Product Vendor of the Distributed Virtual Switch"
    ::= { vmvcAimStatDistribVSwitchEntry 12 }

vmvcAimStatDVSwitchProductVersion OBJECT-TYPE
    SYNTAX SnmpAdminString
    ACCESS read-only
    STATUS mandatory
    DESCRIPTION
        "The Product Forwarding Class of the Distributed Virtual Switch"
    ::= { vmvcAimStatDistribVSwitchEntry 13 }

vmvcAimStatDVSwitchHost OBJECT-TYPE
    SYNTAX SnmpAdminString
    ACCESS read-only
    STATUS mandatory
    DESCRIPTION
        "A delimited list of hosts attached to this distributed virtual switch."
    ::= { vmvcAimStatDistribVSwitchEntry 14 }

vmvcAimStatDVSwitchNumPorts OBJECT-TYPE
    SYNTAX INTEGER
    ACCESS read-only
    STATUS mandatory
    DESCRIPTION
        "The number of ports this distributed virtual switch currently has."
    ::= { vmvcAimStatDistribVSwitchEntry 15 }

vmvcAimStatDVSwitchMaxPorts OBJECT-TYPE
    SYNTAX INTEGER
    ACCESS read-only
    STATUS mandatory
    DESCRIPTION
        "The max number of ports this distributed virtual switch currently has."
    ::= { vmvcAimStatDistribVSwitchEntry 16 }

vmvcAimStatDVSwitchDVPortGroup OBJECT-TYPE
    SYNTAX SnmpAdminString (SIZE(0..1024))
    ACCESS read-only
    STATUS mandatory
    DESCRIPTION
        "All Distributed Virtual Port groups (excluding Uplink Port Groups) configured
         for this virtual switch."
    ::= { vmvcAimStatDistribVSwitchEntry 17 }

vmvcAimStatDVSwitchDVUplinkPortGroup OBJECT-TYPE
    SYNTAX SnmpAdminString (SIZE(0..1024))
    ACCESS read-only
    STATUS mandatory
    DESCRIPTION
        "Distributed Virtual Uplink Port Groups configured for this virtual switch."
    ::= { vmvcAimStatDistribVSwitchEntry 18 }

vmvcAimStatDVSwitchOverallStatus OBJECT-TYPE
    SYNTAX INTEGER {
        gray(1),
        green(2),
        yellow(3),
        red(4)
    }
    ACCESS read-only
    STATUS mandatory
    DESCRIPTION
        "Overall Distributed Virtual Switch status from vCenter.  
         It can be grey,green,red and yellow."
    ::= { vmvcAimStatDistribVSwitchEntry 19 }

vmvcAimStatDVSwitchMonitor OBJECT-TYPE
    SYNTAX INTEGER {
        do-not-monitor(1),
        monitor(2)
    }
    ACCESS read-write
    STATUS mandatory
    DESCRIPTION
        "Flag whether to monitor this Distributed Virtual Switch or not."
    DEFVAL { 2 }
    ::= { vmvcAimStatDistribVSwitchEntry 20 }

vmvcAimStatDVSwitchAlert OBJECT-TYPE
    SYNTAX INTEGER {
        not-green-warn(1),
        not-green-critical(2),
        follow-overallStatus(3)
    }
    ACCESS read-write
    STATUS mandatory
    DESCRIPTION
        "Level choices for the alert, as follows:
            not-green-warn       -  Set the State=warning(3) if OverallStatus!=green
            not-green-crit       -  Set the State=critical(4) if OverallStatus!=green
            follow-overallStatus -  Use the OverallStatus to set the State, as follows:
               OverallStatus=gray    ->  State=unknown(1)
               OverallStatus=green   ->  State=ok(2)
               OverallStatus=yellow  ->  State=warning(3)
               OverallStatus=red     ->  State=critical(4)"
    DEFVAL { 3 }
    ::= { vmvcAimStatDistribVSwitchEntry 21 }

vmvcAimStatDVSwitchState OBJECT-TYPE
    SYNTAX INTEGER {
        unknown(1),
        ok(2),
        warning(3),
        critical(4)
    }
    ACCESS read-only
    STATUS mandatory
    DESCRIPTION
        "The state of the Distributed Virtual Switch, as calculated by the combination of OverallStatus,
         Monitor flag, and Alert level."
    ::= { vmvcAimStatDistribVSwitchEntry 22 }

vmvcAimStatDVSwitchPolicySecurityAllowPromis OBJECT-TYPE
    SYNTAX INTEGER{
        false(1),
        true(2),
        notAvail(3)
    }
    ACCESS read-only
    STATUS mandatory
    DESCRIPTION
        "The flag to indicate whether or not all traffic is seen on the port."
    ::= { vmvcAimStatDistribVSwitchEntry 23 }

vmvcAimStatDVSwitchPolicySecurityForgedTransmit OBJECT-TYPE
    SYNTAX INTEGER{
        false(1),
        true(2),
        notAvail(3)
    }
    ACCESS read-only
    STATUS mandatory
    DESCRIPTION
        "The flag to indicate if different MAC address than that of the virtual network adapter."
    ::= { vmvcAimStatDistribVSwitchEntry 24 }

vmvcAimStatDVSwitchPolicySecurityMACChanges OBJECT-TYPE
    SYNTAX INTEGER{
        false(1),
        true(2),
        notAvail(3)
    }
    ACCESS read-only
    STATUS mandatory
    DESCRIPTION
        "The flag to indicate whether or not the Media Access Control (MAC) address can be changed"
    ::= { vmvcAimStatDistribVSwitchEntry 25 }

vmvcAimStatDVSwitchPolicyShapingInAvgBandWidth OBJECT-TYPE
    SYNTAX INTEGER
    ACCESS read-only
    STATUS mandatory
    DESCRIPTION
        "The input average bandwidth in bits per second if shaping is enabled on the port."
    ::= { vmvcAimStatDistribVSwitchEntry 26 }

vmvcAimStatDVSwitchPolicyShapingInBurstSize OBJECT-TYPE
    SYNTAX INTEGER
    ACCESS read-only
    STATUS mandatory
    DESCRIPTION
        "The input maximum burst size allowed in bytes if shaping is enabled on the port"
    ::= { vmvcAimStatDistribVSwitchEntry 27 }

vmvcAimStatDVSwitchPolicyShapingInEnabled OBJECT-TYPE
    SYNTAX INTEGER{
        false(1),
        true(2),
        notAvail(3)
    }
    ACCESS read-only
    STATUS mandatory
    DESCRIPTION
        "The flag to indicate whether or not input traffic shaper is enabled on the port"
    ::= { vmvcAimStatDistribVSwitchEntry 28 }

vmvcAimStatDVSwitchPolicyShapingInPeakBandWidth OBJECT-TYPE
    SYNTAX INTEGER
    ACCESS read-only
    STATUS mandatory
    DESCRIPTION
        "The input peak bandwidth during bursts in bits per second if traffic shaping is enabled on the port."
    ::= { vmvcAimStatDistribVSwitchEntry 29 }

vmvcAimStatDVSwitchPolicyShapingOutAvgBandWidth OBJECT-TYPE
    SYNTAX INTEGER
    ACCESS read-only
    STATUS mandatory
    DESCRIPTION
        "The output average bandwidth in bits per second if shaping is enabled on the port."
    ::= { vmvcAimStatDistribVSwitchEntry 30 }

vmvcAimStatDVSwitchPolicyShapingOutBurstSize OBJECT-TYPE
    SYNTAX INTEGER
    ACCESS read-only
    STATUS mandatory
    DESCRIPTION
        "The output maximum burst size allowed in bytes if shaping is enabled on the port"
    ::= { vmvcAimStatDistribVSwitchEntry 31 }

vmvcAimStatDVSwitchPolicyShapingOutEnabled OBJECT-TYPE
    SYNTAX INTEGER{
        false(1),
        true(2),
        notAvail(3)
    }
    ACCESS read-only
    STATUS mandatory
    DESCRIPTION
        "The flag to indicate whether or not output traffic shaper is enabled on the port"
    ::= { vmvcAimStatDistribVSwitchEntry 32 }

vmvcAimStatDVSwitchPolicyShapingOutPeakBandWidth OBJECT-TYPE
    SYNTAX INTEGER
    ACCESS read-only
    STATUS mandatory
    DESCRIPTION
        "The output peak bandwidth during bursts in bits per second if traffic shaping is enabled on the port."
    ::= { vmvcAimStatDistribVSwitchEntry 33 }

vmvcAimStatDVSwitchUplinkTeamActivePort OBJECT-TYPE
    SYNTAX SnmpAdminString
    ACCESS read-only
    STATUS mandatory
    DESCRIPTION
        "List of active uplink ports used for load balancing."
    ::= { vmvcAimStatDistribVSwitchEntry 34 }

vmvcAimStatDVSwitchUplinkTeamStandByPort OBJECT-TYPE
    SYNTAX SnmpAdminString
    ACCESS read-only
    STATUS mandatory
    DESCRIPTION
        "Standby uplink ports used for failover"
    ::= { vmvcAimStatDistribVSwitchEntry 35 }

vmvcAimStatDVSwitchUplinkTeamNotifySwitch OBJECT-TYPE
    SYNTAX INTEGER{
        false(1),
        true(2),
        notAvail(3)
    }
    ACCESS read-only
    STATUS mandatory
    DESCRIPTION
        "Flag to specify whether or not to notify the physical switch if a link fails"
    ::= { vmvcAimStatDistribVSwitchEntry 36 }

vmvcAimStatDVSwitchUplinkTeamPolicy OBJECT-TYPE
    SYNTAX SnmpAdminString
    ACCESS read-only
    STATUS mandatory
    DESCRIPTION
        "Uplink teaming policy which includes failover and load balancing."
    ::= { vmvcAimStatDistribVSwitchEntry 37 }

vmvcAimStatDVSwitchUplinkTeamReversePolicy OBJECT-TYPE
    SYNTAX INTEGER{
        false(1),
        true(2),
        notAvail(3)
    }
    ACCESS read-only
    STATUS mandatory
    DESCRIPTION
        "The flag to indicate whether or not the teaming policy is applied to inbound frames as well."
    ::= { vmvcAimStatDistribVSwitchEntry 38 }

vmvcAimStatDVSwitchUplinkTeamRollingOrder OBJECT-TYPE
    SYNTAX INTEGER{
        false(1),
        true(2),
        notAvail(3)
    }
    ACCESS read-only
    STATUS mandatory
    DESCRIPTION
        "The flag to indicate whether or not to use a rolling policy when restoring links"
    ::= { vmvcAimStatDistribVSwitchEntry 39 }

vmvcAimStatDVSwitchUplinkTeamFailureChkBeacon OBJECT-TYPE
    SYNTAX INTEGER{
        false(1),
        true(2),
        notAvail(3)
    }
    ACCESS read-only
    STATUS mandatory
    DESCRIPTION
        "The flag to enable beacon probing as a method to validate the link status of a physical network"
    ::= { vmvcAimStatDistribVSwitchEntry 40 }

vmvcAimStatDVSwitchUplinkTeamFailureChkDuplex OBJECT-TYPE
    SYNTAX INTEGER{
        false(1),
        true(2),
        notAvail(3)
    }
    ACCESS read-only
    STATUS mandatory
    DESCRIPTION
        "The flag to indicate whether or not to use the link duplex reported by the driver as link selection criteria"
    ::= { vmvcAimStatDistribVSwitchEntry 41 }

vmvcAimStatDVSwitchUplinkTeamFailureChkErrPct OBJECT-TYPE
    SYNTAX INTEGER{
        false(1),
        true(2),
        notAvail(3)
    }
    ACCESS read-only
    STATUS mandatory
    DESCRIPTION
        "The flag to indicate whether or not to use link error percentage to detect failure."
    ::= { vmvcAimStatDistribVSwitchEntry 42 }

vmvcAimStatDVSwitchUplinkTeamFailureChkSpeed OBJECT-TYPE
    SYNTAX SnmpAdminString
    ACCESS read-only
    STATUS mandatory
    DESCRIPTION
        "Switch Uplink Team Failure Check Speed."
    ::= { vmvcAimStatDistribVSwitchEntry 43 }

vmvcAimStatDVSwitchUplinkTeamFailureFullDuplex OBJECT-TYPE
    SYNTAX INTEGER{
        false(1),
        true(2),
        notAvail(3)
    }
    ACCESS read-only
    STATUS mandatory
    DESCRIPTION
        "Configured duplexity"
    ::= { vmvcAimStatDistribVSwitchEntry 44 }

vmvcAimStatDVSwitchUplinkTeamFailurePercentage OBJECT-TYPE
    SYNTAX INTEGER
    ACCESS read-only
    STATUS mandatory
    DESCRIPTION
        "Configured percentage"
    ::= { vmvcAimStatDistribVSwitchEntry 45 }

vmvcAimStatDVSwitchUplinkTeamFailureSpeed OBJECT-TYPE
    SYNTAX INTEGER
    ACCESS read-only
    STATUS mandatory
    DESCRIPTION
        "Configured speed"
    ::= { vmvcAimStatDistribVSwitchEntry 46 }

vmvcAimStatDVSwitchVLanID OBJECT-TYPE
    SYNTAX INTEGER
    ACCESS read-only
    STATUS mandatory
    DESCRIPTION
        "DV Switch VLAN ID."
    ::= { vmvcAimStatDistribVSwitchEntry 47 }

vmvcAimStatDVSwitchPrivateVLanID OBJECT-TYPE
    SYNTAX INTEGER
    ACCESS read-only
    STATUS mandatory
    DESCRIPTION
        "DV Switch Private VLAN ID."
    ::= { vmvcAimStatDistribVSwitchEntry 48 }

vmvcAimStatDVSwitchVCUUID OBJECT-TYPE
    SYNTAX SnmpAdminString
    ACCESS read-only
    STATUS mandatory
    DESCRIPTION
        "The vCenter-specific UUID where this Distributed Virtual Switch resides."
    ::= { vmvcAimStatDistribVSwitchEntry 49 }


-- *****************************************************************************
-- Status Distributed Virtual Port Group
-- *****************************************************************************
vmvcAimStatDVPortGrpCount OBJECT-TYPE
    SYNTAX INTEGER
    ACCESS read-only
    STATUS mandatory
    DESCRIPTION
        "Distributed Virtual Port Group count in vmvcAimStatDVPortGrpTable."
    ::= { vmvcAimStatDVPortGrpGroup 1}

vmvcAimStatDVPortGrpTable OBJECT-TYPE
    SYNTAX SEQUENCE OF VmvcAimStatDVPortGrpRow
    ACCESS not-accessible
    STATUS mandatory
    DESCRIPTION
        "Disctributed Virtual Port Group Table."
    ::= { vmvcAimStatDVPortGrpGroup 2 }

vmvcAimStatDVPortGrpEntry OBJECT-TYPE
    SYNTAX VmvcAimStatDVPortGrpRow
    ACCESS not-accessible
    STATUS mandatory
    DESCRIPTION
        "The table entry."
    INDEX { vmvcAimStatDVPGUID }
    ::= { vmvcAimStatDVPortGrpTable 1 }

VmvcAimStatDVPortGrpRow ::=
    SEQUENCE {
        vmvcAimStatDVPGUID                              INTEGER,
        vmvcAimStatDVPGVCUID                            INTEGER,
        vmvcAimStatDVPGVCName                           SnmpAdminString,
        vmvcAimStatDVPGIndex                            SnmpAdminString,
        vmvcAimStatDVPGName                             SnmpAdminString,
        vmvcAimStatDVPGDVSwitchName                     SnmpAdminString,
        vmvcAimStatDVPGDVSwitchIndex                    SnmpAdminString,
        vmvcAimStatDVPGDVSwitchUID                      INTEGER,
        vmvcAimStatDVPGDCName                           SnmpAdminString,
        vmvcAimStatDVPGDCIndex                          SnmpAdminString,
        vmvcAimStatDVPGHost                             SnmpAdminString,
        vmvcAimStatDVPGNumPorts                         INTEGER,
        vmvcAimStatDVPGPortKeys                         SnmpAdminString,
        vmvcAimStatDVPGUplink                           INTEGER,
        vmvcAimStatDVPGOverallStatus                    INTEGER,
        vmvcAimStatDVPGPolicySecurityAllowPromis        INTEGER,
        vmvcAimStatDVPGPolicySecurityForgedTransmit     INTEGER,
        vmvcAimStatDVPGPolicySecurityMACChanges         INTEGER,
        vmvcAimStatDVPGPolicyShapingInAvgBandWidth      INTEGER,
        vmvcAimStatDVPGPolicyShapingInBurstSize         INTEGER,
        vmvcAimStatDVPGPolicyShapingInEnabled           INTEGER,
        vmvcAimStatDVPGPolicyShapingInPeakBandWidth     INTEGER,
        vmvcAimStatDVPGPolicyShapingOutAvgBandWidth     INTEGER,
        vmvcAimStatDVPGPolicyShapingOutBurstSize        INTEGER,
        vmvcAimStatDVPGPolicyShapingOutEnabled          INTEGER,
        vmvcAimStatDVPGPolicyShapingOutPeakBandWidth    INTEGER,
        vmvcAimStatDVPGUplinkTeamActivePort             SnmpAdminString,
        vmvcAimStatDVPGUplinkTeamStandByPort            SnmpAdminString,
        vmvcAimStatDVPGUplinkTeamNotifySwitch           INTEGER,
        vmvcAimStatDVPGUplinkTeamPolicy                 SnmpAdminString,
        vmvcAimStatDVPGUplinkTeamReversePolicy          INTEGER,
        vmvcAimStatDVPGUplinkTeamRollingOrder           INTEGER,
        vmvcAimStatDVPGUplinkTeamFailureChkBeacon       INTEGER,
        vmvcAimStatDVPGUplinkTeamFailureChkDuplex       INTEGER,
        vmvcAimStatDVPGUplinkTeamFailureChkErrPct       INTEGER,
        vmvcAimStatDVPGUplinkTeamFailureChkSpeed        SnmpAdminString,
        vmvcAimStatDVPGUplinkTeamFailureFullDuplex      INTEGER,
        vmvcAimStatDVPGUplinkTeamFailurePercentage      INTEGER,
        vmvcAimStatDVPGUplinkTeamFailureSpeed           INTEGER,
        vmvcAimStatDVPGVLanID                           INTEGER,
        vmvcAimStatDVPGPrivateVLanID                    INTEGER,
        vmvcAimStatDVPGVLanTrunkRange                   SnmpAdminString,
        vmvcAimStatDVPGVCUUID                           SnmpAdminString
    }

vmvcAimStatDVPGUID OBJECT-TYPE
    SYNTAX INTEGER (1..2147483647)
    ACCESS read-only
    STATUS mandatory
    DESCRIPTION
        "UID of the DV port group"
    ::= { vmvcAimStatDVPortGrpEntry 1 }

vmvcAimStatDVPGVCUID OBJECT-TYPE
    SYNTAX INTEGER
    ACCESS read-only
    STATUS mandatory
    DESCRIPTION
        "VC Instance SNMP UID where this DV Port Group resides."
    ::= { vmvcAimStatDVPortGrpEntry 2 }

vmvcAimStatDVPGVCName OBJECT-TYPE
    SYNTAX SnmpAdminString
    ACCESS read-only
    STATUS mandatory
    DESCRIPTION
        "VC Instance where this DV Port Group resides."
    ::= { vmvcAimStatDVPortGrpEntry 3 }

vmvcAimStatDVPGIndex OBJECT-TYPE
    SYNTAX SnmpAdminString
    ACCESS read-only
    STATUS mandatory
    DESCRIPTION
        "MOID of the DV port group"
    ::= { vmvcAimStatDVPortGrpEntry 4 }

vmvcAimStatDVPGName OBJECT-TYPE
    SYNTAX SnmpAdminString
    ACCESS read-only
    STATUS mandatory
    DESCRIPTION
        "Name of the DV port group"
    ::= { vmvcAimStatDVPortGrpEntry 5 }

vmvcAimStatDVPGDVSwitchName OBJECT-TYPE
    SYNTAX SnmpAdminString
    ACCESS read-only
    STATUS mandatory
    DESCRIPTION
        "The distributed virtual switch name on which this DV port group is located"
    ::= { vmvcAimStatDVPortGrpEntry 6 }

vmvcAimStatDVPGDVSwitchIndex OBJECT-TYPE
    SYNTAX SnmpAdminString
    ACCESS read-only
    STATUS mandatory
    DESCRIPTION
        "The distributed virtual switch MOID on which this DV port group is located"
    ::= { vmvcAimStatDVPortGrpEntry 7 }

vmvcAimStatDVPGDVSwitchUID OBJECT-TYPE
    SYNTAX INTEGER (1..2147483647)
    ACCESS read-only
    STATUS mandatory
    DESCRIPTION
        "UID of the Distributed Virtual Switch this DV Port Group is associated with."
    ::= { vmvcAimStatDVPortGrpEntry 8 }

vmvcAimStatDVPGDCName OBJECT-TYPE
    SYNTAX SnmpAdminString
    ACCESS read-only
    STATUS mandatory
    DESCRIPTION
        "The Datacenter where this DV Port Group resides."
    ::= { vmvcAimStatDVPortGrpEntry 9 }

vmvcAimStatDVPGDCIndex OBJECT-TYPE
    SYNTAX SnmpAdminString
    ACCESS read-only
    STATUS mandatory
    DESCRIPTION
        "The Datacenter MOID where this DV Port Group resides."
    ::= { vmvcAimStatDVPortGrpEntry 10 }

vmvcAimStatDVPGHost OBJECT-TYPE
    SYNTAX SnmpAdminString
    ACCESS read-only
    STATUS mandatory
    DESCRIPTION
        "Moids of the Hosts connected to this DV Port Group"
    ::= { vmvcAimStatDVPortGrpEntry 11 }

vmvcAimStatDVPGNumPorts OBJECT-TYPE
    SYNTAX INTEGER
    ACCESS read-only
    STATUS mandatory
    DESCRIPTION
        "The number of ports this DV port group currently has."
    ::= { vmvcAimStatDVPortGrpEntry 12 }

vmvcAimStatDVPGPortKeys OBJECT-TYPE
    SYNTAX SnmpAdminString (SIZE(0..2048))
    ACCESS read-only
    STATUS mandatory
    DESCRIPTION
        "Delimited list of port key numbers assigned to this DV Port Group. Due to size limitations and
         sheer size of the possible list, the format specifies this information as a range.
         For example: 10-138,140-158,161,170,194-236."
    ::= { vmvcAimStatDVPortGrpEntry 13 }

vmvcAimStatDVPGUplink OBJECT-TYPE
    SYNTAX INTEGER{
        false(1),
        true(2)
    }
    ACCESS read-only
    STATUS mandatory
    DESCRIPTION
        "Flag indicating whether this VC Port Group is an Uplink PG or not."
    ::= { vmvcAimStatDVPortGrpEntry 14 }

vmvcAimStatDVPGOverallStatus OBJECT-TYPE
    SYNTAX INTEGER {
        gray(1),
        green(2),
        yellow(3),
        red(4)
    }
    ACCESS read-only
    STATUS mandatory
    DESCRIPTION
        "Overall DV port group status from vCenter.  
         It can be grey,green,red and yellow."
    ::= { vmvcAimStatDVPortGrpEntry 15 }

vmvcAimStatDVPGPolicySecurityAllowPromis OBJECT-TYPE
    SYNTAX INTEGER{
        false(1),
        true(2),
        notAvail(3)
    }
    ACCESS read-only
    STATUS mandatory
    DESCRIPTION
        "The flag to indicate whether or not all traffic is seen on the port."
    ::= { vmvcAimStatDVPortGrpEntry 16 }

vmvcAimStatDVPGPolicySecurityForgedTransmit OBJECT-TYPE
    SYNTAX INTEGER{
        false(1),
        true(2),
        notAvail(3)
    }
    ACCESS read-only
    STATUS mandatory
    DESCRIPTION
        "The flag to indicate if different MAC address than that of the virtual network adapter."
    ::= { vmvcAimStatDVPortGrpEntry 17 }

vmvcAimStatDVPGPolicySecurityMACChanges OBJECT-TYPE
    SYNTAX INTEGER{
        false(1),
        true(2),
        notAvail(3)
    }
    ACCESS read-only
    STATUS mandatory
    DESCRIPTION
        "The flag to indicate whether or not the Media Access Control (MAC) address can be changed"
    ::= { vmvcAimStatDVPortGrpEntry 18 }

vmvcAimStatDVPGPolicyShapingInAvgBandWidth OBJECT-TYPE
    SYNTAX INTEGER
    ACCESS read-only
    STATUS mandatory
    DESCRIPTION
        "The input average bandwidth in bits per second if shaping is enabled on the port."
    ::= { vmvcAimStatDVPortGrpEntry 19 }

vmvcAimStatDVPGPolicyShapingInBurstSize OBJECT-TYPE
    SYNTAX INTEGER
    ACCESS read-only
    STATUS mandatory
    DESCRIPTION
        "The input maximum burst size allowed in bytes if shaping is enabled on the port"
    ::= { vmvcAimStatDVPortGrpEntry 20 }

vmvcAimStatDVPGPolicyShapingInEnabled OBJECT-TYPE
    SYNTAX INTEGER{
        false(1),
        true(2),
        notAvail(3)
    }
    ACCESS read-only
    STATUS mandatory
    DESCRIPTION
        "The flag to indicate whether or not input traffic shaper is enabled on the port"
    ::= { vmvcAimStatDVPortGrpEntry 21 }

vmvcAimStatDVPGPolicyShapingInPeakBandWidth OBJECT-TYPE
    SYNTAX INTEGER
    ACCESS read-only
    STATUS mandatory
    DESCRIPTION
        "The input peak bandwidth during bursts in bits per second if traffic shaping is enabled on the port."
    ::= { vmvcAimStatDVPortGrpEntry 22 }

vmvcAimStatDVPGPolicyShapingOutAvgBandWidth OBJECT-TYPE
    SYNTAX INTEGER
    ACCESS read-only
    STATUS mandatory
    DESCRIPTION
        "The output average bandwidth in bits per second if shaping is enabled on the port."
    ::= { vmvcAimStatDVPortGrpEntry 23 }

vmvcAimStatDVPGPolicyShapingOutBurstSize OBJECT-TYPE
    SYNTAX INTEGER
    ACCESS read-only
    STATUS mandatory
    DESCRIPTION
        "The output maximum burst size allowed in bytes if shaping is enabled on the port"
    ::= { vmvcAimStatDVPortGrpEntry 24 }

vmvcAimStatDVPGPolicyShapingOutEnabled OBJECT-TYPE
    SYNTAX INTEGER{
        false(1),
        true(2),
        notAvail(3)
    }
    ACCESS read-only
    STATUS mandatory
    DESCRIPTION
        "The flag to indicate whether or not output traffic shaper is enabled on the port"
    ::= { vmvcAimStatDVPortGrpEntry 25 }

vmvcAimStatDVPGPolicyShapingOutPeakBandWidth OBJECT-TYPE
    SYNTAX INTEGER
    ACCESS read-only
    STATUS mandatory
    DESCRIPTION
        "The output peak bandwidth during bursts in bits per second if traffic shaping is enabled on the port."
    ::= { vmvcAimStatDVPortGrpEntry 26 }

vmvcAimStatDVPGUplinkTeamActivePort OBJECT-TYPE
    SYNTAX SnmpAdminString
    ACCESS read-only
    STATUS mandatory
    DESCRIPTION
        "List of active uplink ports used for load balancing."
    ::= { vmvcAimStatDVPortGrpEntry 27 }

vmvcAimStatDVPGUplinkTeamStandByPort OBJECT-TYPE
    SYNTAX SnmpAdminString
    ACCESS read-only
    STATUS mandatory
    DESCRIPTION
        "Standby uplink ports used for failover"
    ::= { vmvcAimStatDVPortGrpEntry 28 }

vmvcAimStatDVPGUplinkTeamNotifySwitch OBJECT-TYPE
    SYNTAX INTEGER{
        false(1),
        true(2),
        notAvail(3)
    }
    ACCESS read-only
    STATUS mandatory
    DESCRIPTION
        "Flag to specify whether or not to notify the physical switch if a link fails"
    ::= { vmvcAimStatDVPortGrpEntry 29 }

vmvcAimStatDVPGUplinkTeamPolicy OBJECT-TYPE
    SYNTAX SnmpAdminString
    ACCESS read-only
    STATUS mandatory
    DESCRIPTION
        "Uplink teaming policy which includes failover and load balancing."
    ::= { vmvcAimStatDVPortGrpEntry 30 }

vmvcAimStatDVPGUplinkTeamReversePolicy OBJECT-TYPE
    SYNTAX INTEGER{
        false(1),
        true(2),
        notAvail(3)
    }
    ACCESS read-only
    STATUS mandatory
    DESCRIPTION
        "The flag to indicate whether or not the teaming policy is applied to inbound frames as well."
    ::= { vmvcAimStatDVPortGrpEntry 31 }

vmvcAimStatDVPGUplinkTeamRollingOrder OBJECT-TYPE
    SYNTAX INTEGER{
        false(1),
        true(2),
        notAvail(3)
    }
    ACCESS read-only
    STATUS mandatory
    DESCRIPTION
        "The flag to indicate whether or not to use a rolling policy when restoring links"
    ::= { vmvcAimStatDVPortGrpEntry 32 }

vmvcAimStatDVPGUplinkTeamFailureChkBeacon OBJECT-TYPE
    SYNTAX INTEGER{
        false(1),
        true(2),
        notAvail(3)
    }
    ACCESS read-only
    STATUS mandatory
    DESCRIPTION
        "The flag to enable beacon probing as a method to validate the link status of a physical network"
    ::= { vmvcAimStatDVPortGrpEntry 33 }

vmvcAimStatDVPGUplinkTeamFailureChkDuplex OBJECT-TYPE
    SYNTAX INTEGER{
        false(1),
        true(2),
        notAvail(3)
    }
    ACCESS read-only
    STATUS mandatory
    DESCRIPTION
        "The flag to indicate whether or not to use the link duplex reported by the driver as link selection criteria"
    ::= { vmvcAimStatDVPortGrpEntry 34 }

vmvcAimStatDVPGUplinkTeamFailureChkErrPct OBJECT-TYPE
    SYNTAX INTEGER{
        false(1),
        true(2),
        notAvail(3)
    }
    ACCESS read-only
    STATUS mandatory
    DESCRIPTION
        "The flag to indicate whether or not to use link error percentage to detect failure."
    ::= { vmvcAimStatDVPortGrpEntry 35 }

vmvcAimStatDVPGUplinkTeamFailureChkSpeed OBJECT-TYPE
    SYNTAX SnmpAdminString
    ACCESS read-only
    STATUS mandatory
    DESCRIPTION
        "Uplink Team Failure Check Speed."
    ::= { vmvcAimStatDVPortGrpEntry 36 }

vmvcAimStatDVPGUplinkTeamFailureFullDuplex OBJECT-TYPE
    SYNTAX INTEGER{
        false(1),
        true(2),
        notAvail(3)
    }
    ACCESS read-only
    STATUS mandatory
    DESCRIPTION
        "Configured duplexity"
    ::= { vmvcAimStatDVPortGrpEntry 37 }

vmvcAimStatDVPGUplinkTeamFailurePercentage OBJECT-TYPE
    SYNTAX INTEGER
    ACCESS read-only
    STATUS mandatory
    DESCRIPTION
        "Configured percentage"
    ::= { vmvcAimStatDVPortGrpEntry 38 }

vmvcAimStatDVPGUplinkTeamFailureSpeed OBJECT-TYPE
    SYNTAX INTEGER
    ACCESS read-only
    STATUS mandatory
    DESCRIPTION
        "Configured speed"
    ::= { vmvcAimStatDVPortGrpEntry 39 }

vmvcAimStatDVPGVLanID OBJECT-TYPE
    SYNTAX INTEGER
    ACCESS read-only
    STATUS mandatory
    DESCRIPTION
        "DV PortGroup VLAN ID."
    ::= { vmvcAimStatDVPortGrpEntry 40 }

vmvcAimStatDVPGPrivateVLanID OBJECT-TYPE
    SYNTAX INTEGER
    ACCESS read-only
    STATUS mandatory
    DESCRIPTION
        "DV PortGroup Private VLAN ID."
    ::= { vmvcAimStatDVPortGrpEntry 41 }

vmvcAimStatDVPGVLanTrunkRange OBJECT-TYPE
    SYNTAX SnmpAdminString
    ACCESS read-only
    STATUS mandatory
    DESCRIPTION
        "Delimited Trunk Range list VLan IDs if applicable."
    ::= { vmvcAimStatDVPortGrpEntry 42 }

vmvcAimStatDVPGVCUUID OBJECT-TYPE
    SYNTAX SnmpAdminString
    ACCESS read-only
    STATUS mandatory
    DESCRIPTION
        "The vCenter-specific UUID where this DV Port Group resides."
    ::= { vmvcAimStatDVPortGrpEntry 43 }


-- *****************************************************************************
-- Status Datastore Group
-- *****************************************************************************
vmvcAimStatDatastoreCount OBJECT-TYPE
    SYNTAX INTEGER
    ACCESS read-only
    STATUS mandatory
    DESCRIPTION
        "Number of Datastores in vmvcAimStatDatastoreTable."
    ::= { vmvcAimStatDatastoreGroup 1}

vmvcAimStatDatastoreTable OBJECT-TYPE
    SYNTAX SEQUENCE OF VmvcAimStatDatastoreRow
    ACCESS not-accessible
    STATUS mandatory
    DESCRIPTION
        "Datastore table."
    ::= { vmvcAimStatDatastoreGroup 2 }

vmvcAimStatDatastoreEntry OBJECT-TYPE
    SYNTAX VmvcAimStatDatastoreRow
    ACCESS not-accessible
    STATUS mandatory
    DESCRIPTION
        "The table entry."
    INDEX { vmvcAimStatDatastoreUID  }
    ::= { vmvcAimStatDatastoreTable 1 }

VmvcAimStatDatastoreRow ::=
    SEQUENCE {
        vmvcAimStatDatastoreUID                 INTEGER,
        vmvcAimStatDatastoreIndex               SnmpAdminString,
        vmvcAimStatDatastoreName                SnmpAdminString,
        vmvcAimStatDatastoreURL                 SnmpAdminString,
        vmvcAimStatDatastoreCapacity            INTEGER,
        vmvcAimStatDatastoreFreeSpace           Gauge,
        vmvcAimStatDatastoreFreeSpacePct        Gauge,
        vmvcAimStatDatastoreMaxFileSize         INTEGER,
        vmvcAimStatDatastoreType                SnmpAdminString,
        vmvcAimStatDatastoreMultiHostAccess     INTEGER,
        vmvcAimStatDatastoreAccessible          INTEGER,
        vmvcAimStatDatastoreMonitor             INTEGER,
        vmvcAimStatDatastoreFreeSpaceAlert      INTEGER,
        vmvcAimStatDatastoreFreeSpaceWarnThresh INTEGER,
        vmvcAimStatDatastoreFreeSpaceCritThresh INTEGER,
        vmvcAimStatDatastoreFreeSpaceState      INTEGER,
        vmvcAimStatDatastoreAccessibleAlert     INTEGER,
        vmvcAimStatDatastoreAccessState         INTEGER,
        vmvcAimStatDatastoreHostList            SnmpAdminString,
        vmvcAimStatDatastoreHostNameList        SnmpAdminString,
        vmvcAimStatDatastoreUsedSpace           Gauge,
        vmvcAimStatDatastoreUsedSpacePct        Gauge,
        vmvcAimStatDatastoreVCUID               INTEGER,
        vmvcAimStatDatastoreVCName              SnmpAdminString,
        vmvcAimStatDatastoreVCUUID              SnmpAdminString
    }

vmvcAimStatDatastoreUID OBJECT-TYPE
    SYNTAX INTEGER (1..2147483647)
    ACCESS read-only
    STATUS mandatory
    DESCRIPTION
        "UID of datastore"
    ::= { vmvcAimStatDatastoreEntry  1}

vmvcAimStatDatastoreIndex OBJECT-TYPE
    SYNTAX SnmpAdminString
    ACCESS read-only
    STATUS mandatory
    DESCRIPTION
        "MOID of datastore"
    ::= { vmvcAimStatDatastoreEntry  2}

vmvcAimStatDatastoreName OBJECT-TYPE
    SYNTAX SnmpAdminString
    ACCESS read-only
    STATUS mandatory
    DESCRIPTION
        "The name of the datastore."
    ::= { vmvcAimStatDatastoreEntry  3}

vmvcAimStatDatastoreURL OBJECT-TYPE
    SYNTAX SnmpAdminString
    ACCESS read-only
    STATUS mandatory
    DESCRIPTION
        "The unique locator for the datastore"
    ::= { vmvcAimStatDatastoreEntry  4}

vmvcAimStatDatastoreCapacity OBJECT-TYPE
    SYNTAX INTEGER
    ACCESS read-only
    STATUS mandatory
    DESCRIPTION
        "Capacity of this datastore, in megabytes."
    ::= { vmvcAimStatDatastoreEntry  5}

vmvcAimStatDatastoreFreeSpace OBJECT-TYPE
    SYNTAX Gauge
    ACCESS read-only
    STATUS mandatory
    DESCRIPTION
        "Free space of this datastore in megabytes."
    ::= { vmvcAimStatDatastoreEntry  6}

vmvcAimStatDatastoreFreeSpacePct OBJECT-TYPE
    SYNTAX Gauge
    ACCESS read-only
    STATUS mandatory
    DESCRIPTION
        "Free space Percentage of this datastore"
    ::= { vmvcAimStatDatastoreEntry  7}

vmvcAimStatDatastoreMaxFileSize OBJECT-TYPE
    SYNTAX INTEGER
    ACCESS read-only
    STATUS mandatory
    DESCRIPTION
        "The maximum size of a file that can reside on this file system volume ( MB )"
    ::= { vmvcAimStatDatastoreEntry  8}

vmvcAimStatDatastoreType OBJECT-TYPE
    SYNTAX SnmpAdminString
    ACCESS read-only
    STATUS mandatory
    DESCRIPTION
        " Type of file system volume, such as VMFS or NFS."
    ::= { vmvcAimStatDatastoreEntry  9}

vmvcAimStatDatastoreMultiHostAccess OBJECT-TYPE
    SYNTAX INTEGER
    ACCESS read-only
    STATUS mandatory
    DESCRIPTION
        "More than one host in the datacenter has been configured with access to the datastore"
    ::= { vmvcAimStatDatastoreEntry  10}

vmvcAimStatDatastoreAccessible OBJECT-TYPE
    SYNTAX INTEGER
    ACCESS read-only
    STATUS mandatory
    DESCRIPTION
        "The connectivity status of this datastore"
    ::= { vmvcAimStatDatastoreEntry  11}

vmvcAimStatDatastoreMonitor OBJECT-TYPE
    SYNTAX INTEGER{
        do-not-monitor(1),
        monitor(2)
        }
    ACCESS read-write
    STATUS mandatory
    DESCRIPTION
        "The flag indicating whether to monitor the datastore or not."
    DEFVAL {2 }
    ::= { vmvcAimStatDatastoreEntry  12}

vmvcAimStatDatastoreFreeSpaceAlert OBJECT-TYPE
    SYNTAX INTEGER{
        warning-only(1),
        critical-only(2),
        both(3)
        }
    ACCESS read-write
    STATUS mandatory
    DESCRIPTION
        "Datastore Free Space Alert, That may be warning, critical or both."
    DEFVAL {3}
    ::= { vmvcAimStatDatastoreEntry  13}

vmvcAimStatDatastoreFreeSpaceWarnThresh OBJECT-TYPE
    SYNTAX INTEGER
    ACCESS read-write
    STATUS mandatory
    DESCRIPTION
        "Warning threshold for datastore free space."
    DEFVAL { 40 }
    ::= { vmvcAimStatDatastoreEntry  14}

vmvcAimStatDatastoreFreeSpaceCritThresh OBJECT-TYPE
    SYNTAX INTEGER
    ACCESS read-write
    STATUS mandatory
    DESCRIPTION
        "Critical threshold for datastore free space."
    DEFVAL { 20 }
    ::= { vmvcAimStatDatastoreEntry  15}

vmvcAimStatDatastoreFreeSpaceState OBJECT-TYPE
    SYNTAX INTEGER {
        unknown(1),
        ok(2),
        warning(3),
        critical(4)
    }
    ACCESS read-only
    STATUS mandatory
    DESCRIPTION
        "Datastore Free Space State.Can be ok,warning or critical."
    ::= { vmvcAimStatDatastoreEntry  16}

vmvcAimStatDatastoreAccessibleAlert OBJECT-TYPE
    SYNTAX INTEGER{
        not-accessible-warn(1),
        not-accessible-crit(2)
    }
    ACCESS read-write
    STATUS mandatory
    DESCRIPTION
        "Datastore Accessible Alert."
    DEFVAL {2 }
    ::= { vmvcAimStatDatastoreEntry  17}

vmvcAimStatDatastoreAccessState OBJECT-TYPE
    SYNTAX INTEGER {
        unknown(1),
        ok(2),
        warning(3),
        critical(4)
    }
    ACCESS read-only
    STATUS mandatory
    DESCRIPTION
        "Datastore Accessible State. Can be ok,warning or critical "
    ::= { vmvcAimStatDatastoreEntry  18}

vmvcAimStatDatastoreHostList OBJECT-TYPE
    SYNTAX SnmpAdminString
    ACCESS read-only
    STATUS mandatory
    DESCRIPTION
        "Host list which had mounted this datastore"
    ::= { vmvcAimStatDatastoreEntry  19}

vmvcAimStatDatastoreHostNameList OBJECT-TYPE
    SYNTAX SnmpAdminString
    ACCESS read-only
    STATUS mandatory
    DESCRIPTION
        "Host Name list which had mounted this datastore"
    ::= { vmvcAimStatDatastoreEntry  20}

vmvcAimStatDatastoreUsedSpace OBJECT-TYPE
    SYNTAX Gauge
    ACCESS read-only
    STATUS mandatory
    DESCRIPTION
        "Used space of this datastore in megabytes"
    ::= { vmvcAimStatDatastoreEntry  21}

vmvcAimStatDatastoreUsedSpacePct OBJECT-TYPE
    SYNTAX Gauge
    ACCESS read-only
    STATUS mandatory
    DESCRIPTION
        "Used space Percentage of this datastore"
    ::= { vmvcAimStatDatastoreEntry  22}

vmvcAimStatDatastoreVCUID OBJECT-TYPE
    SYNTAX INTEGER
    ACCESS read-only
    STATUS mandatory
    DESCRIPTION
        "VC Instance SNMP UID where this Datastore resides."
    ::= { vmvcAimStatDatastoreEntry 23 }

vmvcAimStatDatastoreVCName OBJECT-TYPE
    SYNTAX SnmpAdminString
    ACCESS read-only
    STATUS mandatory
    DESCRIPTION
        "VC Instance where this Datastore resides."
    ::= { vmvcAimStatDatastoreEntry 24 }

vmvcAimStatDatastoreVCUUID OBJECT-TYPE
    SYNTAX SnmpAdminString
    ACCESS read-only
    STATUS mandatory
    DESCRIPTION
        "The vCenter-specific UUID where this Datastore resides."
    ::= { vmvcAimStatDatastoreEntry 25 }


-- *****************************************************************************
-- Status VM VDisk Group 
-- *****************************************************************************
vmvcAimStatVMVDiskCount OBJECT-TYPE
    SYNTAX INTEGER
    ACCESS read-only
    STATUS mandatory
    DESCRIPTION
        "Number of Virtual Disks in vmvcAimStatVMVDiskTable."
    ::= { vmvcAimStatVMVDiskGroup 1 }

vmvcAimStatVMVDiskTable OBJECT-TYPE
    SYNTAX SEQUENCE OF VmvcAimStatVMVDiskRow
    ACCESS not-accessible
    STATUS mandatory
    DESCRIPTION
        "VDisk table."
    ::= { vmvcAimStatVMVDiskGroup 2 }

vmvcAimStatVMVDiskEntry OBJECT-TYPE
    SYNTAX VmvcAimStatVMVDiskRow
    ACCESS not-accessible
    STATUS mandatory
    DESCRIPTION
        "The table entry."
    INDEX { vmvcAimStatVMVDiskUID  }
    ::= { vmvcAimStatVMVDiskTable 1 }

VmvcAimStatVMVDiskRow ::=
    SEQUENCE {
        vmvcAimStatVMVDiskUID                   INTEGER,
        vmvcAimStatVMVDiskDeviceId              SnmpAdminString,
        vmvcAimStatVMDiskVMID                   SnmpAdminString,
        vmvcAimStatVMDiskVMName                 SnmpAdminString,
        vmvcAimStatVMVDiskLabel                 SnmpAdminString,
        vmvcAimStatVMVDiskCapacity              INTEGER,
        vmvcAimStatVMVDiskShares                INTEGER,
        vmvcAimStatVMVDiskMode                  SnmpAdminString,
        vmvcAimStatVMVDiskFileName              SnmpAdminString,
        vmvcAimStatVMVDiskSplit                 INTEGER,
        vmvcAimStatVMVDiskThinProvisioned       INTEGER,
        vmvcAimStatVMVDiskWriteThrough          INTEGER,
        vmvcAimStatVMVDiskDatastore             SnmpAdminString,
        vmvcAimStatVMVDiskBusResets             Gauge,
        vmvcAimStatVMVDiskCmdAborted            Gauge,
        vmvcAimStatVMVDiskRead                  Gauge,
        vmvcAimStatVMVDiskWrite                 Gauge,
        vmvcAimStatVMVDiskKBPSRead              Gauge,
        vmvcAimStatVMVDiskKBPSWrite             Gauge,
        vmvcAimStatVMVDiskMonitor               INTEGER,
        vmvcAimStatVMVDiskKBReadAlert           INTEGER,
        vmvcAimStatVMVDiskKBReadState           INTEGER,
        vmvcAimStatVMVDiskKBWriteAlert          INTEGER,
        vmvcAimStatVMVDiskKBWriteState          INTEGER,
        vmvcAimStatVMVDiskState                 INTEGER,
        vmvcAimStatVMVDiskDatastoreName         SnmpAdminString,
        vmvcAimStatVMVDiskReadPerSec            Gauge,
        vmvcAimStatVMVDiskWritePerSec           Gauge,
        vmvcAimStatVMVDiskKBPSReadPerSec        Gauge,
        vmvcAimStatVMVDiskKBPSWritePerSec       Gauge,
        vmvcAimStatVMVDiskCommandsAbortedPerSec Gauge,
        vmvcAimStatVMVDiskBusResetsPerSec       Gauge,
        vmvcAimStatVMVDiskControllerKey         INTEGER,
        vmvcAimStatVMVDiskUnitNumber            INTEGER,
        vmvcAimStatVMVDiskVCUID                 INTEGER,
        vmvcAimStatVMVDiskVCName                SnmpAdminString,
        vmvcAimStatVMVDiskHostName              SnmpAdminString,
        vmvcAimStatVMVDiskVCUUID                SnmpAdminString
    }

vmvcAimStatVMVDiskUID  OBJECT-TYPE
    SYNTAX INTEGER (1..2147483647)
    ACCESS read-only
    STATUS mandatory
    DESCRIPTION
        "VDisk device UID"
    ::= { vmvcAimStatVMVDiskEntry  1}

vmvcAimStatVMVDiskDeviceId  OBJECT-TYPE
    SYNTAX SnmpAdminString
    ACCESS read-only
    STATUS mandatory
    DESCRIPTION
        "VDisk device ID"
    ::= { vmvcAimStatVMVDiskEntry  2}

vmvcAimStatVMDiskVMID    OBJECT-TYPE
    SYNTAX SnmpAdminString
    ACCESS read-only
    STATUS mandatory
    DESCRIPTION
        "Moid of the virtual machine this Device is connected to."
    ::= { vmvcAimStatVMVDiskEntry  3}

vmvcAimStatVMDiskVMName  OBJECT-TYPE
    SYNTAX SnmpAdminString
    ACCESS read-only
    STATUS mandatory
    DESCRIPTION
        "Name of the virtual machine this Device is connected to."
    ::= { vmvcAimStatVMVDiskEntry  4}

vmvcAimStatVMVDiskLabel  OBJECT-TYPE
    SYNTAX SnmpAdminString
    ACCESS read-only
    STATUS mandatory
    DESCRIPTION
        "Display label of the Virtual Disk"
    ::= { vmvcAimStatVMVDiskEntry  5}

vmvcAimStatVMVDiskCapacity  OBJECT-TYPE
    SYNTAX INTEGER
    ACCESS read-only
    STATUS mandatory
    DESCRIPTION
        "Capacity of Device in MB."
    ::= { vmvcAimStatVMVDiskEntry  6}

vmvcAimStatVMVDiskShares OBJECT-TYPE
    SYNTAX INTEGER
    ACCESS read-only
    STATUS mandatory
    DESCRIPTION
        "Shares assigned to the Virtual Disk."
    ::= { vmvcAimStatVMVDiskEntry  7}

vmvcAimStatVMVDiskMode  OBJECT-TYPE
    SYNTAX SnmpAdminString
    ACCESS read-only
    STATUS mandatory
    DESCRIPTION
        "The disk persistence mode."
    ::= { vmvcAimStatVMVDiskEntry  8}

vmvcAimStatVMVDiskFileName  OBJECT-TYPE
    SYNTAX SnmpAdminString
    ACCESS read-only
    STATUS mandatory
    DESCRIPTION
        "Filename for the host file used in this backing"
    ::= { vmvcAimStatVMVDiskEntry  9}

vmvcAimStatVMVDiskSplit  OBJECT-TYPE
    SYNTAX INTEGER
    ACCESS read-only
    STATUS mandatory
    DESCRIPTION
        "Flag to indicate the type of virtual disk file: split or monolithic. If true(1), the virtual disk is stored in multiple files, each 2GB."
    ::= { vmvcAimStatVMVDiskEntry  10}

vmvcAimStatVMVDiskThinProvisioned  OBJECT-TYPE
    SYNTAX INTEGER
    ACCESS read-only
    STATUS mandatory
    DESCRIPTION
        "Flag to indicate to the underlying filesystem, whether the virtual disk backing file should be allocated lazily (using thin provisioning). 
            This flag is only used for file systems that support configuring the provisioning policy on a per file basis, such as VMFS3"
    ::= { vmvcAimStatVMVDiskEntry  11}

vmvcAimStatVMVDiskWriteThrough  OBJECT-TYPE
    SYNTAX INTEGER
    ACCESS read-only
    STATUS mandatory
    DESCRIPTION
        "Flag to indicate whether writes should go directly to the file system or should be buffered"
    ::= { vmvcAimStatVMVDiskEntry  12}

vmvcAimStatVMVDiskDatastore  OBJECT-TYPE
    SYNTAX SnmpAdminString
    ACCESS read-only
    STATUS mandatory
    DESCRIPTION
        "The datastore the Virtual Disk is associated to."
    ::= { vmvcAimStatVMVDiskEntry  13}

vmvcAimStatVMVDiskBusResets  OBJECT-TYPE
    SYNTAX Gauge
    ACCESS read-only
    STATUS mandatory
    DESCRIPTION
        "Number of Bus Resets"
    ::= { vmvcAimStatVMVDiskEntry  14}

vmvcAimStatVMVDiskCmdAborted  OBJECT-TYPE
    SYNTAX Gauge
    ACCESS read-only
    STATUS mandatory
    DESCRIPTION
        "Number of Commands aborted"
    ::= { vmvcAimStatVMVDiskEntry  15}

vmvcAimStatVMVDiskRead  OBJECT-TYPE
    SYNTAX Gauge
    ACCESS read-only
    STATUS mandatory
    DESCRIPTION
        "Number of read"
    ::= { vmvcAimStatVMVDiskEntry  16}

vmvcAimStatVMVDiskWrite  OBJECT-TYPE
    SYNTAX Gauge
    ACCESS read-only
    STATUS mandatory
    DESCRIPTION
        "Number of write"
    ::= { vmvcAimStatVMVDiskEntry  17}

vmvcAimStatVMVDiskKBPSRead  OBJECT-TYPE
    SYNTAX Gauge
    ACCESS read-only
    STATUS mandatory
    DESCRIPTION
        "KBPS read"
    ::= { vmvcAimStatVMVDiskEntry  18}

vmvcAimStatVMVDiskKBPSWrite  OBJECT-TYPE
    SYNTAX Gauge
    ACCESS read-only
    STATUS mandatory
    DESCRIPTION
        "KBPS written"
    ::= { vmvcAimStatVMVDiskEntry  19}

vmvcAimStatVMVDiskMonitor OBJECT-TYPE
    SYNTAX INTEGER {
        do-not-monitor(1),
        monitor(2)
    }
    ACCESS read-write
    STATUS mandatory
    DESCRIPTION
        "Flag indicating whether the Device to be monitored(2) or not(1)."
    DEFVAL { 1 }
    ::= { vmvcAimStatVMVDiskEntry  20}

vmvcAimStatVMVDiskKBReadAlert OBJECT-TYPE
    SYNTAX INTEGER {
        no-read-warning(1),
        no-read-critical(2)
    }
    ACCESS read-write
    STATUS mandatory
    DESCRIPTION
        "The level of alert to raise if the Disk is monitored and there is a loss of KB read."
    DEFVAL { 2 }
    ::= { vmvcAimStatVMVDiskEntry  21}

vmvcAimStatVMVDiskKBReadState OBJECT-TYPE
    SYNTAX INTEGER {
        unknown(1),
        ok(2),
        warning(3),
        critical(4)
    }
    ACCESS read-only
    STATUS mandatory
    DESCRIPTION
        "The read state of the virtual Disk."
    ::= { vmvcAimStatVMVDiskEntry  22}

vmvcAimStatVMVDiskKBWriteAlert OBJECT-TYPE
    SYNTAX INTEGER {
        no-write-warning(1),
        no-write-critical(2)
    }
    ACCESS read-write
    STATUS mandatory
    DESCRIPTION
        "The level of alert to raise if the Disk is monitored and there is a loss of KB read."
    DEFVAL { 2 }
    ::= { vmvcAimStatVMVDiskEntry  23}

vmvcAimStatVMVDiskKBWriteState OBJECT-TYPE
    SYNTAX INTEGER {
        unknown(1),
        ok(2),
        warning(3),
        critical(4)
    }
    ACCESS read-only
    STATUS mandatory
    DESCRIPTION
        "The write state of the virtual Disk."
    ::= { vmvcAimStatVMVDiskEntry  24}

vmvcAimStatVMVDiskState OBJECT-TYPE
    SYNTAX INTEGER {
        unknown(1),
        ok(2),
        warning(3),
        critical(4)
    }
    ACCESS read-only
    STATUS mandatory
    DESCRIPTION
        "The state of the virtual Disk.Can be ok,warning or critical"
    ::= { vmvcAimStatVMVDiskEntry  25}

vmvcAimStatVMVDiskDatastoreName OBJECT-TYPE
    SYNTAX SnmpAdminString
    ACCESS read-only
    STATUS mandatory
    DESCRIPTION
        "Name of the Datastore"
    ::= { vmvcAimStatVMVDiskEntry  26}

vmvcAimStatVMVDiskReadPerSec  OBJECT-TYPE
    SYNTAX Gauge
    ACCESS read-only
    STATUS mandatory
    DESCRIPTION
        "Number of reads per sec"
    ::= { vmvcAimStatVMVDiskEntry  27}

vmvcAimStatVMVDiskWritePerSec  OBJECT-TYPE
    SYNTAX Gauge
    ACCESS read-only
    STATUS mandatory
    DESCRIPTION
        "Number of writes per sec"
    ::= { vmvcAimStatVMVDiskEntry  28}

vmvcAimStatVMVDiskKBPSReadPerSec  OBJECT-TYPE
    SYNTAX Gauge
    ACCESS read-only
    STATUS mandatory
    DESCRIPTION
        "KBPS read per sec"
    ::= { vmvcAimStatVMVDiskEntry  29}

vmvcAimStatVMVDiskKBPSWritePerSec  OBJECT-TYPE
    SYNTAX Gauge
    ACCESS read-only
    STATUS mandatory
    DESCRIPTION
        "KBPS written per sec"
    ::= { vmvcAimStatVMVDiskEntry  30}

vmvcAimStatVMVDiskCommandsAbortedPerSec  OBJECT-TYPE
    SYNTAX Gauge
    ACCESS read-only
    STATUS mandatory
    DESCRIPTION
        "Commands Aborted per sec"
    ::= { vmvcAimStatVMVDiskEntry  31}

vmvcAimStatVMVDiskBusResetsPerSec  OBJECT-TYPE
    SYNTAX Gauge
    ACCESS read-only
    STATUS mandatory
    DESCRIPTION
        "Disk Bus Resets per sec"
    ::= { vmvcAimStatVMVDiskEntry  32}

vmvcAimStatVMVDiskControllerKey  OBJECT-TYPE
    SYNTAX INTEGER
    ACCESS read-only
    STATUS mandatory
    DESCRIPTION
        "The key identifying the controller the disk is associated with."
    ::= { vmvcAimStatVMVDiskEntry  33}

vmvcAimStatVMVDiskUnitNumber  OBJECT-TYPE
    SYNTAX INTEGER
    ACCESS read-only
    STATUS mandatory
    DESCRIPTION
        "The unit number if this disk."
    ::= { vmvcAimStatVMVDiskEntry  34}

vmvcAimStatVMVDiskVCUID OBJECT-TYPE
    SYNTAX INTEGER
    ACCESS read-only
    STATUS mandatory
    DESCRIPTION
        "VC Instance SNMP UID where this VM VDisk resides."
    ::= { vmvcAimStatVMVDiskEntry 35 }

vmvcAimStatVMVDiskVCName OBJECT-TYPE
    SYNTAX SnmpAdminString
    ACCESS read-only
    STATUS mandatory
    DESCRIPTION
        "VC Instance where this VM VDisk resides."
    ::= { vmvcAimStatVMVDiskEntry 36 }

vmvcAimStatVMVDiskHostName OBJECT-TYPE
    SYNTAX SnmpAdminString
    ACCESS read-only
    STATUS mandatory
    DESCRIPTION
        "The ESX(i) Host Name where this device resides."
    ::= { vmvcAimStatVMVDiskEntry 37 }

vmvcAimStatVMVDiskVCUUID OBJECT-TYPE
    SYNTAX SnmpAdminString
    ACCESS read-only
    STATUS mandatory
    DESCRIPTION
        "The vCenter-specific UUID where this VM VDisk resides."
    ::= { vmvcAimStatVMVDiskEntry 38 }


-- *****************************************************************************
-- Status Host Disk Group 
-- *****************************************************************************
vmvcAimStatHostDiskCount OBJECT-TYPE
    SYNTAX INTEGER
    ACCESS read-only
    STATUS mandatory
    DESCRIPTION
        "Number of Disks in vmvcAimStatHostDiskTable."
    ::= { vmvcAimStatHostDiskGroup 1 }

vmvcAimStatHostDiskTable OBJECT-TYPE
    SYNTAX SEQUENCE OF VmvcAimStatHostDiskRow
    ACCESS not-accessible
    STATUS mandatory
    DESCRIPTION
        "Disk table."
    ::= { vmvcAimStatHostDiskGroup 2 }

vmvcAimStatHostDiskEntry OBJECT-TYPE
    SYNTAX VmvcAimStatHostDiskRow
    ACCESS not-accessible
    STATUS mandatory
    DESCRIPTION
        "The table entry."
    INDEX { vmvcAimStatHostDiskUID  }
    ::= { vmvcAimStatHostDiskTable 1 }

VmvcAimStatHostDiskRow ::=
    SEQUENCE {
        vmvcAimStatHostDiskUID                      INTEGER,
        vmvcAimStatHostDiskHostID                   SnmpAdminString,
        vmvcAimStatHostDiskName                     SnmpAdminString,
        vmvcAimStatHostDiskBusResets                Gauge,
        vmvcAimStatHostDiskCmdAborted               Gauge,
        vmvcAimStatHostDiskRead                     Gauge,
        vmvcAimStatHostDiskWrite                    Gauge,
        vmvcAimStatHostDiskKBPSRead                 Gauge,
        vmvcAimStatHostDiskKBPSWrite                Gauge,
        vmvcAimStatHostDiskDatastoreName            SnmpAdminString,
        vmvcAimStatHostDiskReadPerSec               Gauge,
        vmvcAimStatHostDiskWritePerSec              Gauge,
        vmvcAimStatHostDiskKBPSReadPerSec           Gauge,
        vmvcAimStatHostDiskKBPSWritePerSec          Gauge,
        vmvcAimStatHostDiskCommandsAbortedPerSec    Gauge,
        vmvcAimStatHostDiskBusResetsPerSec          Gauge,
        vmvcAimStatHostDiskTotalReadLatency         Gauge,
        vmvcAimStatHostDiskTotalWriteLatency        Gauge,
        vmvcAimStatHostDiskTotalLatency             Gauge,
        vmvcAimStatHostDiskDeviceReadLatency        Gauge,
        vmvcAimStatHostDiskDeviceWriteLatency       Gauge,
        vmvcAimStatHostDiskDeviceLatency            Gauge,
        vmvcAimStatHostDiskQueueReadLatency         Gauge,
        vmvcAimStatHostDiskQueueWriteLatency        Gauge,
        vmvcAimStatHostDiskQueueLatency             Gauge,
        vmvcAimStatHostDiskKernelReadLatency        Gauge,
        vmvcAimStatHostDiskKernelWriteLatency       Gauge,
        vmvcAimStatHostDiskKernelLatency            Gauge,
        vmvcAimStatHostDiskMaxTotalLatency          Gauge,
        vmvcAimStatHostDiskVCUID                    INTEGER,
        vmvcAimStatHostDiskVCName                   SnmpAdminString,
        vmvcAimStatHostDiskVCUUID                   SnmpAdminString
    }

vmvcAimStatHostDiskUID  OBJECT-TYPE
    SYNTAX INTEGER (1..2147483647)
    ACCESS read-only
    STATUS mandatory
    DESCRIPTION
        "Disk device UID"
    ::= { vmvcAimStatHostDiskEntry  1}

vmvcAimStatHostDiskHostID    OBJECT-TYPE
    SYNTAX SnmpAdminString
    ACCESS read-only
    STATUS mandatory
    DESCRIPTION
        "Moid of the host this Device is connected to."
    ::= { vmvcAimStatHostDiskEntry  2}

vmvcAimStatHostDiskName  OBJECT-TYPE
    SYNTAX SnmpAdminString
    ACCESS read-only
    STATUS mandatory
    DESCRIPTION
        "Name of the Disk"
    ::= { vmvcAimStatHostDiskEntry  3}

vmvcAimStatHostDiskBusResets  OBJECT-TYPE
    SYNTAX Gauge
    ACCESS read-only
    STATUS mandatory
    DESCRIPTION
        "Number of Bus Resets"
    ::= { vmvcAimStatHostDiskEntry  4}

vmvcAimStatHostDiskCmdAborted  OBJECT-TYPE
    SYNTAX Gauge
    ACCESS read-only
    STATUS mandatory
    DESCRIPTION
        "Number of Commands aborted"
    ::= { vmvcAimStatHostDiskEntry  5}

vmvcAimStatHostDiskRead  OBJECT-TYPE
    SYNTAX Gauge
    ACCESS read-only
    STATUS mandatory
    DESCRIPTION
        "Number of reads based on the past 20 seconds from the last poll."
    ::= { vmvcAimStatHostDiskEntry  6}

vmvcAimStatHostDiskWrite  OBJECT-TYPE
    SYNTAX Gauge
    ACCESS read-only
    STATUS mandatory
    DESCRIPTION
        "Number of writes based on the past 20 seconds from the last poll."
    ::= { vmvcAimStatHostDiskEntry  7 }

vmvcAimStatHostDiskKBPSRead  OBJECT-TYPE
    SYNTAX Gauge
    ACCESS read-only
    STATUS mandatory
    DESCRIPTION
        "KBPS read"
    ::= { vmvcAimStatHostDiskEntry  8}

vmvcAimStatHostDiskKBPSWrite  OBJECT-TYPE
    SYNTAX Gauge
    ACCESS read-only
    STATUS mandatory
    DESCRIPTION
        "KBPS written"
    ::= { vmvcAimStatHostDiskEntry  9}

vmvcAimStatHostDiskDatastoreName OBJECT-TYPE
    SYNTAX SnmpAdminString
    ACCESS read-only
    STATUS mandatory
    DESCRIPTION
        "Name of the Datastore"
    ::= { vmvcAimStatHostDiskEntry  10}

vmvcAimStatHostDiskReadPerSec  OBJECT-TYPE
    SYNTAX Gauge
    ACCESS read-only
    STATUS mandatory
    DESCRIPTION
        "Number of reads per sec"
    ::= { vmvcAimStatHostDiskEntry  11}

vmvcAimStatHostDiskWritePerSec  OBJECT-TYPE
    SYNTAX Gauge
    ACCESS read-only
    STATUS mandatory
    DESCRIPTION
        "Number of writes per sec"
    ::= { vmvcAimStatHostDiskEntry  12}

vmvcAimStatHostDiskKBPSReadPerSec  OBJECT-TYPE
    SYNTAX Gauge
    ACCESS read-only
    STATUS mandatory
    DESCRIPTION
        "KBPS read per sec"
    ::= { vmvcAimStatHostDiskEntry  13}

vmvcAimStatHostDiskKBPSWritePerSec  OBJECT-TYPE
    SYNTAX Gauge
    ACCESS read-only
    STATUS mandatory
    DESCRIPTION
        "KBPS written per sec"
    ::= { vmvcAimStatHostDiskEntry  14}

vmvcAimStatHostDiskCommandsAbortedPerSec  OBJECT-TYPE
    SYNTAX Gauge
    ACCESS read-only
    STATUS mandatory
    DESCRIPTION
        "Commands Aborted per sec"
    ::= { vmvcAimStatHostDiskEntry  15}

vmvcAimStatHostDiskBusResetsPerSec  OBJECT-TYPE
    SYNTAX Gauge
    ACCESS read-only
    STATUS mandatory
    DESCRIPTION
        "Disk Bus Resets per sec"
    ::= { vmvcAimStatHostDiskEntry  16}

vmvcAimStatHostDiskTotalReadLatency  OBJECT-TYPE
    SYNTAX Gauge
    ACCESS read-only
    STATUS mandatory
    DESCRIPTION
        "The average amount of time taken during the collection interval to process a SCSI read command issued from the Guest OS to the virtual machine. The sum of kernelReadLatency and deviceReadLatency."
    ::= { vmvcAimStatHostDiskEntry  17}

vmvcAimStatHostDiskTotalWriteLatency  OBJECT-TYPE
    SYNTAX Gauge
    ACCESS read-only
    STATUS mandatory
    DESCRIPTION
        "The average amount of time, in milliseconds, taken during the collection interval to process a SCSI write command issued by the Guest OS to the virtual machine. The sum of kernelWriteLatency and deviceWriteLatency."
    ::= { vmvcAimStatHostDiskEntry  18}

vmvcAimStatHostDiskTotalLatency  OBJECT-TYPE
    SYNTAX Gauge
    ACCESS read-only
    STATUS mandatory
    DESCRIPTION
        "The average amount of time, in milliseconds, taken during the collection interval to process a SCSI command issued by the Guest OS to the virtual machine. The sum of kernelLatency and deviceLatency."
    ::= { vmvcAimStatHostDiskEntry  19}

vmvcAimStatHostDiskDeviceReadLatency  OBJECT-TYPE
    SYNTAX Gauge
    ACCESS read-only
    STATUS mandatory
    DESCRIPTION
        "The average time, in milliseconds, taken to complete a read from the physical device"
    ::= { vmvcAimStatHostDiskEntry  20}

vmvcAimStatHostDiskDeviceWriteLatency  OBJECT-TYPE
    SYNTAX Gauge
    ACCESS read-only
    STATUS mandatory
    DESCRIPTION
        "The average amount of time, in milliseconds, to write to the physical device (LUN)."
    ::= { vmvcAimStatHostDiskEntry  21}

vmvcAimStatHostDiskDeviceLatency  OBJECT-TYPE
    SYNTAX Gauge
    ACCESS read-only
    STATUS mandatory
    DESCRIPTION
        "The average amount of time, in milliseconds, to complete a SCSI command from the physical device."
    ::= { vmvcAimStatHostDiskEntry  22}

vmvcAimStatHostDiskQueueReadLatency  OBJECT-TYPE
    SYNTAX Gauge
    ACCESS read-only
    STATUS mandatory
    DESCRIPTION
        "The average time, in milliseconds, spent in the ESX Server VMKernel queue per read."
    ::= { vmvcAimStatHostDiskEntry  23}

vmvcAimStatHostDiskQueueWriteLatency  OBJECT-TYPE
    SYNTAX Gauge
    ACCESS read-only
    STATUS mandatory
    DESCRIPTION
        "The average amount time, in milliseconds, taken during the collection interval per SCSI write command in the VMKernel queue."
    ::= { vmvcAimStatHostDiskEntry  24}

vmvcAimStatHostDiskQueueLatency  OBJECT-TYPE
    SYNTAX Gauge
    ACCESS read-only
    STATUS mandatory
    DESCRIPTION
        "The average amount of time, in milliseconds, spent in the VMkernel queue, per SCSI command, during the collection interval."
    ::= { vmvcAimStatHostDiskEntry  25}

vmvcAimStatHostDiskKernelReadLatency  OBJECT-TYPE
    SYNTAX Gauge
    ACCESS read-only
    STATUS mandatory
    DESCRIPTION
        "The average time, in milliseconds, spent in ESX Server VMKernel per read"
    ::= { vmvcAimStatHostDiskEntry  26}

vmvcAimStatHostDiskKernelWriteLatency  OBJECT-TYPE
    SYNTAX Gauge
    ACCESS read-only
    STATUS mandatory
    DESCRIPTION
        "The average amount of time, in milliseconds, spent by VMKernel processing each SCSI write command."
    ::= { vmvcAimStatHostDiskEntry  27}

vmvcAimStatHostDiskKernelLatency  OBJECT-TYPE
    SYNTAX Gauge
    ACCESS read-only
    STATUS mandatory
    DESCRIPTION
        "The average amount of time, in milliseconds, spent by VMkernel processing each SCSI command."
    ::= { vmvcAimStatHostDiskEntry  28}

vmvcAimStatHostDiskMaxTotalLatency  OBJECT-TYPE
    SYNTAX Gauge
    ACCESS read-only
    STATUS mandatory
    DESCRIPTION
        "Highest latency value across all disks used by the host, in milliseconds. Latency measures the time taken to process a SCSI command issued by the guest OS to the virtual machine. The kernel latency is the time VMkernel takes to process an IO request. The device latency is the time it takes the hardware to handle the request."
    ::= { vmvcAimStatHostDiskEntry  29}

vmvcAimStatHostDiskVCUID OBJECT-TYPE
    SYNTAX INTEGER
    ACCESS read-only
    STATUS mandatory
    DESCRIPTION
        "VC Instance SNMP UID where this Host Disk resides."
    ::= { vmvcAimStatHostDiskEntry  30}

vmvcAimStatHostDiskVCName OBJECT-TYPE
    SYNTAX SnmpAdminString
    ACCESS read-only
    STATUS mandatory
    DESCRIPTION
        "VC Instance where this Host Disk resides."
    ::= { vmvcAimStatHostDiskEntry  31}

vmvcAimStatHostDiskVCUUID OBJECT-TYPE
    SYNTAX SnmpAdminString
    ACCESS read-only
    STATUS mandatory
    DESCRIPTION
        "The vCenter-specific UUID where this Host Disk resides."
    ::= { vmvcAimStatHostDiskEntry  32}


-- *****************************************************************************
-- Status Host SCSI Controller Group 
-- *****************************************************************************
vmvcAimStatSCSIControllerCount OBJECT-TYPE
    SYNTAX INTEGER
    ACCESS read-only
    STATUS mandatory
    DESCRIPTION
        "Number of SCSI Controller in vmvcAimStatSCSIControllerTable."
    ::= { vmvcAimStatSCSIControllerGroup 1 }

vmvcAimStatSCSIControllerTable OBJECT-TYPE
    SYNTAX SEQUENCE OF VmvcAimStatSCSIControllerRow
    ACCESS not-accessible
    STATUS mandatory
    DESCRIPTION
        "SCSI Controller table."
    ::= { vmvcAimStatSCSIControllerGroup 2 }

vmvcAimStatSCSIControllerEntry OBJECT-TYPE
    SYNTAX VmvcAimStatSCSIControllerRow
    ACCESS not-accessible
    STATUS mandatory
    DESCRIPTION
        "The table entry."
    INDEX { vmvcAimStatSCSIControllerUID  }
    ::= { vmvcAimStatSCSIControllerTable 1 }

VmvcAimStatSCSIControllerRow ::=
    SEQUENCE {
        vmvcAimStatSCSIControllerUID            INTEGER,
        vmvcAimStatSCSIControllerVMID           SnmpAdminString,
        vmvcAimStatSCSIControllerName           SnmpAdminString,
        vmvcAimStatSCSIControllerSummary        SnmpAdminString,
        vmvcAimStatSCSIControllerKey            INTEGER,
        vmvcAimStatSCSIControllerControllerKey  INTEGER,
        vmvcAimStatSCSIControllerBusNumber      INTEGER,
        vmvcAimStatSCSIControllerUnitNumber     INTEGER,
        vmvcAimStatSCSIControllerVCUID          INTEGER,
        vmvcAimStatSCSIControllerVCName         SnmpAdminString,
        vmvcAimStatSCSIControllerVCUUID         SnmpAdminString
    }

vmvcAimStatSCSIControllerUID  OBJECT-TYPE
    SYNTAX INTEGER (1..2147483647)
    ACCESS read-only
    STATUS mandatory
    DESCRIPTION
        "SCSI Controller UID"
    ::= { vmvcAimStatSCSIControllerEntry  1}

vmvcAimStatSCSIControllerVMID    OBJECT-TYPE
    SYNTAX SnmpAdminString
    ACCESS read-only
    STATUS mandatory
    DESCRIPTION
        "The ID of the VM that the SCSI Controller is associated with."
    ::= { vmvcAimStatSCSIControllerEntry  2}

vmvcAimStatSCSIControllerName  OBJECT-TYPE
    SYNTAX SnmpAdminString
    ACCESS read-only
    STATUS mandatory
    DESCRIPTION
        "The name of the SCSI Controller."
    ::= { vmvcAimStatSCSIControllerEntry  3}
            
vmvcAimStatSCSIControllerSummary  OBJECT-TYPE
    SYNTAX SnmpAdminString
    ACCESS read-only
    STATUS mandatory
    DESCRIPTION
        "The SCSI Controller summary (type)."
    ::= { vmvcAimStatSCSIControllerEntry  4}

vmvcAimStatSCSIControllerKey  OBJECT-TYPE
    SYNTAX INTEGER
    ACCESS read-only
    STATUS mandatory
    DESCRIPTION
        "The identifier for the SCSI interface."
    ::= { vmvcAimStatSCSIControllerEntry  5}

vmvcAimStatSCSIControllerControllerKey  OBJECT-TYPE
    SYNTAX INTEGER
    ACCESS read-only
    STATUS mandatory
    DESCRIPTION
        "Object key that denotes the controller object for this device. This property contains 
         the key property value of the controller device object."
    ::= { vmvcAimStatSCSIControllerEntry  6}

vmvcAimStatSCSIControllerBusNumber  OBJECT-TYPE
    SYNTAX INTEGER
    ACCESS read-only
    STATUS mandatory
    DESCRIPTION
        "Bus number associated with this controller."
    ::= { vmvcAimStatSCSIControllerEntry  7}

vmvcAimStatSCSIControllerUnitNumber  OBJECT-TYPE
    SYNTAX INTEGER
    ACCESS read-only
    STATUS mandatory
    DESCRIPTION
        "Unit number of this device on its controller. This property is null if the controller property is null 
         (for example, when the device is not attached to a specific controller object). 
         Normally, two devices on the same controller may not be assigned the same unit number. "
    ::= { vmvcAimStatSCSIControllerEntry  8}

vmvcAimStatSCSIControllerVCUID OBJECT-TYPE
    SYNTAX INTEGER
    ACCESS read-only
    STATUS mandatory
    DESCRIPTION
        "VC Instance SNMP UID where this SCSI Controller resides."
    ::= { vmvcAimStatSCSIControllerEntry  9 }

vmvcAimStatSCSIControllerVCName OBJECT-TYPE
    SYNTAX SnmpAdminString
    ACCESS read-only
    STATUS mandatory
    DESCRIPTION
        "VC Instance where this SCSI Controller resides."
    ::= { vmvcAimStatSCSIControllerEntry  10 }

vmvcAimStatSCSIControllerVCUUID OBJECT-TYPE
    SYNTAX SnmpAdminString
    ACCESS read-only
    STATUS mandatory
    DESCRIPTION
        "The vCenter-specific UUID where this SCSI Controller resides."
    ::= { vmvcAimStatSCSIControllerEntry  11 }


-- *****************************************************************************
-- Status VM Guest Disk Group 
-- *****************************************************************************
vmvcAimStatVMGuestDiskCount OBJECT-TYPE
    SYNTAX INTEGER
    ACCESS read-only
    STATUS mandatory
    DESCRIPTION
        "Number of VM Guest Disks in vmvcAimStatVMGuestDiskTable."
    ::= { vmvcAimStatVMGuestDiskGroup 1 }

vmvcAimStatVMGuestDiskTable OBJECT-TYPE
    SYNTAX SEQUENCE OF VmvcAimStatVMGuestDiskRow
    ACCESS not-accessible
    STATUS mandatory
    DESCRIPTION
        "VM Guest Disk table."
    ::= { vmvcAimStatVMGuestDiskGroup 2 }

vmvcAimStatVMGuestDiskEntry OBJECT-TYPE
    SYNTAX VmvcAimStatVMGuestDiskRow
    ACCESS not-accessible
    STATUS mandatory
    DESCRIPTION
        "The table entry."
    INDEX { vmvcAimStatVMGuestDiskUID  }
    ::= { vmvcAimStatVMGuestDiskTable 1 }

VmvcAimStatVMGuestDiskRow ::=
    SEQUENCE {
            vmvcAimStatVMGuestDiskUID               INTEGER,
            vmvcAimStatVMGuestDiskVMID              SnmpAdminString,
            vmvcAimStatVMGuestDiskVMName            SnmpAdminString,
            vmvcAimStatVMGuestDiskPath              SnmpAdminString,
            vmvcAimStatVMGuestDiskCapacity          INTEGER,
            vmvcAimStatVMGuestDiskFreeSpace         INTEGER,
            vmvcAimStatVMGuestDiskUsagePct          Gauge,
            vmvcAimStatVMGuestDiskMonitor           INTEGER,
            vmvcAimStatVMGuestDiskAlert             INTEGER,
            vmvcAimStatVMGuestDiskUsageWarnThresh   INTEGER,
            vmvcAimStatVMGuestDiskUsageCritThresh   INTEGER,
            vmvcAimStatVMGuestDiskState             INTEGER,
            vmvcAimStatVMGuestDiskVCUID             INTEGER,
            vmvcAimStatVMGuestDiskVCName            SnmpAdminString,
            vmvcAimStatVMGuestDiskVCUUID            SnmpAdminString
    }

vmvcAimStatVMGuestDiskUID  OBJECT-TYPE
    SYNTAX INTEGER (1..2147483647)
    ACCESS read-only
    STATUS mandatory
    DESCRIPTION
        "VM Guest Disk device UID"
    ::= { vmvcAimStatVMGuestDiskEntry  1}

vmvcAimStatVMGuestDiskVMID    OBJECT-TYPE
    SYNTAX SnmpAdminString
    ACCESS read-only
    STATUS mandatory
    DESCRIPTION
        "Moid of the virtual machine this Device is connected to."
    ::= { vmvcAimStatVMGuestDiskEntry  2}

vmvcAimStatVMGuestDiskVMName  OBJECT-TYPE
    SYNTAX SnmpAdminString
    ACCESS read-only
    STATUS mandatory
    DESCRIPTION
        "Name of the virtual machine this Device is connected to."
    ::= { vmvcAimStatVMGuestDiskEntry  3}

vmvcAimStatVMGuestDiskPath  OBJECT-TYPE
    SYNTAX SnmpAdminString
    ACCESS read-only
    STATUS mandatory
    DESCRIPTION
        "Path of the VM Guest Disk."
    ::= { vmvcAimStatVMGuestDiskEntry  4}

vmvcAimStatVMGuestDiskCapacity  OBJECT-TYPE
    SYNTAX INTEGER
    ACCESS read-only
    STATUS mandatory
    DESCRIPTION
        "Capacity of Device in MB."
    ::= { vmvcAimStatVMGuestDiskEntry  5}

vmvcAimStatVMGuestDiskFreeSpace OBJECT-TYPE
    SYNTAX INTEGER
    ACCESS read-only
    STATUS mandatory
    DESCRIPTION
        "Free space of device in MB."
    ::= { vmvcAimStatVMGuestDiskEntry  6}

vmvcAimStatVMGuestDiskUsagePct OBJECT-TYPE
    SYNTAX Gauge
    ACCESS read-only
    STATUS mandatory
    DESCRIPTION
        "Disk usage in percent."
    ::= { vmvcAimStatVMGuestDiskEntry  7}

vmvcAimStatVMGuestDiskMonitor OBJECT-TYPE
    SYNTAX INTEGER {
        do-not-monitor(1),
        monitor(2)
    }
    ACCESS read-write
    STATUS mandatory
    DESCRIPTION
        "Flag indicating whether the Guest Disk Usage is to be 
         monitored(2) or not(1)."
    DEFVAL { 2 }
    ::= { vmvcAimStatVMGuestDiskEntry  8}

vmvcAimStatVMGuestDiskAlert OBJECT-TYPE
    SYNTAX INTEGER {
        warning-only(1),
        critical-only(2),
        both(3)
        }
    ACCESS read-write
    STATUS mandatory
    DESCRIPTION
        "Guest Disk Usage Alert.  This may be warning, critical or 
         both."
    DEFVAL { 3 }
    ::= { vmvcAimStatVMGuestDiskEntry  9}

vmvcAimStatVMGuestDiskUsageWarnThresh OBJECT-TYPE
    SYNTAX INTEGER
    ACCESS read-write
    STATUS mandatory
    DESCRIPTION
        "VM Guest Disk percentage usage Warning Threshold."
    DEFVAL { 60 }
    ::= { vmvcAimStatVMGuestDiskEntry  10}

vmvcAimStatVMGuestDiskUsageCritThresh OBJECT-TYPE
    SYNTAX INTEGER
    ACCESS read-write
    STATUS mandatory
    DESCRIPTION
        "VM Guest Disk percentage usage Critical Threshold."
    DEFVAL { 80 }
    ::= { vmvcAimStatVMGuestDiskEntry  11}

vmvcAimStatVMGuestDiskState OBJECT-TYPE
    SYNTAX INTEGER {
        unknown(1),
        ok(2),
        warning(3),
        critical(4)
    }
    ACCESS read-only
    STATUS mandatory
    DESCRIPTION
        "State of VM Guest Disk."
    ::= { vmvcAimStatVMGuestDiskEntry 12}
        
vmvcAimStatVMGuestDiskVCUID OBJECT-TYPE
    SYNTAX INTEGER
    ACCESS read-only
    STATUS mandatory
    DESCRIPTION
        "VC Instance SNMP UID where this VM Guest Disk resides."
    ::= { vmvcAimStatVMGuestDiskEntry  13 }

vmvcAimStatVMGuestDiskVCName OBJECT-TYPE
    SYNTAX SnmpAdminString
    ACCESS read-only
    STATUS mandatory
    DESCRIPTION
        "VC Instance where this VM Guest Disk resides."
    ::= { vmvcAimStatVMGuestDiskEntry  14 }

vmvcAimStatVMGuestDiskVCUUID OBJECT-TYPE
    SYNTAX SnmpAdminString
    ACCESS read-only
    STATUS mandatory
    DESCRIPTION
        "The vCenter-specific UUID where this VM Guest Disk resides."
    ::= { vmvcAimStatVMGuestDiskEntry  15 }


-- *****************************************************************************
-- Status CPU Sensor Group
-- *****************************************************************************
vmvcAimStatCPUSensorCount OBJECT-TYPE
    SYNTAX INTEGER
    ACCESS read-only
    STATUS mandatory
    DESCRIPTION
        "Host CPU Sensor count in vmvcAimStatCPUSensorTable."
    ::= { vmvcAimStatCPUSensorGroup 1}

vmvcAimStatCPUSensorTable OBJECT-TYPE
    SYNTAX SEQUENCE OF VmvcAimStatCPUSensorRow
    ACCESS not-accessible
    STATUS mandatory
    DESCRIPTION
        "CPU Sensor."
    ::= { vmvcAimStatCPUSensorGroup 2 }

vmvcAimStatCPUSensorEntry OBJECT-TYPE
    SYNTAX VmvcAimStatCPUSensorRow
    ACCESS not-accessible
    STATUS mandatory
    DESCRIPTION
        "The table entry."
    INDEX { vmvcAimStatCPUSensorUID }
    ::= { vmvcAimStatCPUSensorTable 1 }

VmvcAimStatCPUSensorRow ::=
    SEQUENCE {
        vmvcAimStatCPUSensorUID         INTEGER,
        vmvcAimStatCPUSensorName        SnmpAdminString,
        vmvcAimStatCPUSensorHostIndex   SnmpAdminString,
        vmvcAimStatCPUSensorHostName    SnmpAdminString,
        vmvcAimStatCPUSensorState       INTEGER,
        vmvcAimStatCPUSensorStatus      INTEGER,
        vmvcAimStatCPUSensorAlert       INTEGER,
        vmvcAimStatCPUSensorMonitor     INTEGER,
        vmvcAimStatCPUSensorVCUID       INTEGER,
        vmvcAimStatCPUSensorVCName      SnmpAdminString,
        vmvcAimStatCPUSensorVCUUID      SnmpAdminString
    }

vmvcAimStatCPUSensorUID OBJECT-TYPE
    SYNTAX INTEGER (1..2147483647)
    ACCESS read-only
    STATUS mandatory
    DESCRIPTION
        "UID of the CPU Sensor"
    ::= { vmvcAimStatCPUSensorEntry  1}

vmvcAimStatCPUSensorName OBJECT-TYPE
    SYNTAX SnmpAdminString
    ACCESS read-only
    STATUS mandatory
    DESCRIPTION
        "Name of the CPU Sensor"
    ::= { vmvcAimStatCPUSensorEntry  2}

vmvcAimStatCPUSensorHostIndex OBJECT-TYPE
    SYNTAX SnmpAdminString
    ACCESS read-only
    STATUS mandatory
    DESCRIPTION
        "Moid of Host which has this CPU"
    ::= { vmvcAimStatCPUSensorEntry  3}

vmvcAimStatCPUSensorHostName OBJECT-TYPE
    SYNTAX SnmpAdminString
    ACCESS read-only
    STATUS mandatory
    DESCRIPTION
        "The Hostname which has this CPU"
    ::= { vmvcAimStatCPUSensorEntry  4}

vmvcAimStatCPUSensorState OBJECT-TYPE
    SYNTAX INTEGER {
        unknown(1),
        ok(2),
        warning(3),
        critical(4)
    }
    ACCESS read-only
    STATUS mandatory
    DESCRIPTION
        "The state of CPU Sensor(ok,warning,critical)"
    ::= { vmvcAimStatCPUSensorEntry  5}

vmvcAimStatCPUSensorStatus OBJECT-TYPE
    SYNTAX INTEGER {
        gray(1),
        green(2),
        yellow(3),
        red(4)
    }
    ACCESS read-only
    STATUS mandatory
    DESCRIPTION
        "The state of CPU Sensor(green,red,yellow,unknown)"
    ::= { vmvcAimStatCPUSensorEntry  6}

vmvcAimStatCPUSensorAlert OBJECT-TYPE
    SYNTAX INTEGER {
        not-green-warn(1),
        not-green-critical(2)
    }
    ACCESS read-write
    STATUS mandatory
    DESCRIPTION
        "Level for the alert"
    DEFVAL { 2 }
    ::= { vmvcAimStatCPUSensorEntry  7}

vmvcAimStatCPUSensorMonitor OBJECT-TYPE
    SYNTAX INTEGER {
        do-not-monitor(1),
        monitor(2)
    }
    ACCESS read-write
    STATUS mandatory
    DESCRIPTION
        "Flag whether to monitor the Sensor or not"
    DEFVAL { 2 }
    ::= { vmvcAimStatCPUSensorEntry  8}

vmvcAimStatCPUSensorVCUID OBJECT-TYPE
    SYNTAX INTEGER
    ACCESS read-only
    STATUS mandatory
    DESCRIPTION
        "VC Instance SNMP UID where this CPU Sensor resides."
    ::= { vmvcAimStatCPUSensorEntry 9 }

vmvcAimStatCPUSensorVCName OBJECT-TYPE
    SYNTAX SnmpAdminString
    ACCESS read-only
    STATUS mandatory
    DESCRIPTION
        "VC Instance where this CPU Sensor resides."
    ::= { vmvcAimStatCPUSensorEntry 10 }

vmvcAimStatCPUSensorVCUUID OBJECT-TYPE
    SYNTAX SnmpAdminString
    ACCESS read-only
    STATUS mandatory
    DESCRIPTION
        "The vCenter-specific UUID where this CPU Sensor resides."
    ::= { vmvcAimStatCPUSensorEntry 11 }


-- *****************************************************************************
-- Status Memory Sensor Group
-- *****************************************************************************
vmvcAimStatMemSensorCount OBJECT-TYPE
    SYNTAX INTEGER
    ACCESS read-only
    STATUS mandatory
    DESCRIPTION
        "Host Mem Sensor count in vmvcAimStatMemSensorTable."
    ::= { vmvcAimStatMemSensorGroup 1}

vmvcAimStatMemSensorTable OBJECT-TYPE
    SYNTAX SEQUENCE OF VmvcAimStatMemSensorRow
    ACCESS not-accessible
    STATUS mandatory
    DESCRIPTION
        "Mem Sensor."
    ::= { vmvcAimStatMemSensorGroup 2 }

vmvcAimStatMemSensorEntry OBJECT-TYPE
    SYNTAX VmvcAimStatMemSensorRow
    ACCESS not-accessible
    STATUS mandatory
    DESCRIPTION
        "The table entry."
    INDEX { vmvcAimStatMemSensorUID }
    ::= { vmvcAimStatMemSensorTable 1 }

VmvcAimStatMemSensorRow ::=
    SEQUENCE {
        vmvcAimStatMemSensorUID         INTEGER,
        vmvcAimStatMemSensorName        SnmpAdminString,
        vmvcAimStatMemSensorHostIndex   SnmpAdminString,
        vmvcAimStatMemSensorHostName    SnmpAdminString,
        vmvcAimStatMemSensorState       INTEGER,
        vmvcAimStatMemSensorStatus      INTEGER,
        vmvcAimStatMemSensorAlert       INTEGER,
        vmvcAimStatMemSensorMonitor     INTEGER,
        vmvcAimStatMemSensorVCUID       INTEGER,
        vmvcAimStatMemSensorVCName      SnmpAdminString,
        vmvcAimStatMemSensorVCUUID      SnmpAdminString
    }

vmvcAimStatMemSensorUID OBJECT-TYPE
    SYNTAX INTEGER (1..2147483647)
    ACCESS read-only
    STATUS mandatory
    DESCRIPTION
        "UID of the Mem Sensor"
    ::= { vmvcAimStatMemSensorEntry  1}

vmvcAimStatMemSensorName OBJECT-TYPE
    SYNTAX SnmpAdminString
    ACCESS read-only
    STATUS mandatory
    DESCRIPTION
        "Name of the Mem Sensor"
    ::= { vmvcAimStatMemSensorEntry  2}

vmvcAimStatMemSensorHostIndex OBJECT-TYPE
    SYNTAX SnmpAdminString
    ACCESS read-only
    STATUS mandatory
    DESCRIPTION
        "Moid of Host which has this Mem"
    ::= { vmvcAimStatMemSensorEntry  3}

vmvcAimStatMemSensorHostName OBJECT-TYPE
    SYNTAX SnmpAdminString
    ACCESS read-only
    STATUS mandatory
    DESCRIPTION
        "The Hostname which has this Mem"
    ::= { vmvcAimStatMemSensorEntry  4}

vmvcAimStatMemSensorState OBJECT-TYPE
    SYNTAX INTEGER {
        unknown(1),
        ok(2),
        warning(3),
        critical(4)
    }
    ACCESS read-only
    STATUS mandatory
    DESCRIPTION
        "The state of Mem Sensor(ok,warning,critical)"
    ::= { vmvcAimStatMemSensorEntry  5}

vmvcAimStatMemSensorStatus OBJECT-TYPE
    SYNTAX INTEGER {
        gray(1),
        green(2),
        yellow(3),
        red(4)
    }
    ACCESS read-only
    STATUS mandatory
    DESCRIPTION
        "The state of Mem Sensor(green,red,yellow,unknown)"
    ::= { vmvcAimStatMemSensorEntry  6}

vmvcAimStatMemSensorAlert OBJECT-TYPE
    SYNTAX INTEGER {
        not-green-warn(1),
        not-green-critical(2)
    }
    ACCESS read-write
    STATUS mandatory
    DESCRIPTION
        "Level for the alert"
    DEFVAL { 2 }
    ::= { vmvcAimStatMemSensorEntry  7}

vmvcAimStatMemSensorMonitor OBJECT-TYPE
    SYNTAX INTEGER {
        do-not-monitor(1),
        monitor(2)
    }
    ACCESS read-write
    STATUS mandatory
    DESCRIPTION
        "Flag whether to monitor the Sensor or not"
    DEFVAL { 2 }
    ::= { vmvcAimStatMemSensorEntry  8}

vmvcAimStatMemSensorVCUID OBJECT-TYPE
    SYNTAX INTEGER
    ACCESS read-only
    STATUS mandatory
    DESCRIPTION
        "VC Instance SNMP UID where this Memory Sensor resides."
    ::= { vmvcAimStatMemSensorEntry 9 }

vmvcAimStatMemSensorVCName OBJECT-TYPE
    SYNTAX SnmpAdminString
    ACCESS read-only
    STATUS mandatory
    DESCRIPTION
        "VC Instance where this Memory Sensor resides."
    ::= { vmvcAimStatMemSensorEntry 10 }

vmvcAimStatMemSensorVCUUID OBJECT-TYPE
    SYNTAX SnmpAdminString
    ACCESS read-only
    STATUS mandatory
    DESCRIPTION
        "The vCenter-specific UUId where this Memory Sensor resides."
    ::= { vmvcAimStatMemSensorEntry 11 }


-- *****************************************************************************
-- Status Fan Sensor Group
-- *****************************************************************************
vmvcAimStatFanSensorCount OBJECT-TYPE
    SYNTAX INTEGER
    ACCESS read-only
    STATUS mandatory
    DESCRIPTION
        "Host Fan Sensor count in vmvcAimStatFanSensorTable."
    ::= { vmvcAimStatFanSensorGroup 1}

vmvcAimStatFanSensorTable OBJECT-TYPE
    SYNTAX SEQUENCE OF VmvcAimStatFanSensorRow
    ACCESS not-accessible
    STATUS mandatory
    DESCRIPTION
        "Fan Sensor."
    ::= { vmvcAimStatFanSensorGroup 2 }

vmvcAimStatFanSensorEntry OBJECT-TYPE
    SYNTAX VmvcAimStatFanSensorRow
    ACCESS not-accessible
    STATUS mandatory
    DESCRIPTION
        "The table entry."
    INDEX { vmvcAimStatFanSensorUID }
    ::= { vmvcAimStatFanSensorTable 1 }

VmvcAimStatFanSensorRow ::=
    SEQUENCE {
        vmvcAimStatFanSensorUID         INTEGER,
        vmvcAimStatFanSensorName        SnmpAdminString,
        vmvcAimStatFanSensorHostIndex   SnmpAdminString,
        vmvcAimStatFanSensorHostName    SnmpAdminString,
        vmvcAimStatFanSensorState       INTEGER,
        vmvcAimStatFanSensorStatus      INTEGER,
        vmvcAimStatFanSensorRPM         INTEGER,
        vmvcAimStatFanSensorAlert       INTEGER,
        vmvcAimStatFanSensorMonitor     INTEGER,
        vmvcAimStatFanSensorVCUID       INTEGER,
        vmvcAimStatFanSensorVCName      SnmpAdminString,
        vmvcAimStatFanSensorVCUUID      SnmpAdminString
    }

vmvcAimStatFanSensorUID OBJECT-TYPE
    SYNTAX INTEGER (1..2147483647)
    ACCESS read-only
    STATUS mandatory
    DESCRIPTION
        "UID of the Fan Sensor"
    ::= { vmvcAimStatFanSensorEntry  1}

vmvcAimStatFanSensorName OBJECT-TYPE
    SYNTAX SnmpAdminString
    ACCESS read-only
    STATUS mandatory
    DESCRIPTION
        "Name of the Fan Sensor"
    ::= { vmvcAimStatFanSensorEntry  2}

vmvcAimStatFanSensorHostIndex OBJECT-TYPE
    SYNTAX SnmpAdminString
    ACCESS read-only
    STATUS mandatory
    DESCRIPTION
        "Moid of Host which has this Fan"
    ::= { vmvcAimStatFanSensorEntry  3}

vmvcAimStatFanSensorHostName OBJECT-TYPE
    SYNTAX SnmpAdminString
    ACCESS read-only
    STATUS mandatory
    DESCRIPTION
        "The Hostname which has this Fan"
    ::= { vmvcAimStatFanSensorEntry  4}

vmvcAimStatFanSensorState OBJECT-TYPE
    SYNTAX INTEGER {
        unknown(1),
        ok(2),
        warning(3),
        critical(4)
    }
    ACCESS read-only
    STATUS mandatory
    DESCRIPTION
        "The state of Fan Sensor(ok,warning,critical)"
    ::= { vmvcAimStatFanSensorEntry  5}

vmvcAimStatFanSensorStatus OBJECT-TYPE
    SYNTAX INTEGER {
        gray(1),
        green(2),
        yellow(3),
        red(4)
    }
    ACCESS read-only
    STATUS mandatory
    DESCRIPTION
        "The state of Fan Sensor(green,red,yellow,unknown)"
    ::= { vmvcAimStatFanSensorEntry  6}

vmvcAimStatFanSensorRPM OBJECT-TYPE
    SYNTAX INTEGER
    ACCESS read-only
    STATUS mandatory
    DESCRIPTION
        "The RPM of Fan Sensor"
    ::= { vmvcAimStatFanSensorEntry  7}

vmvcAimStatFanSensorAlert OBJECT-TYPE
    SYNTAX INTEGER {
        not-green-warn(1),
        not-green-critical(2)
    }
    ACCESS read-write
    STATUS mandatory
    DESCRIPTION
        "Level for the alert"
    DEFVAL { 2 }
    ::= { vmvcAimStatFanSensorEntry  8}

vmvcAimStatFanSensorMonitor OBJECT-TYPE
    SYNTAX INTEGER {
        do-not-monitor(1),
        monitor(2)
    }
    ACCESS read-write
    STATUS mandatory
    DESCRIPTION
        "Flag whether to monitor the Sensor or not"
    DEFVAL { 2 }
    ::= { vmvcAimStatFanSensorEntry  9}

vmvcAimStatFanSensorVCUID OBJECT-TYPE
    SYNTAX INTEGER
    ACCESS read-only
    STATUS mandatory
    DESCRIPTION
        "VC Instance SNMP UID where this Fan Sensor resides."
    ::= { vmvcAimStatFanSensorEntry 10 }

vmvcAimStatFanSensorVCName OBJECT-TYPE
    SYNTAX SnmpAdminString
    ACCESS read-only
    STATUS mandatory
    DESCRIPTION
        "VC Instance where this Fan Sensor resides."
    ::= { vmvcAimStatFanSensorEntry 11 }

vmvcAimStatFanSensorVCUUID OBJECT-TYPE
    SYNTAX SnmpAdminString
    ACCESS read-only
    STATUS mandatory
    DESCRIPTION
        "The vCenter-specific UUID where this Fan Sensor resides."
    ::= { vmvcAimStatFanSensorEntry 12 }


-- *****************************************************************************
-- Status Voltage Sensor Group
-- *****************************************************************************
vmvcAimStatVoltageSensorCount OBJECT-TYPE
    SYNTAX INTEGER
    ACCESS read-only
    STATUS mandatory
    DESCRIPTION
        "Host Voltage Sensor count in vmvcAimStatVoltageSensorTable."
    ::= { vmvcAimStatVoltageSensorGroup 1}

vmvcAimStatVoltageSensorTable OBJECT-TYPE
    SYNTAX SEQUENCE OF VmvcAimStatVoltageSensorRow
    ACCESS not-accessible
    STATUS mandatory
    DESCRIPTION
        "Voltage Sensor."
    ::= { vmvcAimStatVoltageSensorGroup 2 }

vmvcAimStatVoltageSensorEntry OBJECT-TYPE
    SYNTAX VmvcAimStatVoltageSensorRow
    ACCESS not-accessible
    STATUS mandatory
    DESCRIPTION
        "The table entry."
    INDEX { vmvcAimStatVoltageSensorUID }
    ::= { vmvcAimStatVoltageSensorTable 1 }

VmvcAimStatVoltageSensorRow ::=
    SEQUENCE {
        vmvcAimStatVoltageSensorUID         INTEGER,
        vmvcAimStatVoltageSensorName        SnmpAdminString,
        vmvcAimStatVoltageSensorHostIndex   SnmpAdminString,
        vmvcAimStatVoltageSensorHostName    SnmpAdminString,
        vmvcAimStatVoltageSensorState       INTEGER,
        vmvcAimStatVoltageSensorStatus      INTEGER,
        vmvcAimStatVoltageSensorVoltage     INTEGER,
        vmvcAimStatVoltageSensorAlert       INTEGER,
        vmvcAimStatVoltageSensorMonitor     INTEGER,
        vmvcAimStatVoltageSensorVCUID       INTEGER,
        vmvcAimStatVoltageSensorVCName      SnmpAdminString,
        vmvcAimStatVoltageSensorVCUUID      SnmpAdminString
    }


vmvcAimStatVoltageSensorUID OBJECT-TYPE
    SYNTAX INTEGER (1..2147483647)
    ACCESS read-only
    STATUS mandatory
    DESCRIPTION
        "UID of the Voltage Sensor"
    ::= { vmvcAimStatVoltageSensorEntry  1}

vmvcAimStatVoltageSensorName OBJECT-TYPE
    SYNTAX SnmpAdminString
    ACCESS read-only
    STATUS mandatory
    DESCRIPTION
        "Name of the Voltage Sensor"
    ::= { vmvcAimStatVoltageSensorEntry  2}

vmvcAimStatVoltageSensorHostIndex OBJECT-TYPE
    SYNTAX SnmpAdminString
    ACCESS read-only
    STATUS mandatory
    DESCRIPTION
        "Moid of Host which has this Voltage"
    ::= { vmvcAimStatVoltageSensorEntry  3}

vmvcAimStatVoltageSensorHostName OBJECT-TYPE
    SYNTAX SnmpAdminString
    ACCESS read-only
    STATUS mandatory
    DESCRIPTION
        "The Hostname which has this Voltage"
    ::= { vmvcAimStatVoltageSensorEntry  4}

vmvcAimStatVoltageSensorState OBJECT-TYPE
    SYNTAX INTEGER {
        unknown(1),
        ok(2),
        warning(3),
        critical(4)
    }
    ACCESS read-only
    STATUS mandatory
    DESCRIPTION
        "The state of Voltage Sensor(ok,warning,critical)"
    ::= { vmvcAimStatVoltageSensorEntry  5}

vmvcAimStatVoltageSensorStatus OBJECT-TYPE
    SYNTAX INTEGER {
        gray(1),
        green(2),
        yellow(3),
        red(4)
    }
    ACCESS read-only
    STATUS mandatory
    DESCRIPTION
        "The state of Voltage Sensor(green,yellow,red,unknown)"
    ::= { vmvcAimStatVoltageSensorEntry  6}

vmvcAimStatVoltageSensorVoltage OBJECT-TYPE
    SYNTAX INTEGER
    ACCESS read-only
    STATUS mandatory
    DESCRIPTION
        "The Voltage of Voltage Sensor in volts"
    ::= { vmvcAimStatVoltageSensorEntry  7}

vmvcAimStatVoltageSensorAlert OBJECT-TYPE
    SYNTAX INTEGER {
        not-green-warn(1),
        not-green-critical(2)
    }
    ACCESS read-write
    STATUS mandatory
    DESCRIPTION
        "Level for the alert"
    DEFVAL { 2 }
    ::= { vmvcAimStatVoltageSensorEntry  8}

vmvcAimStatVoltageSensorMonitor OBJECT-TYPE
    SYNTAX INTEGER {
        do-not-monitor(1),
        monitor(2)
    }
    ACCESS read-write
    STATUS mandatory
    DESCRIPTION
        "Flag whether to monitor the Sensor or not"
    DEFVAL { 2 }
    ::= { vmvcAimStatVoltageSensorEntry  9}

vmvcAimStatVoltageSensorVCUID OBJECT-TYPE
    SYNTAX INTEGER
    ACCESS read-only
    STATUS mandatory
    DESCRIPTION
        "VC Instance SNMP UID where this Voltage Sensor resides."
    ::= { vmvcAimStatVoltageSensorEntry 10 }

vmvcAimStatVoltageSensorVCName OBJECT-TYPE
    SYNTAX SnmpAdminString
    ACCESS read-only
    STATUS mandatory
    DESCRIPTION
        "VC Instance where this Voltage Sensor resides."
    ::= { vmvcAimStatVoltageSensorEntry 11 }

vmvcAimStatVoltageSensorVCUUID OBJECT-TYPE
    SYNTAX SnmpAdminString
    ACCESS read-only
    STATUS mandatory
    DESCRIPTION
        "The vCenter-specific UUID where this Voltage Sensor resides."
    ::= { vmvcAimStatVoltageSensorEntry 12 }


-- *****************************************************************************
-- Status Temp Sensor Group
-- *****************************************************************************
vmvcAimStatTempSensorCount OBJECT-TYPE
    SYNTAX INTEGER
    ACCESS read-only
    STATUS mandatory
    DESCRIPTION
        "Host Temp Sensor count in vmvcAimStatTempSensorTable."
    ::= { vmvcAimStatTempSensorGroup 1}

vmvcAimStatTempSensorTable OBJECT-TYPE
    SYNTAX SEQUENCE OF VmvcAimStatTempSensorRow
    ACCESS not-accessible
    STATUS mandatory
    DESCRIPTION
        "Temp Sensor."
    ::= { vmvcAimStatTempSensorGroup 2 }

vmvcAimStatTempSensorEntry OBJECT-TYPE
    SYNTAX VmvcAimStatTempSensorRow
    ACCESS not-accessible
    STATUS mandatory
    DESCRIPTION
        "The table entry."
    INDEX { vmvcAimStatTempSensorUID }
    ::= { vmvcAimStatTempSensorTable 1 }

VmvcAimStatTempSensorRow ::=
    SEQUENCE {
        vmvcAimStatTempSensorUID        INTEGER,
        vmvcAimStatTempSensorName       SnmpAdminString,
        vmvcAimStatTempSensorHostIndex  SnmpAdminString,
        vmvcAimStatTempSensorHostName   SnmpAdminString,
        vmvcAimStatTempSensorState      INTEGER,
        vmvcAimStatTempSensorStatus     INTEGER,
        vmvcAimStatTempSensorTemp       INTEGER,
        vmvcAimStatTempSensorAlert      INTEGER,
        vmvcAimStatTempSensorMonitor    INTEGER,
        vmvcAimStatTempSensorVCUID      INTEGER,
        vmvcAimStatTempSensorVCName     SnmpAdminString,
        vmvcAimStatTempSensorVCUUID     SnmpAdminString
    }

vmvcAimStatTempSensorUID OBJECT-TYPE
    SYNTAX INTEGER (1..2147483647)
    ACCESS read-only
    STATUS mandatory
    DESCRIPTION
        "UID of the Temp Sensor"
    ::= { vmvcAimStatTempSensorEntry  1}

vmvcAimStatTempSensorName OBJECT-TYPE
    SYNTAX SnmpAdminString
    ACCESS read-only
    STATUS mandatory
    DESCRIPTION
        "Name of the Temp Sensor"
    ::= { vmvcAimStatTempSensorEntry  2}

vmvcAimStatTempSensorHostIndex OBJECT-TYPE
    SYNTAX SnmpAdminString
    ACCESS read-only
    STATUS mandatory
    DESCRIPTION
        "Moid of Host which has this Temp"
    ::= { vmvcAimStatTempSensorEntry  3}

vmvcAimStatTempSensorHostName OBJECT-TYPE
    SYNTAX SnmpAdminString
    ACCESS read-only
    STATUS mandatory
    DESCRIPTION
        "The Hostname which has this Temp"
    ::= { vmvcAimStatTempSensorEntry  4}

vmvcAimStatTempSensorState OBJECT-TYPE
    SYNTAX INTEGER {
        unknown(1),
        ok(2),
        warning(3),
        critical(4)
    }
    ACCESS read-only
    STATUS mandatory
    DESCRIPTION
        "The state of Temp Sensor(ok,warning,critical)"
    ::= { vmvcAimStatTempSensorEntry  5}

vmvcAimStatTempSensorStatus OBJECT-TYPE
    SYNTAX INTEGER {
        gray(1),
        green(2),
        yellow(3),
        red(4)
    }
    ACCESS read-only
    STATUS mandatory
    DESCRIPTION
        "The state of Temp Sensor(green,red,yellow,unknown)"
    ::= { vmvcAimStatTempSensorEntry  6}

vmvcAimStatTempSensorTemp OBJECT-TYPE
    SYNTAX INTEGER
    ACCESS read-only
    STATUS mandatory
    DESCRIPTION
        "The Temp of Temp Sensor in Centigrade"
    ::= { vmvcAimStatTempSensorEntry  7}

vmvcAimStatTempSensorAlert OBJECT-TYPE
    SYNTAX INTEGER {
        not-green-warn(1),
        not-green-critical(2)
    }
    ACCESS read-write
    STATUS mandatory
    DESCRIPTION
        "Level for the alert"
    DEFVAL { 2 }
    ::= { vmvcAimStatTempSensorEntry  8}

vmvcAimStatTempSensorMonitor OBJECT-TYPE
    SYNTAX INTEGER {
        do-not-monitor(1),
        monitor(2)
    }
    ACCESS read-write
    STATUS mandatory
    DESCRIPTION
        "Flag whether to monitor the Sensor or not"
    DEFVAL { 2 }
    ::= { vmvcAimStatTempSensorEntry  9}

vmvcAimStatTempSensorVCUID OBJECT-TYPE
    SYNTAX INTEGER
    ACCESS read-only
    STATUS mandatory
    DESCRIPTION
        "VC Instance SNMP UID where this Temperature Sensor resides."
    ::= { vmvcAimStatTempSensorEntry 10 }

vmvcAimStatTempSensorVCName OBJECT-TYPE
    SYNTAX SnmpAdminString
    ACCESS read-only
    STATUS mandatory
    DESCRIPTION
        "VC Instance where this Temperature Sensor resides."
    ::= { vmvcAimStatTempSensorEntry 11 }

vmvcAimStatTempSensorVCUUID OBJECT-TYPE
    SYNTAX SnmpAdminString
    ACCESS read-only
    STATUS mandatory
    DESCRIPTION
        "The vCenter-specific UUID where this Temperature Sensor resides."
    ::= { vmvcAimStatTempSensorEntry 12 }


-- *****************************************************************************
-- Status Power Sensor Group
-- *****************************************************************************
vmvcAimStatPowerSensorCount OBJECT-TYPE
    SYNTAX INTEGER
    ACCESS read-only
    STATUS mandatory
    DESCRIPTION
        "Host Power Sensor count in vmvcAimStatTempSensorTable."
    ::= { vmvcAimStatPowerSensorGroup 1}

vmvcAimStatPowerSensorTable OBJECT-TYPE
    SYNTAX SEQUENCE OF VmvcAimStatPowerSensorRow
    ACCESS not-accessible
    STATUS mandatory
    DESCRIPTION
        "Power Sensor."
    ::= { vmvcAimStatPowerSensorGroup 2 }

vmvcAimStatPowerSensorEntry OBJECT-TYPE
    SYNTAX VmvcAimStatPowerSensorRow
    ACCESS not-accessible
    STATUS mandatory
    DESCRIPTION
        "The table entry."
    INDEX { vmvcAimStatPowerSensorUID }
    ::= { vmvcAimStatPowerSensorTable 1 }

VmvcAimStatPowerSensorRow ::=
    SEQUENCE {
        vmvcAimStatPowerSensorUID       INTEGER,
        vmvcAimStatPowerSensorName      SnmpAdminString,
        vmvcAimStatPowerSensorHostIndex SnmpAdminString,
        vmvcAimStatPowerSensorHostName  SnmpAdminString,
        vmvcAimStatPowerSensorState     INTEGER,
        vmvcAimStatPowerSensorStatus    INTEGER,
        vmvcAimStatPowerSensorWatts     INTEGER,
        vmvcAimStatPowerSensorAlert     INTEGER,
        vmvcAimStatPowerSensorMonitor   INTEGER,
        vmvcAimStatPowerSensorVCUID     INTEGER,
        vmvcAimStatPowerSensorVCName    SnmpAdminString,
        vmvcAimStatPowerSensorVCUUID    SnmpAdminString
    }

vmvcAimStatPowerSensorUID OBJECT-TYPE
    SYNTAX INTEGER (1..2147483647)
    ACCESS read-only
    STATUS mandatory
    DESCRIPTION
        "UID of the Power Sensor"
    ::= { vmvcAimStatPowerSensorEntry  1}

vmvcAimStatPowerSensorName OBJECT-TYPE
    SYNTAX SnmpAdminString
    ACCESS read-only
    STATUS mandatory
    DESCRIPTION
        "Name of the Power Sensor"
    ::= { vmvcAimStatPowerSensorEntry  2}

vmvcAimStatPowerSensorHostIndex OBJECT-TYPE
    SYNTAX SnmpAdminString
    ACCESS read-only
    STATUS mandatory
    DESCRIPTION
        "Moid of Host which has this Power Sensor"
    ::= { vmvcAimStatPowerSensorEntry  3}

vmvcAimStatPowerSensorHostName OBJECT-TYPE
    SYNTAX SnmpAdminString
    ACCESS read-only
    STATUS mandatory
    DESCRIPTION
        "The Hostname which has this Power Sensor"
    ::= { vmvcAimStatPowerSensorEntry  4}

vmvcAimStatPowerSensorState OBJECT-TYPE
    SYNTAX INTEGER {
        unknown(1),
        ok(2),
        warning(3),
        critical(4)
    }
    ACCESS read-only
    STATUS mandatory
    DESCRIPTION
        "The state of Power Sensor(ok,warning,critical)"
    ::= { vmvcAimStatPowerSensorEntry  5}

vmvcAimStatPowerSensorStatus OBJECT-TYPE
    SYNTAX INTEGER {
        gray(1),
        green(2),
        yellow(3),
        red(4)
    }
    ACCESS read-only
    STATUS mandatory
    DESCRIPTION
        "The state of Power Sensor(green,red,yellow,unknown)"
    ::= { vmvcAimStatPowerSensorEntry  6}

vmvcAimStatPowerSensorWatts OBJECT-TYPE
    SYNTAX INTEGER
    ACCESS read-only
    STATUS mandatory
    DESCRIPTION
        "The Consumption of Power in Watts"
    ::= { vmvcAimStatPowerSensorEntry  7}

vmvcAimStatPowerSensorAlert OBJECT-TYPE
    SYNTAX INTEGER {
        not-green-warn(1),
        not-green-critical(2)
    }
    ACCESS read-write
    STATUS mandatory
    DESCRIPTION
        "Level for the alert"
    DEFVAL { 2 }
    ::= { vmvcAimStatPowerSensorEntry  8}

vmvcAimStatPowerSensorMonitor OBJECT-TYPE
    SYNTAX INTEGER {
        do-not-monitor(1),
        monitor(2)
    }
    ACCESS read-write
    STATUS mandatory
    DESCRIPTION
        "Flag whether to monitor the Sensor or not"
    DEFVAL { 2 }
    ::= { vmvcAimStatPowerSensorEntry  9}

vmvcAimStatPowerSensorVCUID OBJECT-TYPE
    SYNTAX INTEGER
    ACCESS read-only
    STATUS mandatory
    DESCRIPTION
        "VC Instance SNMP UID where this Power Sensor resides."
    ::= { vmvcAimStatPowerSensorEntry 10 }

vmvcAimStatPowerSensorVCName OBJECT-TYPE
    SYNTAX SnmpAdminString
    ACCESS read-only
    STATUS mandatory
    DESCRIPTION
        "VC Instance where this Power Sensor resides."
    ::= { vmvcAimStatPowerSensorEntry 11 }

vmvcAimStatPowerSensorVCUUID OBJECT-TYPE
    SYNTAX SnmpAdminString
    ACCESS read-only
    STATUS mandatory
    DESCRIPTION
        "The vCenter-specific UUID where this Power Sensor resides."
    ::= { vmvcAimStatPowerSensorEntry 12 }


-- *****************************************************************************
-- Status Storage Sensor Group
-- *****************************************************************************
vmvcAimStatStorageSensorCount OBJECT-TYPE
    SYNTAX INTEGER
    ACCESS read-only
    STATUS mandatory
    DESCRIPTION
        "Host Storage Sensor count in vmvcAimStatTempSensorTable."
    ::= { vmvcAimStatStorageSensorGroup 1}

vmvcAimStatStorageSensorTable OBJECT-TYPE
    SYNTAX SEQUENCE OF VmvcAimStatStorageSensorRow
    ACCESS not-accessible
    STATUS mandatory
    DESCRIPTION
        "Storage Sensor."
    ::= { vmvcAimStatStorageSensorGroup 2 }

vmvcAimStatStorageSensorEntry OBJECT-TYPE
    SYNTAX VmvcAimStatStorageSensorRow
    ACCESS not-accessible
    STATUS mandatory
    DESCRIPTION
        "The table entry."
    INDEX { vmvcAimStatStorageSensorUID }
    ::= { vmvcAimStatStorageSensorTable 1 }

VmvcAimStatStorageSensorRow ::=
    SEQUENCE {
        vmvcAimStatStorageSensorUID         INTEGER,
        vmvcAimStatStorageSensorName        SnmpAdminString,
        vmvcAimStatStorageSensorHostIndex   SnmpAdminString,
        vmvcAimStatStorageSensorHostName    SnmpAdminString,
        vmvcAimStatStorageSensorState       INTEGER,
        vmvcAimStatStorageSensorStatus      INTEGER,
        vmvcAimStatStorageSensorAlert       INTEGER,
        vmvcAimStatStorageSensorMonitor     INTEGER,
        vmvcAimStatStorageSensorVCUID       INTEGER,
        vmvcAimStatStorageSensorVCName      SnmpAdminString,
        vmvcAimStatStorageSensorVCUUID      SnmpAdminString
    }

vmvcAimStatStorageSensorUID OBJECT-TYPE
    SYNTAX INTEGER (1..2147483647)
    ACCESS read-only
    STATUS mandatory
    DESCRIPTION
        "UID of the Storage Sensor"
    ::= { vmvcAimStatStorageSensorEntry  1}

vmvcAimStatStorageSensorName OBJECT-TYPE
    SYNTAX SnmpAdminString
    ACCESS read-only
    STATUS mandatory
    DESCRIPTION
        "Name of the Storage Sensor"
    ::= { vmvcAimStatStorageSensorEntry  2}

vmvcAimStatStorageSensorHostIndex OBJECT-TYPE
    SYNTAX SnmpAdminString
    ACCESS read-only
    STATUS mandatory
    DESCRIPTION
        "Moid of Host which has this Storage Sensor"
    ::= { vmvcAimStatStorageSensorEntry  3}

vmvcAimStatStorageSensorHostName OBJECT-TYPE
    SYNTAX SnmpAdminString
    ACCESS read-only
    STATUS mandatory
    DESCRIPTION
        "The Hostname which has this Storage Sensor"
    ::= { vmvcAimStatStorageSensorEntry  4}

vmvcAimStatStorageSensorState OBJECT-TYPE
    SYNTAX INTEGER {
        unknown(1),
        ok(2),
        warning(3),
        critical(4)
    }
    ACCESS read-only
    STATUS mandatory
    DESCRIPTION
        "The state of Storage Sensor(ok,warning,critical)"
    ::= { vmvcAimStatStorageSensorEntry  5}

vmvcAimStatStorageSensorStatus OBJECT-TYPE
    SYNTAX INTEGER {
        gray(1),
        green(2),
        yellow(3),
        red(4)
    }
    ACCESS read-only
    STATUS mandatory
    DESCRIPTION
        "The state of Storage Sensor(green,red,yellow,unknown)"
    ::= { vmvcAimStatStorageSensorEntry  6}

vmvcAimStatStorageSensorAlert OBJECT-TYPE
    SYNTAX INTEGER {
        not-green-warn(1),
        not-green-critical(2)
    }
    ACCESS read-write
    STATUS mandatory
    DESCRIPTION
        "Level for the alert"
    DEFVAL { 2 }
    ::= { vmvcAimStatStorageSensorEntry  7}

vmvcAimStatStorageSensorMonitor OBJECT-TYPE
    SYNTAX INTEGER {
        do-not-monitor(1),
        monitor(2)
    }
    ACCESS read-write
    STATUS mandatory
    DESCRIPTION
        "Flag whether to monitor the Sensor or not"
    DEFVAL { 2 }
    ::= { vmvcAimStatStorageSensorEntry  8}

vmvcAimStatStorageSensorVCUID OBJECT-TYPE
    SYNTAX INTEGER
    ACCESS read-only
    STATUS mandatory
    DESCRIPTION
        "VC Instance SNMP UID where this Storage Sensor resides."
    ::= { vmvcAimStatStorageSensorEntry 9 }

vmvcAimStatStorageSensorVCName OBJECT-TYPE
    SYNTAX SnmpAdminString
    ACCESS read-only
    STATUS mandatory
    DESCRIPTION
        "VC Instance where this Storage Sensor resides."
    ::= { vmvcAimStatStorageSensorEntry 10 }

vmvcAimStatStorageSensorVCUUID OBJECT-TYPE
    SYNTAX SnmpAdminString
    ACCESS read-only
    STATUS mandatory
    DESCRIPTION
        "The vCenter-specific UUID where this Storage Sensor resides."
    ::= { vmvcAimStatStorageSensorEntry 11 }


-- *****************************************************************************
-- Status Snapshot Specification Group
-- *****************************************************************************

vmvcAimStatSnapshotCount OBJECT-TYPE
    SYNTAX INTEGER
    ACCESS read-only
    STATUS mandatory
    DESCRIPTION
        "Number of Snapshot in vmvcAimStatSnapshotTable."
    ::= { vmvcAimStatSnapshotGroup 1}

vmvcAimStatSnapshotTable OBJECT-TYPE
    SYNTAX SEQUENCE OF VmvcAimStatSnapshotRow
    ACCESS not-accessible
    STATUS mandatory
    DESCRIPTION
        "Customization Specification table."
    ::= { vmvcAimStatSnapshotGroup 2 }

vmvcAimStatSnapshotEntry OBJECT-TYPE
    SYNTAX VmvcAimStatSnapshotRow
    ACCESS not-accessible
    STATUS mandatory
    DESCRIPTION
        "The table entry."
    INDEX { vmvcAimStatSnapshotUID }
    ::= { vmvcAimStatSnapshotTable 1 }

VmvcAimStatSnapshotRow ::=
    SEQUENCE {
        vmvcAimStatSnapshotUID          INTEGER,
        vmvcAimStatSnapshotParent       SnmpAdminString,
        vmvcAimStatSnapshotName         SnmpAdminString,
        vmvcAimStatSnapshotDescription  SnmpAdminString,
        vmvcAimStatSnapshotID           SnmpAdminString,
        vmvcAimStatSnapshotTime         INTEGER,
        vmvcAimStatSnapshotMemoryState  INTEGER,
        vmvcAimStatSnapshotQuiesce      INTEGER,
        vmvcAimStatSnapshotVMIndex      SnmpAdminString,
        vmvcAimStatSnapshotCurrent      INTEGER,
        vmvcAimStatSnapshotVCUID        INTEGER,
        vmvcAimStatSnapshotVCName       SnmpAdminString,
        vmvcAimStatSnapshotVCUUID       SnmpAdminString
    }

vmvcAimStatSnapshotUID OBJECT-TYPE
    SYNTAX INTEGER (1..2147483647)
    ACCESS read-only
    STATUS mandatory
    DESCRIPTION
        "Integer UID of the snapshot."
    ::= { vmvcAimStatSnapshotEntry  1}

vmvcAimStatSnapshotParent OBJECT-TYPE
    SYNTAX SnmpAdminString
    ACCESS read-only
    STATUS mandatory
    DESCRIPTION
        "ID of the parent snapshot or ID of the VM if there is 
         no parent snapshot."
    ::= { vmvcAimStatSnapshotEntry  2}

vmvcAimStatSnapshotName OBJECT-TYPE
    SYNTAX SnmpAdminString
    ACCESS read-only
    STATUS mandatory
    DESCRIPTION
        "Name of the snapshot."
    ::= { vmvcAimStatSnapshotEntry  3}

vmvcAimStatSnapshotDescription OBJECT-TYPE
    SYNTAX SnmpAdminString (SIZE(0..1024))
    ACCESS read-only
    STATUS mandatory
    DESCRIPTION
        "Description of the snapshot."
    ::= { vmvcAimStatSnapshotEntry  4}

vmvcAimStatSnapshotID OBJECT-TYPE
    SYNTAX SnmpAdminString
    ACCESS read-only
    STATUS mandatory
    DESCRIPTION
        "Id of the snapshot."
    ::= { vmvcAimStatSnapshotEntry  5}

vmvcAimStatSnapshotTime OBJECT-TYPE
    SYNTAX INTEGER
    ACCESS read-only
    STATUS mandatory
    DESCRIPTION
        "Number of seconds elapsed since midnight (00:00:00), January 1, 1970, 
         coordinated universal time (UTC) when the snapshot was taken."
    ::= { vmvcAimStatSnapshotEntry  6}

vmvcAimStatSnapshotMemoryState OBJECT-TYPE
    SYNTAX INTEGER 
    ACCESS read-only
    STATUS mandatory
    DESCRIPTION
        "A boolean Value used to represent the internal state of a virtual machine.
         If TRUE, a dump of the internal state of the virtual machine (basically a memory dump) is included in the snapshot.
         If FALSE, the power state of the snapshot is set to powered off. "
    ::= { vmvcAimStatSnapshotEntry  7}

vmvcAimStatSnapshotQuiesce OBJECT-TYPE
    SYNTAX INTEGER 
    ACCESS read-only
    STATUS mandatory
    DESCRIPTION
        "A boolean Value used for the quiesce the file system in the virtual machine.
         If TRUE and the virtual machine is powered on when the snapshot is taken, VMware Tools is used to quiesce the file
         system in the virtual machine. 
         If the    virutal machine is powered off or VMware Tools are not available, the quiesce flag is ignored."
    ::= { vmvcAimStatSnapshotEntry  8}

vmvcAimStatSnapshotVMIndex OBJECT-TYPE
    SYNTAX SnmpAdminString
    ACCESS read-only
    STATUS mandatory
    DESCRIPTION
        "The index (VMIndex) of the VM the snapshot is associated with."
    ::= { vmvcAimStatSnapshotEntry 9 }

vmvcAimStatSnapshotCurrent OBJECT-TYPE
    SYNTAX INTEGER {
        true(1),
        false(2)
        }
    ACCESS read-only
    STATUS mandatory
    DESCRIPTION
        "A boolean value indicating whether this snapshot is the current snapshot the VM is running."
    ::= { vmvcAimStatSnapshotEntry  10}

vmvcAimStatSnapshotVCUID OBJECT-TYPE
    SYNTAX INTEGER
    ACCESS read-only
    STATUS mandatory
    DESCRIPTION
        "VC Instance SNMP UID where this Snapshot resides."
    ::= { vmvcAimStatSnapshotEntry 11 }

vmvcAimStatSnapshotVCName OBJECT-TYPE
    SYNTAX SnmpAdminString
    ACCESS read-only
    STATUS mandatory
    DESCRIPTION
        "VC Instance where this Snapshot resides."
    ::= { vmvcAimStatSnapshotEntry 12 }

vmvcAimStatSnapshotVCUUID OBJECT-TYPE
    SYNTAX SnmpAdminString
    ACCESS read-only
    STATUS mandatory
    DESCRIPTION
        "The vCenter-specific UUID where this Snapshot resides."
    ::= { vmvcAimStatSnapshotEntry 13 }


-- *****************************************************************************
-- vmvcAimEventGroup 
-- *****************************************************************************
vmvcAimEventCount OBJECT-TYPE
    SYNTAX INTEGER
    ACCESS read-only
    STATUS mandatory
    DESCRIPTION
        "Number of events in event table."
    ::= {vmvcAimEventGroup 1}

vmvcAimEventCountMax OBJECT-TYPE
    SYNTAX INTEGER
    ACCESS read-write
    STATUS mandatory
    DESCRIPTION
        "The maximum number of events to be stored in the event table, after which the rows start getting overwritten."
    DEFVAL { 500 }
    ::= {vmvcAimEventGroup 2}

vmvcAimEventHistory OBJECT-TYPE
    SYNTAX INTEGER
    ACCESS read-write
    STATUS mandatory
    DESCRIPTION
        "The number of days the events are maintained. The value is in the number of days."
    DEFVAL {30}
    ::= {vmvcAimEventGroup 3}

vmvcAimEventClear OBJECT-TYPE
    SYNTAX INTEGER {
            do-not-clear(1),
                   clear(2)
            }
    ACCESS read-write
    STATUS mandatory
    DESCRIPTION
        "Flag indicating whether to clear all the events in the aimstatuseventtable or not. 1)DO_NOT_CLEAR 2)CLEAR."
    DEFVAL { 1 }    
    ::= {vmvcAimEventGroup 4}

vmvcAimEventTable OBJECT-TYPE
    SYNTAX SEQUENCE OF VmvcAimEventRow
    ACCESS not-accessible
    STATUS mandatory
    DESCRIPTION
        "A Event table."
    ::= {vmvcAimEventGroup 5}

vmvcAimEventEntry OBJECT-TYPE
    SYNTAX VmvcAimEventRow
    ACCESS not-accessible
    STATUS mandatory
    DESCRIPTION
        "The table entry."
    INDEX { vmvcAimEventUID }
    ::= { vmvcAimEventTable 1 }

VmvcAimEventRow ::=
    SEQUENCE {
        vmvcAimEventUID             INTEGER,
        vmvcAimEventID              SnmpAdminString,
        vmvcAimEventplatformType    SnmpAdminString,
        vmvcAimEventplatformName    SnmpAdminString,
        vmvcAimEventObjType         SnmpAdminString,
        vmvcAimEventObjName         SnmpAdminString,
        vmvcAimEventOldState        INTEGER,
        vmvcAimEventNewState        INTEGER,
        vmvcAimEventOldValue        SnmpAdminString,
        vmvcAimEventNewValue        SnmpAdminString,
        vmvcAimEventDateTime        SnmpAdminString,
        vmvcAimEventDateTimeSec     INTEGER,
        vmvcAimEventCfgFile         SnmpAdminString,
        vmvcAimEventVCUID           INTEGER,
        vmvcAimEventVCName          SnmpAdminString
    }

vmvcAimEventUID OBJECT-TYPE
    SYNTAX INTEGER (1..2147483647)
    ACCESS read-only
    STATUS mandatory
    DESCRIPTION
        " Event UID."
    ::= { vmvcAimEventEntry 1 }

vmvcAimEventID OBJECT-TYPE
    SYNTAX SnmpAdminString
    ACCESS read-only
    STATUS mandatory
    DESCRIPTION
        "The Event ID."
    ::= { vmvcAimEventEntry 2 }

vmvcAimEventplatformType OBJECT-TYPE
    SYNTAX SnmpAdminString
    ACCESS read-only
    STATUS mandatory
    DESCRIPTION
        "The Platform Type."
    ::= { vmvcAimEventEntry 3 }

vmvcAimEventplatformName OBJECT-TYPE
    SYNTAX SnmpAdminString
    ACCESS read-only
    STATUS mandatory
    DESCRIPTION
        "The Platform Name."
    ::= { vmvcAimEventEntry 4 }

vmvcAimEventObjType OBJECT-TYPE
    SYNTAX SnmpAdminString
    ACCESS read-only
    STATUS mandatory
    DESCRIPTION
        "The Object Type."
    ::= { vmvcAimEventEntry 5 }

vmvcAimEventObjName OBJECT-TYPE
    SYNTAX SnmpAdminString
    ACCESS read-only
    STATUS mandatory
    DESCRIPTION
        "The Object Name."
    ::= { vmvcAimEventEntry 6 }

vmvcAimEventOldState OBJECT-TYPE
    SYNTAX INTEGER {
        unknown(1),
        ok(2),
        warning(3),
        critical(4)
    }    
    ACCESS read-only
    STATUS mandatory
    DESCRIPTION
        "The Old State."
    ::= { vmvcAimEventEntry 7 }

vmvcAimEventNewState OBJECT-TYPE
    SYNTAX INTEGER {
        unknown(1),
        ok(2),
        warning(3),
        critical(4)
    }
    ACCESS read-only
    STATUS mandatory
    DESCRIPTION
        "The New state."
    ::= { vmvcAimEventEntry 8 }

vmvcAimEventOldValue OBJECT-TYPE
    SYNTAX SnmpAdminString
    ACCESS read-only
    STATUS mandatory
    DESCRIPTION
        "The Old Value."
    ::= { vmvcAimEventEntry 9 }

vmvcAimEventNewValue OBJECT-TYPE
    SYNTAX SnmpAdminString
    ACCESS read-only
    STATUS mandatory
    DESCRIPTION
        "The New Value."
    ::= { vmvcAimEventEntry 10 }

vmvcAimEventDateTime OBJECT-TYPE
    SYNTAX SnmpAdminString
    ACCESS read-only
    STATUS mandatory
    DESCRIPTION
        "Date and Time.  This attribute is now DEPRECATED and will return empty data, 
         as it does not support I18N conventions."
    ::= { vmvcAimEventEntry 11 }

vmvcAimEventDateTimeSec     OBJECT-TYPE
    SYNTAX INTEGER
    ACCESS read-only
    STATUS mandatory
    DESCRIPTION
        "The time the event occured in seconds."
    ::= { vmvcAimEventEntry 12 }

vmvcAimEventCfgFile OBJECT-TYPE
    SYNTAX SnmpAdminString
    ACCESS read-only
    STATUS mandatory
    DESCRIPTION
        "The name of the configuration file."
    ::= { vmvcAimEventEntry 13 }

vmvcAimEventVCUID OBJECT-TYPE
    SYNTAX INTEGER
    ACCESS read-only
    STATUS mandatory
    DESCRIPTION
        "VC Instance UID where this event occurred."
    ::= { vmvcAimEventEntry 14 }

vmvcAimEventVCName OBJECT-TYPE
    SYNTAX SnmpAdminString
    ACCESS read-only
    STATUS mandatory
    DESCRIPTION
        "VC Instance where this event occurred."
    ::= { vmvcAimEventEntry 15 }


-- *****************************************************************************
-- vmvcAimVCEventGroup 
-- *****************************************************************************
vmvcAimVCEventCount OBJECT-TYPE
    SYNTAX INTEGER
    ACCESS read-only
    STATUS mandatory
    DESCRIPTION
        "Number of events in VC event table."
    ::= {vmvcAimVCEventGroup 1}

vmvcAimVCEventCountMax OBJECT-TYPE
    SYNTAX INTEGER
    ACCESS read-write
    STATUS mandatory
    DESCRIPTION
        "The maximum number of events to be stored in the VC event table, after which the rows are removed."
    DEFVAL { 500 }
    ::= {vmvcAimVCEventGroup 2}

vmvcAimVCEventHistory OBJECT-TYPE
    SYNTAX INTEGER
    ACCESS read-write
    STATUS mandatory
    DESCRIPTION
        "The number of days the events are maintained. The value is in the number of days."
    DEFVAL {30}
    ::= {vmvcAimVCEventGroup 3}

vmvcAimVCEventClear OBJECT-TYPE
    SYNTAX INTEGER {
            do-not-clear(1),
                   clear(2)
            }
    ACCESS read-write
    STATUS mandatory
    DESCRIPTION
        "Flag indicating whether to clear all the events in the VC Event table or not. 1)DO_NOT_CLEAR 2)CLEAR."
    DEFVAL { 1 }    
    ::= {vmvcAimVCEventGroup 4}

vmvcAimVCEventTable OBJECT-TYPE
    SYNTAX SEQUENCE OF VmvcAimVCEventRow
    ACCESS not-accessible
    STATUS mandatory
    DESCRIPTION
        "The VC Event table."
    ::= {vmvcAimVCEventGroup 5}

vmvcAimVCEventEntry OBJECT-TYPE
    SYNTAX VmvcAimVCEventRow
    ACCESS not-accessible
    STATUS mandatory
    DESCRIPTION
        "The table entry."
    INDEX { vmvcAimVCEventUID }
    ::= { vmvcAimVCEventTable 1 }

VmvcAimVCEventRow ::=
    SEQUENCE {
        vmvcAimVCEventUID       INTEGER,
        vmvcAimVCEventType      SnmpAdminString,
        vmvcAimVCEventDesc      SnmpAdminString,
        vmvcAimVCEventDateTime  INTEGER,
        vmvcAimVCEventTask      SnmpAdminString,
        vmvcAimVCEventTarget    SnmpAdminString,
        vmvcAimVCEventUser      SnmpAdminString,
        vmvcAimVCEventVCUID     INTEGER,
        vmvcAimVCEventVCName    SnmpAdminString
    }

vmvcAimVCEventUID OBJECT-TYPE
    SYNTAX INTEGER (1..2147483647)
    ACCESS read-only
    STATUS mandatory
    DESCRIPTION
        "The Event UID."
    ::= { vmvcAimVCEventEntry 1 }

vmvcAimVCEventType OBJECT-TYPE
    SYNTAX SnmpAdminString
    ACCESS read-only
    STATUS mandatory
    DESCRIPTION
        "The Event Type."
    ::= { vmvcAimVCEventEntry 2 }

vmvcAimVCEventDesc OBJECT-TYPE
    SYNTAX SnmpAdminString
    ACCESS read-only
    STATUS mandatory
    DESCRIPTION
        "The Event Description."
    ::= { vmvcAimVCEventEntry 3 }

vmvcAimVCEventDateTime OBJECT-TYPE
    SYNTAX INTEGER
    ACCESS read-only
    STATUS mandatory
    DESCRIPTION
        "The Event Timestamp (in sec after epoch)."
    ::= { vmvcAimVCEventEntry 4 }

vmvcAimVCEventTask OBJECT-TYPE
    SYNTAX SnmpAdminString
    ACCESS read-only
    STATUS mandatory
    DESCRIPTION
        "The Event Task."
    ::= { vmvcAimVCEventEntry 5 }

vmvcAimVCEventTarget OBJECT-TYPE
    SYNTAX SnmpAdminString
    ACCESS read-only
    STATUS mandatory
    DESCRIPTION
        "The Event target."
    ::= { vmvcAimVCEventEntry 6 }

vmvcAimVCEventUser OBJECT-TYPE
    SYNTAX SnmpAdminString
    ACCESS read-only
    STATUS mandatory
    DESCRIPTION
        "The Event User."
    ::= { vmvcAimVCEventEntry 7 }

vmvcAimVCEventVCUID OBJECT-TYPE
    SYNTAX INTEGER
    ACCESS read-only
    STATUS mandatory
    DESCRIPTION
        "VC Instance UID where this VC event occurred."
    ::= { vmvcAimVCEventEntry 8 }

vmvcAimVCEventVCName OBJECT-TYPE
    SYNTAX SnmpAdminString
    ACCESS read-only
    STATUS mandatory
    DESCRIPTION
        "VC Instance where this VC event occurred."
    ::= { vmvcAimVCEventEntry 9 }


-- *****************************************************************************
--  Trap Definitions
-- *****************************************************************************

vmvcAimServerReadyEvent OBJECT IDENTIFIER ::= { traps 165200 }
vmvcAimServerReadyTrap TRAP-TYPE
    ENTERPRISE sysmgmt
    VARIABLES {
        vmvcAimStatServerName,
        vmvcAimStatServerState,
        vmvcAimStatVCName,
        vmvcAimStatVCState,
        vmvcAimStatVCUUID
    }
    DESCRIPTION
        "VC AIM has finished its initial poll and is now ready to publish and 
         receive information.  This trap is analogous to a warmStart trap for 
         this AIM.  This trap is ALWAYS enabled, but sent only in single-instance
         compatibility mode.  Superseded by vmvcAim2VCAddedTrap in multi-instance."
    ::= 165200

vmvcAimServerStateChangeEvent OBJECT IDENTIFIER ::= { traps 165201 }
vmvcAimServerStateChangeTrap TRAP-TYPE
    ENTERPRISE sysmgmt
    VARIABLES {
        vmvcAimStatServerName,
        vmvcAimStatServerState,
        vmvcAimStatVCName,
        vmvcAimStatVCState,
        vmvcAimConfigVCRowStatus,
        vmvcAimConfigVCDataStatus,
        vmvcAimStatVCUUID
    }
    DESCRIPTION
        "VC Server State has changed.
         vmvcAimStatServerState is supplied for single-instance compatibility mode.
         Enabled with Trap Enable Flag 0x2."
    ::= 165201

vmvcAimVCConfigChangeEvent OBJECT IDENTIFIER ::= { traps 165202 }
vmvcAimVCConfigChangeTrap TRAP-TYPE
    ENTERPRISE sysmgmt
    VARIABLES {
        vmvcAimStatServerName,
        vmvcAimStatServerStatusAlert,
        vmvcAimStatServerStatusMonitor,
        vmvcAimStatServerCPUAlert,
        vmvcAimStatServerCPUMonitor,
        vmvcAimStatServerCPULagSetting,
        vmvcAimStatServerMemAlert,
        vmvcAimStatServerMemoryMonitor,
        vmvcAimStatVCName,
        vmvcAimStatVCStatusAlert,
        vmvcAimStatVCStatusMonitor,
        vmvcAimStatVCLocalCPUUsageAlert,
        vmvcAimStatVCLocalCPUMonitor,
        vmvcAimStatVCLocalCPULagSetting,
        vmvcAimStatVCLocalMemAlert,
        vmvcAimStatVCLocalMemoryMonitor,
        vmvcAimConfigVCHostName,
        vmvcAimConfigVCProtocol,
        vmvcAimConfigVCPort,
        vmvcAimConfigVCPollInterval,
        vmvcAimConfigVCRefreshInterval,
        vmvcAimConfigVCEventPollInterval,
        vmvcAimConfigVCEventEnable,
        vmvcAimConfigVCEventMonitorInfo,
        vmvcAimConfigVCEventMonitorUser,
        vmvcAimConfigVCEventMonitorWarning,
        vmvcAimConfigVCEventMonitorError,
        vmvcAimConfigVCRowStatus,
        vmvcAimStatVCUUID
    }
    DESCRIPTION
        "VC Server Monitoring Configuration or Execution Configuration has changed.
         Enabled with Trap Enable Flag 0x4."
    ::= 165202

vmvcAimVCCPUStateChangeEvent OBJECT IDENTIFIER ::= { traps 165203 }
vmvcAimVCCPUStateChangeTrap TRAP-TYPE
    ENTERPRISE sysmgmt
    VARIABLES {
        vmvcAimStatServerName,
        vmvcAimStatServerCPUState,
        vmvcAimStatServerCPUUsage,
        vmvcAimStatServerAlertCPUUsageWarnThresh,
        vmvcAimStatServerAlertCPUUsageCritThresh,
        vmvcAimStatVCName,
        vmvcAimStatVCLocalCPUState,
        vmvcAimStatVCLocalCPUUsage,
        vmvcAimStatVCLocalCPUUsageWarn,
        vmvcAimStatVCLocalCPUUsageCrit,
        vmvcAimStatVCUUID
    }
    DESCRIPTION
        "CPU State of VC has changed.  Only applies to Local VC.
         Enabled with Trap Enable Flag 0x2."
    ::= 165203

vmvcAimVCThresholdChangeEvent OBJECT IDENTIFIER ::= { traps 165204 }
vmvcAimVCThresholdChangeTrap TRAP-TYPE
    ENTERPRISE sysmgmt
    VARIABLES {
        vmvcAimStatServerName,
        vmvcAimStatServerAlertCPUUsageWarnThresh,
        vmvcAimStatServerAlertCPUUsageCritThresh,
        vmvcAimStatServerMemWarnThres,
        vmvcAimStatServerMemCritThres,
        vmvcAimStatServerTotalCPUUsageWarnThresh,
        vmvcAimStatServerTotalCPUUsageCritThresh,
        vmvcAimStatServerTotalMemWarnThres,
        vmvcAimStatServerTotalMemCritThres,
        vmvcAimStatServerTotalDatastoreFreeSpaceWarnThresh,
        vmvcAimStatServerTotalDatastoreFreeSpaceCritThresh,
        vmvcAimStatVCName,
        vmvcAimStatVCLocalCPUUsageWarn,
        vmvcAimStatVCLocalCPUUsageCrit,
        vmvcAimStatVCLocalMemWarn,
        vmvcAimStatVCLocalMemCrit,
        vmvcAimStatVCTotalCPUUsageWarn,
        vmvcAimStatVCTotalCPUUsageCrit,
        vmvcAimStatVCTotalMemWarn,
        vmvcAimStatVCTotalMemCrit,
        vmvcAimStatVCTotalDatastoreFreeSpaceWarn,
        vmvcAimStatVCTotalDatastoreFreeSpaceCrit,
        vmvcAimStatVCUUID
    }
    DESCRIPTION
        "One or more monitoring thresholds have been modified for VC.
         Enabled with Trap Enable Flag 0x4."
    ::= 165204

vmvcAimVCEventReceivedEvent OBJECT IDENTIFIER ::= { traps 165205 }
vmvcAimVCEventReceivedTrap TRAP-TYPE
    ENTERPRISE sysmgmt
    VARIABLES {
        vmvcAimStatServerName,
        vmvcAimVCEventUID,
        vmvcAimVCEventType,
        vmvcAimVCEventDesc,
        vmvcAimVCEventDateTime,
        vmvcAimVCEventTask,
        vmvcAimVCEventTarget,
        vmvcAimVCEventUser,
        vmvcAimStatVCName,
        vmvcAimStatVCUUID
    }
    DESCRIPTION
        "VC Event has been received. Trap varbinds supply information.
         Enabled/disabled by vmvcAimConfigGeneralVCEventEnable."
    ::= 165205

vmvcAimVCMemStateChangeEvent OBJECT IDENTIFIER ::= { traps 165206 }
vmvcAimVCMemStateChangeTrap TRAP-TYPE
    ENTERPRISE sysmgmt
    VARIABLES {
        vmvcAimStatServerName,
        vmvcAimStatServerMemState,
        vmvcAimStatServerMemUsage,
        vmvcAimStatServerMemWarnThres,
        vmvcAimStatServerMemCritThres,
        vmvcAimStatVCName,
        vmvcAimStatVCLocalMemState,
        vmvcAimStatVCLocalMemUsage,
        vmvcAimStatVCLocalMemWarn,
        vmvcAimStatVCLocalMemCrit,
        vmvcAimStatVCUUID
    }
    DESCRIPTION
        "Memory State of VC has changed.  Only applies to Local VC.
         Enabled with Trap Enable Flag 0x2."
    ::= 165206

vmvcAimHostCpuStateChangeEvent OBJECT IDENTIFIER ::= { traps 165208 }
vmvcAimHostCpuStateChangeTrap TRAP-TYPE
    ENTERPRISE sysmgmt
    VARIABLES {
        vmvcAimStatServerName,
        vmvcAimStatHostDCName,
        vmvcAimStatHostClusterName,
        vmvcAimStatHostName,
        vmvcAimStatHostCPUState,
        vmvcAimStatHostCPUUsage,
        vmvcAimStatHostAlertCPUUsageWarnThresh,
        vmvcAimStatHostAlertCPUUsageCritThresh,
        vmvcAimStatHostDCIndex,
        vmvcAimStatHostClusterId,
        vmvcAimStatHostID,
        vmvcAimStatVCName,
        vmvcAimStatHostVCName,
        vmvcAimStatHostVCUUID
    }
    DESCRIPTION
        "The state of a monitored host has changed.  This is 
         specific to the CPU Usage for the given host.
         Enabled with Trap Enable Flag 0x2."
    ::= 165208

vmvcAimHostTotalCpuStateChangeEvent OBJECT IDENTIFIER ::= { traps 165209 }
vmvcAimHostTotalCpuStateChangeTrap TRAP-TYPE
    ENTERPRISE sysmgmt
    VARIABLES {
        vmvcAimStatServerName,
        vmvcAimStatHostDCName,
        vmvcAimStatHostClusterName,
        vmvcAimStatHostName,
        vmvcAimStatHostTotalCPUState,
        vmvcAimStatHostTotalCPU,
        vmvcAimStatHostTotalCPUWarnThreshold,
        vmvcAimStatHostTotalCPUCritThreshold,
        vmvcAimStatHostDCIndex,
        vmvcAimStatHostClusterId,
        vmvcAimStatHostID,
        vmvcAimStatVCName,
        vmvcAimStatHostVCName,
        vmvcAimStatHostVCUUID
    }
    DESCRIPTION
        "The state of a monitored host has changed.  This is 
         specific to the Total CPU Usage for the given host.
         Enabled with Trap Enable Flag 0x2."
    ::= 165209

vmvcAimHostTotalMemStateChangeEvent OBJECT IDENTIFIER ::= { traps 165210 }
vmvcAimHostTotalMemStateChangeTrap TRAP-TYPE
    ENTERPRISE sysmgmt
    VARIABLES {
        vmvcAimStatServerName,
        vmvcAimStatHostDCName,
        vmvcAimStatHostClusterName,
        vmvcAimStatHostName,
        vmvcAimStatHostMemoryTotalState,
        vmvcAimStatHostMemoryTotal,
        vmvcAimStatHostMemoryTotalWarnThreshold,
        vmvcAimStatHostMemoryTotalCritThreshold,
        vmvcAimStatHostDCIndex,
        vmvcAimStatHostClusterId,
        vmvcAimStatHostID,
        vmvcAimStatVCName,
        vmvcAimStatHostVCName,
        vmvcAimStatHostVCUUID
    }
    DESCRIPTION
        "The state of a monitored host has changed.  This is 
         specific to the Total Memory Usage for the given host.
         Enabled with Trap Enable Flag 0x2."
    ::= 165210

vmvcAimHostMemStateChangeEvent OBJECT IDENTIFIER ::= { traps 165211 }
vmvcAimHostMemStateChangeTrap TRAP-TYPE
    ENTERPRISE sysmgmt
    VARIABLES {
        vmvcAimStatServerName,
        vmvcAimStatHostDCName,
        vmvcAimStatHostClusterName,
        vmvcAimStatHostName,
        vmvcAimStatHostMemoryState,
        vmvcAimStatHostMemoryUsage,
        vmvcAimStatHostAlertMemoryUsageWarnThreshold,
        vmvcAimStatHostAlertMemoryUsageCritThreshold,
        vmvcAimStatHostDCIndex,
        vmvcAimStatHostClusterId,
        vmvcAimStatHostID,
        vmvcAimStatVCName,
        vmvcAimStatHostVCName,
        vmvcAimStatHostVCUUID
    }
    DESCRIPTION
        "The state of a monitored host has changed.  This is 
         specific to the Memory Usage for the given host.
         Enabled with Trap Enable Flag 0x2."
    ::= 165211

vmvcAimHostConfigChangeEvent OBJECT IDENTIFIER ::= { traps 165212 }
vmvcAimHostConfigChangeTrap TRAP-TYPE
    ENTERPRISE sysmgmt
    VARIABLES {
        vmvcAimStatServerName,
        vmvcAimStatHostDCName,
        vmvcAimStatHostClusterName,
        vmvcAimStatHostName,
        vmvcAimStatHostMonitor,
        vmvcAimStatHostCPUAlert,
        vmvcAimStatHostCPUMonitor,
        vmvcAimStatHostCPULagSetting,
        vmvcAimStatHostMemoryAlert,
        vmvcAimStatHostMemoryMonitor,
        vmvcAimStatHostDCIndex,
        vmvcAimStatHostClusterId,
        vmvcAimStatHostID,
        vmvcAimStatHostComputeResourceFolderId,
        vmvcAimStatVCName,
        vmvcAimStatHostVCName,
        vmvcAimStatHostVCUUID
    }
    DESCRIPTION
        "The monitoring configuration of a host has been changed.
         This is very specific to the CPU and Memory monitors for
         the given host.
         Enabled with Trap Enable Flag 0x4."
    ::= 165212

vmvcAimHostTotalVMCpuStateChangeEvent OBJECT IDENTIFIER ::= { traps 165213 }
vmvcAimHostTotalVMCpuStateChangeTrap TRAP-TYPE
    ENTERPRISE sysmgmt
    VARIABLES {
        vmvcAimStatServerName,
        vmvcAimStatHostDCName,
        vmvcAimStatHostClusterName,
        vmvcAimStatHostName,
        vmvcAimStatHostTotalVMCPUState,
        vmvcAimStatHostTotalVMCPU,
        vmvcAimStatHostTotalVMCPUWarnThreshold,
        vmvcAimStatHostTotalVMCPUCritThreshold,
        vmvcAimStatHostDCIndex,
        vmvcAimStatHostClusterId,
        vmvcAimStatHostID,
        vmvcAimStatVCName,
        vmvcAimStatHostVCName,
        vmvcAimStatHostVCUUID
    }
    DESCRIPTION
        "The state of a monitored host has changed.  This is 
         specific to the Total VM CPU, Usage of the ESX Server console 
         with respect to total machine CPU.
         Enabled with Trap Enable Flag 0x2."
    ::= 165213

vmvcAimHostMemOtherStateChangeEvent OBJECT IDENTIFIER ::= { traps 165214 }
vmvcAimHostMemOtherStateChangeTrap TRAP-TYPE
    ENTERPRISE sysmgmt
    VARIABLES {
        vmvcAimStatServerName,
        vmvcAimStatHostDCName,
        vmvcAimStatHostClusterName,
        vmvcAimStatHostName,
        vmvcAimStatHostMemoryOtherState,
        vmvcAimStatHostMemoryOther,
        vmvcAimStatHostMemoryOtherWarnThreshold,
        vmvcAimStatHostMemoryOtherCritThreshold,
        vmvcAimStatHostDCIndex,
        vmvcAimStatHostClusterId,
        vmvcAimStatHostID,
        vmvcAimStatVCName,
        vmvcAimStatHostVCName,
        vmvcAimStatHostVCUUID
    }
    DESCRIPTION
        "The state of a monitored host has changed.  This is 
         specific to the Memory Other Usage of all VMs 
         with respect to total machine memory.
         Enabled with Trap Enable Flag 0x2."
    ::= 165214

vmvcAimHostThresholdChangeEvent OBJECT IDENTIFIER ::= { traps 165215 }
vmvcAimHostThresholdChangeTrap TRAP-TYPE
    ENTERPRISE sysmgmt
    VARIABLES {
        vmvcAimStatServerName,
        vmvcAimStatHostDCName,
        vmvcAimStatHostClusterName,
        vmvcAimStatHostName,
        vmvcAimStatHostAlertCPUUsageWarnThresh,
        vmvcAimStatHostAlertCPUUsageCritThresh,
        vmvcAimStatHostAlertMemoryUsageWarnThreshold,
        vmvcAimStatHostAlertMemoryUsageCritThreshold,
        vmvcAimStatHostTotalVMCPUWarnThreshold,
        vmvcAimStatHostTotalVMCPUCritThreshold,
        vmvcAimStatHostTotalCPUWarnThreshold,
        vmvcAimStatHostTotalCPUCritThreshold,
        vmvcAimStatHostTotalVMMemoryWarnThreshold,
        vmvcAimStatHostTotalVMMemoryCritThreshold,
        vmvcAimStatHostMemoryOtherWarnThreshold,
        vmvcAimStatHostMemoryOtherCritThreshold,
        vmvcAimStatHostMemoryTotalWarnThreshold,
        vmvcAimStatHostMemoryTotalCritThreshold,
        vmvcAimStatHostDCIndex,
        vmvcAimStatHostClusterId,
        vmvcAimStatHostID,
        vmvcAimStatVCName,
        vmvcAimStatHostVCName,
        vmvcAimStatHostVCUUID
    }
    DESCRIPTION
        "One or more monitoring thresholds have been modified for the
         given host.
         Enabled with Trap Enable Flag 0x4."
    ::= 165215

vmvcAimHostAddedEvent OBJECT IDENTIFIER ::= { traps 165216 }
vmvcAimHostAddedTrap TRAP-TYPE
    ENTERPRISE sysmgmt
    VARIABLES {
        vmvcAimStatServerName,
        vmvcAimStatHostDCName,
        vmvcAimStatHostClusterName,
        vmvcAimStatHostName,
        vmvcAimStatHostComputeResourceFolderName,
        vmvcAimStatHostOSType,
        vmvcAimStatHostProd,
        vmvcAimStatHostProdBuildVer,
        vmvcAimStatHostProdVer,
        vmvcAimStatHostProdAPIType,
        vmvcAimStatHostProdAPIVer,
        vmvcAimStatHostMonitor,
        vmvcAimStatHostCPUAlert,
        vmvcAimStatHostCPUMonitor,
        vmvcAimStatHostMemoryAlert,
        vmvcAimStatHostMemoryMonitor,
        vmvcAimStatHostCPUState,
        vmvcAimStatHostMemoryState,
        vmvcAimStatHostDCIndex,
        vmvcAimStatHostClusterId,
        vmvcAimStatHostID,
        vmvcAimStatHostComputeResourceFolderId,
        vmvcAimStatHostMaxSupportedVCPUs,
        vmvcAimStatVCName,
        vmvcAimStatHostFaultToleranceConf,
        vmvcAimStatHostFaultToleranceVersion,
        vmvcAimStatHostTotalFTPrimaryVM,
        vmvcAimStatHostPoweredOnFTPrimaryVM,
        vmvcAimStatHostTotalFTSecondaryVM,
        vmvcAimStatHostPoweredOnFTSecondaryVM,
        vmvcAimStatHostVCName,
        vmvcAimStatHostVCUUID
    }
    DESCRIPTION
        "A Host was added to the VC configuration.  Information on this
         host is specified within the varbind list.
         Enabled with Trap Enable Flag 0x1."
    ::= 165216

vmvcAimHostRemovedEvent OBJECT IDENTIFIER ::= { traps 165217 }
vmvcAimHostRemovedTrap TRAP-TYPE
    ENTERPRISE sysmgmt
    VARIABLES {
        vmvcAimStatServerName,
        vmvcAimStatHostDCName,
        vmvcAimStatHostClusterName,
        vmvcAimStatHostName,
        vmvcAimStatHostDCIndex,
        vmvcAimStatHostClusterId,
        vmvcAimStatHostID,
        vmvcAimStatHostComputeResourceFolderId,
        vmvcAimStatVCName,
        vmvcAimStatHostVCName,
        vmvcAimStatHostVCUUID
    }
    DESCRIPTION
        "A Host was removed from the VC configuration.  The Host Name
         removed is specified within the varbind list.
         Enabled with Trap Enable Flag 0x1."
    ::= 165217

vmvcAimHostVMotionEvent OBJECT IDENTIFIER ::= { traps 165218 }
vmvcAimHostVMotionTrap TRAP-TYPE
    ENTERPRISE sysmgmt
    VARIABLES {
        vmvcAimStatServerName,
        vmvcAimStatHostDCName,
        vmvcAimStatHostClusterName,
        vmvcAimStatHostName,
        vmvcAimStatHostVMotionEnabled,
        vmvcAimStatHostDCIndex,
        vmvcAimStatHostClusterId,
        vmvcAimStatHostID,
        vmvcAimStatVCName,
        vmvcAimStatHostVCName,
        vmvcAimStatHostVCUUID
    }
    DESCRIPTION
        "VMotion configuration has changed for the specified host.  The
         value of the flag is specified within the varbind list.
         Enabled with Trap Enable Flag 0x1."
    ::= 165218

vmvcAimHostConnectionStateEvent OBJECT IDENTIFIER ::= { traps 165219 }
vmvcAimHostConnectionStateTrap TRAP-TYPE
    ENTERPRISE sysmgmt
    VARIABLES {
        vmvcAimStatServerName,
        vmvcAimStatHostDCName,
        vmvcAimStatHostClusterName,
        vmvcAimStatHostName,
        vmvcAimStatHostConnectionState,
        vmvcAimStatHostDCIndex,
        vmvcAimStatHostClusterId,
        vmvcAimStatHostID,
        vmvcAimStatVCName,
        vmvcAimStatHostVCName,
        vmvcAimStatHostVCUUID
    }
    DESCRIPTION
        "The Connection Status of the specified host has changed.  The
         new connection value is specified within the varbind list.
         Enabled with Trap Enable Flag 0x1."
    ::= 165219

vmvcAimHostTotalVMMemStateChangeEvent OBJECT IDENTIFIER ::= { traps 165220 }
vmvcAimHostTotalVMMemStateChangeTrap TRAP-TYPE
    ENTERPRISE sysmgmt
    VARIABLES {
        vmvcAimStatServerName,
        vmvcAimStatHostDCName,
        vmvcAimStatHostClusterName,
        vmvcAimStatHostName,
        vmvcAimStatHostTotalVMMemoryState,
        vmvcAimStatHostTotalVMMemory,
        vmvcAimStatHostTotalVMMemoryWarnThreshold,
        vmvcAimStatHostTotalVMMemoryCritThreshold,
        vmvcAimStatHostDCIndex,
        vmvcAimStatHostClusterId,
        vmvcAimStatHostID,
        vmvcAimStatVCName,
        vmvcAimStatHostVCName,
        vmvcAimStatHostVCUUID
    }
    DESCRIPTION
        "The state of a monitored host has changed.  This is 
         specific to the Total VM Memory, Usage of the ESX Server console 
         with respect to total machine Memory.
         Enabled with Trap Enable Flag 0x2."
    ::= 165220

vmvcAimVMCpuStateChangeEvent OBJECT IDENTIFIER ::= { traps 165221 }
vmvcAimVMCpuStateChangeTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMCPUState,
        vmvcAimStatVMCPUSharesPercentage,
        vmvcAimStatVMCPUSharesWarnThreshold,
        vmvcAimStatVMCPUSharesCritThreshold,
        vmvcAimStatVMHostID,
        vmvcAimStatVMResourcePoolId,
        vmvcAimStatVMIndex,
        vmvcAimStatVCName,
        vmvcAimStatVMVCName,
        vmvcAimStatVMVCUUID
    }
    DESCRIPTION
        "The state of the specified monitored VM has changed.  The new
         state, as well as the thresholds and the actual value, are
         supplied.
         Enabled with Trap Enable Flag 0x2."
    ::= 165221

vmvcAimVMAddedEvent OBJECT IDENTIFIER ::= { traps 165222 }
vmvcAimVMAddedTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMIPv4Address,
        vmvcAimStatVMIPv6Address,
        vmvcAimStatVMId,
        vmvcAimStatVMPowerStatus,
        vmvcAimStatVMHeartbeat,
        vmvcAimStatVMCPUAggregateStatus,
        vmvcAimStatVMMemoryState,
        vmvcAimStatVMHeartbeatState,
        vmvcAimStatVMPowerState,
        vmvcAimStatVMMonitor,
        vmvcAimStatVMCPUMonitor,
        vmvcAimStatVMMemoryMonitor,
        vmvcAimStatVMCPUAlert,
        vmvcAimStatVMMemoryAlert,
        vmvcAimStatVMAlertPowerOffStatus,
        vmvcAimStatVMBehaviour,
        vmvcAimStatVMConnectionState,
        vmvcAimStatVMHostID,
        vmvcAimStatVMResourcePoolId,
        vmvcAimStatVMIndex,
        vmvcAimStatVMFullPath,
        vmvcAimStatVMPhyName,
        vmvcAimStatVMCPUHotPlug,
        vmvcAimStatVMMemoryHotAdd,
        vmvcAimStatVMMemoryHotAddIncrement,
        vmvcAimStatVMMemoryHotAddLimit,
        vmvcAimStatVCName,
        vmvcAimStatVMHostName,
        vmvcAimStatVMFaultToleranceStatus,
        vmvcAimStatVMFTActivityState,
        vmvcAimStatVMFaultToleranceRole,
        vmvcAimStatVMFTSiblingIndex,
        vmvcAimStatVMFTSiblingHostIndex,
        vmvcAimStatVMFTSiblingHostName,
        vmvcAimStatVMFTSiblingHostUID,
        vmvcAimStatVMFTTotalSiblingCPU,
        vmvcAimStatVMFTTotalSiblingMemory,
        vmvcAimStatVMVCName,
        vmvcAimStatVMVCUUID
    }
    DESCRIPTION
        "A new VM has been configured within VC.  The specifics of this
         VM are specified within the varbind list.
         Enabled with Trap Enable Flag 0x1."
    ::= 165222

vmvcAimVMRemovedEvent OBJECT IDENTIFIER ::= { traps 165223 }
vmvcAimVMRemovedTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMHostID,
        vmvcAimStatVMResourcePoolId,
        vmvcAimStatVMIndex,
        vmvcAimStatVCName,
        vmvcAimStatVMVCName,
        vmvcAimStatVMVCUUID
    }
    DESCRIPTION
        "The specified VM has been removed from VC.
         Enabled with Trap Enable Flag 0x1."
    ::= 165223

vmvcAimVMConfigChangeEvent OBJECT IDENTIFIER ::= { traps 165224 }
vmvcAimVMConfigChangeTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMCPUState,
        vmvcAimStatVMCPUAlert,
        vmvcAimStatVMCPUMonitor,
        vmvcAimStatVMCPULagSetting,
        vmvcAimStatVMMemoryState,
        vmvcAimStatVMMemoryAlert,
        vmvcAimStatVMMemoryMonitor,
        vmvcAimStatVMPowerState,
        vmvcAimStatVMAlertPowerOffStatus,
        vmvcAimStatVMHeartbeatState,
        vmvcAimStatVMAlertHeartbeatLoss,
        vmvcAimStatVMPctReadyState,
        vmvcAimStatVMPctReadyAlert,
        vmvcAimStatVMMonitor,
        vmvcAimStatVMHostID,
        vmvcAimStatVMResourcePoolId,
        vmvcAimStatVMIndex,
        vmvcAimStatVCName,
        vmvcAimStatVMVCName,
        vmvcAimStatVMVCUUID
    }
    DESCRIPTION
        "The monitoring configuration for the specified VM has been
         modified.  This does not include changes to monitoring 
         thresholds.
         Enabled with Trap Enable Flag 0x4."
    ::= 165224

vmvcAimVMThresholdChangeEvent OBJECT IDENTIFIER ::= { traps 165225 }
vmvcAimVMThresholdChangeTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMCPUSharesWarnThreshold,
        vmvcAimStatVMCPUSharesCritThreshold,
        vmvcAimStatVMMemoryWarnThreshold,
        vmvcAimStatVMMemoryCritThreshold,
        vmvcAimStatVMPctReadyWarnThreshold,
        vmvcAimStatVMPctReadyCritThreshold,
        vmvcAimStatVMHostID,
        vmvcAimStatVMResourcePoolId,
        vmvcAimStatVMIndex,
        vmvcAimStatVCName,
        vmvcAimStatVMVCName,
        vmvcAimStatVMVCUUID
    }
    DESCRIPTION
        "The monitoring threshold configuration for the specified VM 
         has been modified.
         Enabled with Trap Enable Flag 0x4."
    ::= 165225

vmvcAimVMPercentReadyEvent OBJECT IDENTIFIER ::= { traps 165226 }
vmvcAimVMPercentReadyTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMPctReadyState,
        vmvcAimStatVMPctReady,
        vmvcAimStatVMPctReadyWarnThreshold,
        vmvcAimStatVMPctReadyCritThreshold,
        vmvcAimStatVMPctReadyAlert,
        vmvcAimStatVMHostID,
        vmvcAimStatVMResourcePoolId,
        vmvcAimStatVMIndex,
        vmvcAimStatVCName,
        vmvcAimStatVMVCName,
        vmvcAimStatVMVCUUID
    }
    DESCRIPTION
        "The state of the Percent Ready monitor for the specified VM 
         has changed.
         Enabled with Trap Enable Flag 0x2."
    ::= 165226

vmvcAimVMRenamedEvent OBJECT IDENTIFIER ::= { traps 165227 }
vmvcAimVMRenamedTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMHostID,
        vmvcAimStatVMResourcePoolId,
        vmvcAimStatVMIndex,
        vmvcAimStatVCName,
        vmvcAimStatVMVCName,
        vmvcAimStatVMVCUUID
    }
    DESCRIPTION
        "The designated VM Instance has been renamed.  The new name is 
         supplied in the varbind list.
         Enabled with Trap Enable Flag 0x1."
    ::= 165227

vmvcAimVMBehaviourChangeEvent OBJECT IDENTIFIER ::= { traps 165228 }
vmvcAimVMBehaviourChangeTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMBehaviour,
        vmvcAimStatVMHostID,
        vmvcAimStatVMResourcePoolId,
        vmvcAimStatVMIndex,
        vmvcAimStatVCName,
        vmvcAimStatVMVCName,
        vmvcAimStatVMVCUUID
    }
    DESCRIPTION
        "The DR VM Behaviour for the designated VM Instance has changed.
         The new value is specified within the varbind list.
         Enabled with Trap Enable Flag 0x1."
    ::= 165228

vmvcAimVMConnectionStateChangeEvent OBJECT IDENTIFIER ::= { traps 165229 }
vmvcAimVMConnectionStateChangeTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMConnectionState,
        vmvcAimStatVMHostID,
        vmvcAimStatVMResourcePoolId,
        vmvcAimStatVMIndex,
        vmvcAimStatVCName,
        vmvcAimStatVMVCName,
        vmvcAimStatVMVCUUID
    }
    DESCRIPTION
        "The Connection State of the designated VM instance has changed.
         The new connection value is specified within the varbind list.
         Enabled with Trap Enable Flag 0x1."
    ::= 165229

vmvcAimVMMigratedEvent OBJECT IDENTIFIER ::= { traps 165230 }
vmvcAimVMMigratedTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMIndex,
        vmvcAimStatVMPhyName,
        vmvcAimStatHostName,
        vmvcAimStatVMHostID,
        vmvcAimStatVMResourcePoolId,
        vmvcAimStatVMIndex,
        vmvcAimStatVCName,
        vmvcAimStatVMVCName,
        vmvcAimStatVMVCUUID
    }
    DESCRIPTION
        "The designated VM Instance has been migrated. The last attribute HostName is the previous Host Name.
         Enabled with Trap Enable Flag 0x1."
    ::= 165230

vmvcAimVMNICStateChangeEvent OBJECT IDENTIFIER ::= { traps 165231 }
vmvcAimVMNICStateChangeTrap TRAP-TYPE
    ENTERPRISE sysmgmt
    VARIABLES {
        vmvcAimStatServerName,
        vmvcAimStatHostDCName,
        vmvcAimStatHostClusterName,
        vmvcAimStatHostName,
        vmvcAimStatVMName,
        vmvcAimStatVMVNICMAC,
        vmvcAimStatVMVNICState,
        vmvcAimStatVMVNICAlert,
        vmvcAimStatVMVNICVMIndex,
        vmvcAimStatVMVNICName,
        vmvcAimStatVMVNICDeviceId,
        vmvcAimStatVCName,
        vmvcAimStatVMVNICHostName,
        vmvcAimStatVMVNICVMName,
        vmvcAimStatVMVNICVCName,
        vmvcAimStatVMVNICVCUUID
    }
    DESCRIPTION
        "The state of the VM network interface has changed.
         Enabled with Trap Enable Flag 0x2."
    ::= 165231

vmvcAimVMNICAddedEvent OBJECT IDENTIFIER ::= { traps 165232 }
vmvcAimVMNICAddedTrap TRAP-TYPE
    ENTERPRISE sysmgmt
    VARIABLES {
        vmvcAimStatServerName,
        vmvcAimStatHostDCName,
        vmvcAimStatHostClusterName,
        vmvcAimStatHostName,
        vmvcAimStatVMName,
        vmvcAimStatVMVNICMAC,
        vmvcAimStatVMVNICState,
        vmvcAimStatVMVNICKBPSRcvd,
        vmvcAimStatVMVNICKBPSTxt,
        vmvcAimStatVMVNICAlert,
        vmvcAimStatVMVNICConnected,
        vmvcAimStatVMVNICMonitor,
        vmvcAimStatVMVNICVMIndex,
        vmvcAimStatVMVNICName,
        vmvcAimStatVMVNICDeviceId,
        vmvcAimStatVCName,
        vmvcAimStatVMVNICDVPortGroupIndex,
        vmvcAimStatVMVNICDeviceSummary,
        vmvcAimStatVMVNICHostName,
        vmvcAimStatVMVNICVMName,
        vmvcAimStatVMVNICVCName,
        vmvcAimStatVMVNICVCUUID
    }
    DESCRIPTION
        "A new VMNIC has been detected.  Specifics for this VMNIC are
         specified within the varbind list.
         Enabled with Trap Enable Flag 0x1."
    ::= 165232

vmvcAimVMNICRemovedEvent OBJECT IDENTIFIER ::= { traps 165233 }
vmvcAimVMNICRemovedTrap TRAP-TYPE
    ENTERPRISE sysmgmt
    VARIABLES {
        vmvcAimStatServerName,
        vmvcAimStatHostDCName,
        vmvcAimStatHostClusterName,
        vmvcAimStatHostName,
        vmvcAimStatVMName,
        vmvcAimStatVMVNICMAC,
        vmvcAimStatVMVNICVMIndex,
        vmvcAimStatVMVNICName,
        vmvcAimStatVMVNICDeviceId,
        vmvcAimStatVCName,
        vmvcAimStatVMVNICHostName,
        vmvcAimStatVMVNICVMName,
        vmvcAimStatVMVNICVCName,
        vmvcAimStatVMVNICVCUUID
    }
    DESCRIPTION
        "The specified VMNIC has been removed.
         Enabled with Trap Enable Flag 0x1."
    ::= 165233

vmvcAimVMNICConfigChangeEvent OBJECT IDENTIFIER ::= { traps 165234 }
vmvcAimVMNICConfigChangeTrap TRAP-TYPE
    ENTERPRISE sysmgmt
    VARIABLES {
        vmvcAimStatServerName,
        vmvcAimStatHostDCName,
        vmvcAimStatHostClusterName,
        vmvcAimStatHostName,
        vmvcAimStatVMName,
        vmvcAimStatVMVNICMAC,
        vmvcAimStatVMVNICAlert,
        vmvcAimStatVMVNICMonitor,
        vmvcAimStatVMVNICState,
        vmvcAimStatVMVNICConnected,
        vmvcAimStatVMVNICVMIndex,
        vmvcAimStatVMVNICName,
        vmvcAimStatVMVNICDeviceId,
        vmvcAimStatVCName,
        vmvcAimStatVMVNICHostName,
        vmvcAimStatVMVNICVMName,
        vmvcAimStatVMVNICVCName,
        vmvcAimStatVMVNICVCUUID
    }
    DESCRIPTION
        "The monitoring configuration for the specified VM network 
         interface has been modified.
         Enabled with Trap Enable Flag 0x4."
    ::= 165234

vmvcAimVSwitchStateChangeEvent OBJECT IDENTIFIER ::= { traps 165235 }
vmvcAimVSwitchStateChangeTrap TRAP-TYPE
    ENTERPRISE sysmgmt
    VARIABLES {
        vmvcAimStatServerName,
        vmvcAimStatSwitchName,
        vmvcAimStatSwitchHost,
        vmvcAimStatSwitchState,
        vmvcAimStatSwitchIndex,
        vmvcAimStatVCName,
        vmvcAimStatSwitchVCName,
        vmvcAimStatSwitchVCUUID
    }
    DESCRIPTION
        "VSwitch State has been changed.
         Enabled with Trap Enable Flag 0x2."
    ::= 165235

vmvcAimVMVDiskStateChangeEvent OBJECT IDENTIFIER ::= { traps 165236 }
vmvcAimVMVDiskStateChangeTrap TRAP-TYPE
    ENTERPRISE sysmgmt
    VARIABLES {
        vmvcAimStatServerName,
        vmvcAimStatHostDCName,
        vmvcAimStatHostClusterName,
        vmvcAimStatHostName,
        vmvcAimStatVMName,
        vmvcAimStatVMVDiskLabel,
        vmvcAimStatVMVDiskState,
        vmvcAimStatVMDiskVMID,
        vmvcAimStatVMVDiskDeviceId,
        vmvcAimStatVMVDiskControllerKey,
        vmvcAimStatVMVDiskUnitNumber,
        vmvcAimStatVCName,
        vmvcAimStatVMVDiskHostName,
        vmvcAimStatVMDiskVMName,
        vmvcAimStatVMVDiskVCName,
        vmvcAimStatVMVDiskVCUUID
    }
    DESCRIPTION
        "The state of the monitored VM Virtual Disk has changed.
         Enabled with Trap Enable Flag 0x2."
    ::= 165236

vmvcAimVMVDiskAddedEvent OBJECT IDENTIFIER ::= { traps 165237 }
vmvcAimVMVDiskAddedTrap TRAP-TYPE
    ENTERPRISE sysmgmt
    VARIABLES {
        vmvcAimStatServerName,
        vmvcAimStatHostDCName,
        vmvcAimStatHostClusterName,
        vmvcAimStatHostName,
        vmvcAimStatVMName,
        vmvcAimStatVMVDiskLabel,
        vmvcAimStatVMVDiskState,
        vmvcAimStatVMVDiskRead,
        vmvcAimStatVMVDiskWrite,
        vmvcAimStatVMVDiskKBReadAlert,
        vmvcAimStatVMVDiskKBWriteAlert,
        vmvcAimStatVMVDiskKBReadState,
        vmvcAimStatVMVDiskKBWriteState,
        vmvcAimStatVMVDiskWriteThrough,
        vmvcAimStatVMVDiskSplit,
        vmvcAimStatVMVDiskMode,
        vmvcAimStatVMVDiskShares,
        vmvcAimStatVMVDiskCapacity,
        vmvcAimStatVMVDiskFileName,
        vmvcAimStatVMVDiskMonitor,
        vmvcAimStatVMDiskVMID,
        vmvcAimStatVMVDiskDeviceId,
        vmvcAimStatVMVDiskControllerKey,
        vmvcAimStatVMVDiskUnitNumber,
        vmvcAimStatVCName,
        vmvcAimStatVMVDiskHostName,
        vmvcAimStatVMDiskVMName,
        vmvcAimStatVMVDiskVCName,
        vmvcAimStatVMVDiskVCUUID
    }
    DESCRIPTION
        "The specified Virtual Disk has been detected and added.
         Enabled with Trap Enable Flag 0x1."
    ::= 165237

vmvcAimVMVDiskRemovedEvent OBJECT IDENTIFIER ::= { traps 165238 }
vmvcAimVMVDiskRemovedTrap TRAP-TYPE
    ENTERPRISE sysmgmt
    VARIABLES {
        vmvcAimStatServerName,
        vmvcAimStatHostDCName,
        vmvcAimStatHostClusterName,
        vmvcAimStatHostName,
        vmvcAimStatVMName,
        vmvcAimStatVMVDiskLabel,
        vmvcAimStatVMDiskVMID,
        vmvcAimStatVMVDiskDeviceId,
        vmvcAimStatVMVDiskControllerKey,
        vmvcAimStatVMVDiskUnitNumber,
        vmvcAimStatVCName,
        vmvcAimStatVMVDiskHostName,
        vmvcAimStatVMDiskVMName,
        vmvcAimStatVMVDiskVCName,
        vmvcAimStatVMVDiskVCUUID
    }
    DESCRIPTION
        "The specified Virtual Disk has been removed.
         Enabled with Trap Enable Flag 0x1."
    ::= 165238

vmvcAimVMVDiskConfigChangeEvent OBJECT IDENTIFIER ::= { traps 165239 }
vmvcAimVMVDiskConfigChangeTrap TRAP-TYPE
    ENTERPRISE sysmgmt
    VARIABLES {
        vmvcAimStatServerName,
        vmvcAimStatHostDCName,
        vmvcAimStatHostClusterName,
        vmvcAimStatHostName,
        vmvcAimStatVMName,
        vmvcAimStatVMVDiskLabel,
        vmvcAimStatVMVDiskMonitor,
        vmvcAimStatVMVDiskKBReadAlert,
        vmvcAimStatVMVDiskKBWriteAlert,
        vmvcAimStatVMVDiskState,
        vmvcAimStatVMDiskVMID,
        vmvcAimStatVMVDiskDeviceId,
        vmvcAimStatVMVDiskControllerKey,
        vmvcAimStatVMVDiskUnitNumber,
        vmvcAimStatVCName,
        vmvcAimStatVMVDiskHostName,
        vmvcAimStatVMDiskVMName,
        vmvcAimStatVMVDiskVCName,
        vmvcAimStatVMVDiskVCUUID
    }
    DESCRIPTION
        "The monitoring configuration for the specified VM virtual disk
         has been modified.
         Enabled with Trap Enable Flag 0x4."
    ::= 165239

vmvcAimDCOverallStateChangeEvent OBJECT IDENTIFIER ::= { traps 165240 }
vmvcAimDCOverallStateChangeTrap TRAP-TYPE
    ENTERPRISE sysmgmt
    VARIABLES {
        vmvcAimStatServerName,
        vmvcAimStatDatacenterName,
        vmvcAimStatDatacenterOverallState,
        vmvcAimStatDatacenterIndex,
        vmvcAimStatVCName,
        vmvcAimStatDatacenterVCName,
        vmvcAimStatDatacenterVCUUID
    }
    DESCRIPTION
        "DataCenter Overall State has been changed.
         Enabled with Trap Enable Flag 0x2."
    ::= 165240

vmvcAimPNICStateChangeEvent OBJECT IDENTIFIER ::= { traps 165241 }
vmvcAimPNICStateChangeTrap TRAP-TYPE
    ENTERPRISE sysmgmt
    VARIABLES {
        vmvcAimStatServerName,
        vmvcAimStatHostDCName,
        vmvcAimStatHostClusterName,
        vmvcAimStatHostName,
        vmvcAimStatPNICName,
        vmvcAimStatPNICState,
        vmvcAimStatPNICAlert,
        vmvcAimStatVCName,
        vmvcAimStatPNICVCName,
        vmvcAimStatPNICVCUUID
    }
    DESCRIPTION
        "The state of the monitored physical NIC has changed.
         Enabled with Trap Enable Flag 0x2."
    ::= 165241

vmvcAimPNICAddedEvent OBJECT IDENTIFIER ::= { traps 165242 }
vmvcAimPNICAddedTrap TRAP-TYPE
    ENTERPRISE sysmgmt
    VARIABLES {
        vmvcAimStatServerName,
        vmvcAimStatHostDCName,
        vmvcAimStatHostClusterName,
        vmvcAimStatHostName,
        vmvcAimStatPNICName,
        vmvcAimStatPNICAlert,
        vmvcAimStatPNICPCI,
        vmvcAimStatPNICVendor,
        vmvcAimStatPNICIPIsDHCP,
        vmvcAimStatPNICIP,
        vmvcAimStatPNICSubnetmask,
        vmvcAimStatPNICLinkSpeedDuplex,
        vmvcAimStatPNICVirtualSwitch,
        vmvcAimStatPNICLinkState,
        vmvcAimStatPNICMonitor,
        vmvcAimStatVCName,
        vmvcAimStatPNICDVUplinkPGIndex,
        vmvcAimStatPNICDVPortKey,
        vmvcAimStatPNICDVUplink,
        vmvcAimStatPNICMAC,
        vmvcAimStatPNICVCName,
        vmvcAimStatPNICVCUUID
    }
    DESCRIPTION
        "A new Physical NIC has been detected and added.
         Enabled with Trap Enable Flag 0x1."
    ::= 165242

vmvcAimPNICRemovedEvent OBJECT IDENTIFIER ::= { traps 165243 }
vmvcAimPNICRemovedTrap TRAP-TYPE
    ENTERPRISE sysmgmt
    VARIABLES {
        vmvcAimStatServerName,
        vmvcAimStatHostDCName,
        vmvcAimStatHostClusterName,
        vmvcAimStatHostName,
        vmvcAimStatPNICName,
        vmvcAimStatVCName,
        vmvcAimStatPNICVCName,
        vmvcAimStatPNICVCUUID
    }
    DESCRIPTION
        "The specified Physical NIC has been removed.  However,
         this trap does not trigger when a Host is removed, as 
         HostRemovedEvent will take precedence.
         Enabled with Trap Enable Flag 0x1."
    ::= 165243

vmvcAimPNICConfigChangeEvent OBJECT IDENTIFIER ::= { traps 165244 }
vmvcAimPNICConfigChangeTrap TRAP-TYPE
    ENTERPRISE sysmgmt
    VARIABLES {
        vmvcAimStatServerName,
        vmvcAimStatHostDCName,
        vmvcAimStatHostClusterName,
        vmvcAimStatHostName,
        vmvcAimStatPNICName,
        vmvcAimStatPNICMonitor,
        vmvcAimStatPNICAlert,
        vmvcAimStatPNICState,
        vmvcAimStatVCName,
        vmvcAimStatPNICVCName,
        vmvcAimStatPNICVCUUID
    }
    DESCRIPTION
        "The monitoring configuration for the specified physical NIC
         has been modified.
         Enabled with Trap Enable Flag 0x4."
    ::= 165244

vmvcAimDCTotalCPUStateChangeEvent OBJECT IDENTIFIER ::= { traps 165245 }
vmvcAimDCTotalCPUStateChangeTrap TRAP-TYPE
    ENTERPRISE sysmgmt
    VARIABLES {
        vmvcAimStatServerName,
        vmvcAimStatDatacenterName,
        vmvcAimStatDatacenterTotalCPUState,
        vmvcAimStatDatacenterTotalCPUUsage,
        vmvcAimStatDatacenterTotalCPUUsageWarnThresh,
        vmvcAimStatDatacenterTotalCPUUsageCritThresh,
        vmvcAimStatDatacenterIndex,
        vmvcAimStatVCName,
        vmvcAimStatDatacenterVCName,
        vmvcAimStatDatacenterVCUUID
    }
    DESCRIPTION
        "DataCenter Total CPU State has been changed.
         Enabled with Trap Enable Flag 0x2."
    ::= 165245

vmvcAimDCAddedEvent OBJECT IDENTIFIER ::= { traps 165246 }
vmvcAimDCAddedTrap TRAP-TYPE
    ENTERPRISE sysmgmt
    VARIABLES {
        vmvcAimStatServerName,
        vmvcAimStatDatacenterName,
        vmvcAimStatDatacenterDCFolderId,
        vmvcAimStatDatacenterDCFolderPath,
        vmvcAimStatDatacenterTotalCPUUsage,
        vmvcAimStatDatacenterTotalCPUUsageWarnThresh,
        vmvcAimStatDatacenterTotalCPUUsageCritThresh,
        vmvcAimStatDatacenterTotalMemUsage,
        vmvcAimStatDatacenterTotalMemWarnThres,
        vmvcAimStatDatacenterTotalMemCritThres,
        vmvcAimStatDatacenterIndex,
        vmvcAimStatVCName,
        vmvcAimStatDatacenterVCName,
        vmvcAimStatDatacenterVCUUID
    }
    DESCRIPTION
        "A new Datacenter entry has been detected and added.
         Enabled with Trap Enable Flag 0x1."
    ::= 165246

vmvcAimDCRemovedEvent OBJECT IDENTIFIER ::= { traps 165247 }
vmvcAimDCRemovedTrap TRAP-TYPE
    ENTERPRISE sysmgmt
    VARIABLES {
        vmvcAimStatServerName,
        vmvcAimStatDatacenterName,
        vmvcAimStatDatacenterIndex,
        vmvcAimStatVCName,
        vmvcAimStatDatacenterVCName,
        vmvcAimStatDatacenterVCUUID
    }
    DESCRIPTION
        "The specified Datacenter entry has been removed.
         Enabled with Trap Enable Flag 0x1."
    ::= 165247

vmvcAimDCRenamedEvent OBJECT IDENTIFIER ::= { traps 165248 }
vmvcAimDCRenamedTrap TRAP-TYPE
    ENTERPRISE sysmgmt
    VARIABLES {
        vmvcAimStatServerName,
        vmvcAimStatDatacenterName,
        vmvcAimStatDatacenterIndex,
        vmvcAimStatVCName,
        vmvcAimStatDatacenterVCName,
        vmvcAimStatDatacenterVCUUID
    }
    DESCRIPTION
        "The specified Datacenter has been renamed.  The new name is 
         located within the varbind list.
         Enabled with Trap Enable Flag 0x1."
    ::= 165248

vmvcAimDCConfigChangeEvent OBJECT IDENTIFIER ::= { traps 165249 }
vmvcAimDCConfigChangeTrap TRAP-TYPE
    ENTERPRISE sysmgmt
    VARIABLES {
        vmvcAimStatServerName,
        vmvcAimStatDatacenterName,
        vmvcAimStatDatacenterTotalCPUUsageWarnThresh,
        vmvcAimStatDatacenterTotalCPUUsageCritThresh,
        vmvcAimStatDatacenterTotalMemWarnThres,
        vmvcAimStatDatacenterTotalMemCritThres,
        vmvcAimStatDatacenterIndex,
        vmvcAimStatVCName,
        vmvcAimStatDatacenterVCName,
        vmvcAimStatDatacenterVCUUID
    }
    DESCRIPTION
        "The monitoring configuration for the specified Datacenter has 
         been modified.
         Enabled with Trap Enable Flag 0x4."
    ::= 165249

vmvcAimDCTotalMEMStateChangeEvent OBJECT IDENTIFIER ::= { traps 165250 }
vmvcAimDCTotalMEMStateChangeTrap TRAP-TYPE
    ENTERPRISE sysmgmt
    VARIABLES {
        vmvcAimStatServerName,
        vmvcAimStatDatacenterName,
        vmvcAimStatDatacenterTotalMemState,
        vmvcAimStatDatacenterTotalMemUsage,
        vmvcAimStatDatacenterTotalMemWarnThres,
        vmvcAimStatDatacenterTotalMemCritThres,
        vmvcAimStatDatacenterIndex,
        vmvcAimStatVCName,
        vmvcAimStatDatacenterVCName,
        vmvcAimStatDatacenterVCUUID
    }
    DESCRIPTION
        "DataCenter Total Memory State has been changed.
         Enabled with Trap Enable Flag 0x2."
    ::= 165250

vmvcAimClusterAddedEvent OBJECT IDENTIFIER ::= { traps 165251 }
vmvcAimClusterAddedTrap TRAP-TYPE
    ENTERPRISE sysmgmt
    VARIABLES {
        vmvcAimStatServerName,
        vmvcAimStatClusterDCName,
        vmvcAimStatClusterName,
        vmvcAimStatClusterDRSEnabled,
        vmvcAimStatClusterHAEnabled,
        vmvcAimStatClusterComputeResourceFolderID,
        vmvcAimStatClusterComputeResourceFolderPath,
        vmvcAimStatClusterVMBehaviour,
        vmvcAimStatClusterVMotionrate,
        vmvcAimStatClusterDCIndex,
        vmvcAimStatClusterIndex,
        vmvcAimStatVCName,
        vmvcAimStatClusterVCName,
        vmvcAimStatClusterVCUUID
    }
    DESCRIPTION
        "A new Cluster entry was detected and added.
         Enabled with Trap Enable Flag 0x1."
    ::= 165251

vmvcAimClusterRemovedEvent OBJECT IDENTIFIER ::= { traps 165252 }
vmvcAimClusterRemovedTrap TRAP-TYPE
    ENTERPRISE sysmgmt
    VARIABLES {
        vmvcAimStatServerName,
        vmvcAimStatClusterDCName,
        vmvcAimStatClusterName,
        vmvcAimStatClusterDCIndex,
        vmvcAimStatClusterIndex,
        vmvcAimStatVCName,
        vmvcAimStatClusterVCName,
        vmvcAimStatClusterVCUUID
    }
    DESCRIPTION
        "The specified Cluster has been removed.
         Enabled with Trap Enable Flag 0x1."
    ::= 165252

vmvcAimClusterHADRSChangeEvent OBJECT IDENTIFIER ::= { traps 165253 }
vmvcAimClusterHADRSChangeTrap TRAP-TYPE
    ENTERPRISE sysmgmt
    VARIABLES {
        vmvcAimStatServerName,
        vmvcAimStatClusterDCName,
        vmvcAimStatClusterName,
        vmvcAimStatClusterDRSEnabled,
        vmvcAimStatClusterHAEnabled,
        vmvcAimStatClusterDCIndex,
        vmvcAimStatClusterIndex,
        vmvcAimStatVCName,
        vmvcAimStatClusterVCName,
        vmvcAimStatClusterVCUUID
    }
    DESCRIPTION
        "The HA and/or DRS enabled configuration has been changed on the
         specified cluster.
         Enabled with Trap Enable Flag 0x1."
    ::= 165253

vmvcAimClusterRenamedEvent OBJECT IDENTIFIER ::= { traps 165254 }
vmvcAimClusterRenamedTrap TRAP-TYPE
    ENTERPRISE sysmgmt
    VARIABLES {
        vmvcAimStatServerName,
        vmvcAimStatClusterDCName,
        vmvcAimStatClusterName,
        vmvcAimStatClusterDCIndex,
        vmvcAimStatClusterIndex,
        vmvcAimStatVCName,
        vmvcAimStatClusterVCName,
        vmvcAimStatClusterVCUUID
    }
    DESCRIPTION
        "The specified Cluster has been renamed.  The new name is 
         located within the varbind list.
         Enabled with Trap Enable Flag 0x1."
    ::= 165254

vmvcAimClusterDRSConfigChangeEvent OBJECT IDENTIFIER ::= { traps 165255 }
vmvcAimClusterDRSConfigChangeTrap TRAP-TYPE
    ENTERPRISE sysmgmt
    VARIABLES {
        vmvcAimStatServerName,
        vmvcAimStatClusterDCName,
        vmvcAimStatClusterName,
        vmvcAimStatClusterVMBehaviour,
        vmvcAimStatClusterVMotionrate,
        vmvcAimStatClusterDCIndex,
        vmvcAimStatClusterIndex,
        vmvcAimStatVCName,
        vmvcAimStatClusterVCName,
        vmvcAimStatClusterVCUUID
    }
    DESCRIPTION
        "The DRS configuration for the specified cluster has been 
         changed.  This trap is triggered by changes to defaultVmBehavior and 
         VMware EVC. The integer flags are specified as varbinds to this trap.
         Enabled with Trap Enable Flag 0x1."
    ::= 165255

vmvcAimResourcePoolAddedEvent OBJECT IDENTIFIER ::= { traps 165256 }
vmvcAimResourcePoolAddedTrap TRAP-TYPE
    ENTERPRISE sysmgmt
    VARIABLES {
        vmvcAimStatServerName,
        vmvcAimStatDatacenterName,
        vmvcAimStatClusterName,
        vmvcAimStatHostName,
        vmvcAimStatResourcePoolName,
        vmvcAimStatResourcePoolIndexPath,
        vmvcAimStatResourcePoolName,
        vmvcAimStatResourcePoolParentPath,
        vmvcAimStatResourcePoolComputeResourceName,
        vmvcAimStatResourcePoolComputeResourcePath,
        vmvcAimStatResourcePoolCPUExpandReservation,
        vmvcAimStatResourcePoolMemExpandReservation,
        vmvcAimStatResourcePoolCPUShares,
        vmvcAimStatResourcePoolMemShares,
        vmvcAimStatResourcePoolCfgChgVersion,
        vmvcAimStatResourcePoolStatus,
        vmvcAimStatResourcePoolCPUUnReserveForPool,
        vmvcAimStatResourcePoolCPUUnReserveForVM,
        vmvcAimStatResourcePoolCPUReserveUsed,
        vmvcAimStatResourcePoolCPUReserveUsedForVM,
        vmvcAimStatResourcePoolMemUnReserveForPool,
        vmvcAimStatResourcePoolMemUnReserveForVM,
        vmvcAimStatResourcePoolMemReserveUsed,
        vmvcAimStatResourcePoolMemReserveUsedForVM,
        vmvcAimStatResourcePoolCPUMax,
        vmvcAimStatResourcePoolCPUMin,
        vmvcAimStatResourcePoolCPUMaxUsage,
        vmvcAimStatResourcePoolCPUOverAllUsage,
        vmvcAimStatResourcePoolMemMax,
        vmvcAimStatResourcePoolMemMin,
        vmvcAimStatResourcePoolMemMaxUsage,
        vmvcAimStatResourcePoolMemOverAllUsage,
        vmvcAimStatResourcePoolMonitor,
        vmvcAimStatResourcePoolAlert,
        vmvcAimStatResourcePoolIndex,
        vmvcAimStatResourcePoolParentId,
        vmvcAimStatResourcePoolType,
        vmvcAimStatVCName,
        vmvcAimStatResourcePoolVCName,
        vmvcAimStatResourcePoolComputeResourceId,
        vmvcAimStatResourcePoolState,
        vmvcAimStatResourcePoolVCUUID
    }
    DESCRIPTION
        "A new Resource Pool has been detected and added.
         Enabled with Trap Enable Flag 0x1."
    ::= 165256

vmvcAimResourcePoolRemovedEvent OBJECT IDENTIFIER ::= { traps 165257 }
vmvcAimResourcePoolRemovedTrap TRAP-TYPE
    ENTERPRISE sysmgmt
    VARIABLES {
        vmvcAimStatServerName,
        vmvcAimStatDatacenterName,
        vmvcAimStatClusterName,
        vmvcAimStatHostName,
        vmvcAimStatResourcePoolName,
        vmvcAimStatResourcePoolIndexPath,
        vmvcAimStatResourcePoolName,
        vmvcAimStatResourcePoolIndex,
        vmvcAimStatResourcePoolParentId,
        vmvcAimStatResourcePoolType,
        vmvcAimStatVCName,
        vmvcAimStatResourcePoolVCName,
        vmvcAimStatResourcePoolVCUUID
    }
    DESCRIPTION
        "The specified Resource Pool has been removed.
         Enabled with Trap Enable Flag 0x1."
    ::= 165257

vmvcAimResourcePoolCpuStateChangeEvent OBJECT IDENTIFIER ::= { traps 165258 }
vmvcAimResourcePoolCpuStateChangeTrap TRAP-TYPE
    ENTERPRISE sysmgmt
    VARIABLES {
        vmvcAimStatServerName,
        vmvcAimStatDatacenterName,
        vmvcAimStatClusterName,
        vmvcAimStatHostName,
        vmvcAimStatResourcePoolName,
        vmvcAimStatResourcePoolIndexPath,
        vmvcAimStatResourcePoolName,
        vmvcAimStatResourcePoolCPUState,
        vmvcAimStatResourcePoolIndex,
        vmvcAimStatResourcePoolParentId,
        vmvcAimStatResourcePoolType,
        vmvcAimStatVCName,
        vmvcAimStatResourcePoolVCName,
        vmvcAimStatResourcePoolVCUUID
    }
    DESCRIPTION
        "CPU states of the monitored resource pool has 
         changed.
         Enabled with Trap Enable Flag 0x2."
    ::= 165258

vmvcAimResourcePoolConfigChangeEvent OBJECT IDENTIFIER ::= { traps 165259 }
vmvcAimResourcePoolConfigChangeTrap TRAP-TYPE
    ENTERPRISE sysmgmt
    VARIABLES {
        vmvcAimStatServerName,
        vmvcAimStatDatacenterName,
        vmvcAimStatClusterName,
        vmvcAimStatHostName,
        vmvcAimStatResourcePoolName,
        vmvcAimStatResourcePoolIndexPath,
        vmvcAimStatResourcePoolName,
        vmvcAimStatResourcePoolCPUUsageWarn,
        vmvcAimStatResourcePoolCPUUsageCrit,
        vmvcAimStatResourcePoolCPUAlert,
        vmvcAimStatResourcePoolMemUsageWarn,
        vmvcAimStatResourcePoolMemUsageCrit,
        vmvcAimStatResourcePoolMemAlert,
        vmvcAimStatResourcePoolMonitor,
        vmvcAimStatResourcePoolAlert,
        vmvcAimStatResourcePoolIndex,
        vmvcAimStatResourcePoolParentId,
        vmvcAimStatResourcePoolType,
        vmvcAimStatVCName,
        vmvcAimStatResourcePoolVCName,
        vmvcAimStatResourcePoolVCUUID
    }
    DESCRIPTION
        "The monitor configuration for the specified resource pool has 
         been changed.
         Enabled with Trap Enable Flag 0x4."
    ::= 165259

vmvcAimResourcePoolRenamedEvent OBJECT IDENTIFIER ::= { traps 165260 }
vmvcAimResourcePoolRenamedTrap TRAP-TYPE
    ENTERPRISE sysmgmt
    VARIABLES {
        vmvcAimStatServerName,
        vmvcAimStatDatacenterName,
        vmvcAimStatClusterName,
        vmvcAimStatHostName,
        vmvcAimStatResourcePoolName,
        vmvcAimStatResourcePoolIndexPath,
        vmvcAimStatResourcePoolName,
        vmvcAimStatResourcePoolIndex,
        vmvcAimStatResourcePoolParentId,
        vmvcAimStatResourcePoolType,
        vmvcAimStatVCName,
        vmvcAimStatResourcePoolVCName,
        vmvcAimStatResourcePoolVCUUID
    }
    DESCRIPTION
        "The specified Resource Pool has been renamed.  The new name is 
         located within the varbind list.
         Enabled with Trap Enable Flag 0x1."
    ::= 165260

vmvcAimTemplateAddedEvent OBJECT IDENTIFIER ::= { traps 165261 }
vmvcAimTemplateAddedTrap TRAP-TYPE
    ENTERPRISE sysmgmt
    VARIABLES {
        vmvcAimStatServerName,
        vmvcAimStatHostDCName,
        vmvcAimStatHostClusterName,
        vmvcAimStatHostName,
        vmvcAimStatTemplateName,
        vmvcAimStatTemplateVMFolderName,
        vmvcAimStatTemplateVMFolderFullPath,
        vmvcAimStatTemplateOsType,
        vmvcAimStatTemplateNumVCpu,
        vmvcAimStatTemplateMem,
        vmvcAimStatTemplateIPAddress,
        vmvcAimStatTemplateDatastore,
        vmvcAimStatTemplateNetwork,
        vmvcAimStatTemplateConfigFile,
        vmvcAimStatTemplateIndex,
        vmvcAimStatTemplateVMFolderId,
        vmvcAimStatTemplateHostID,
        vmvcAimStatVCName,
        vmvcAimStatTemplateVCName,
        vmvcAimStatTemplateVCUUID
    }
    DESCRIPTION
        "A new Template was detected and added.
         Enabled with Trap Enable Flag 0x1."
    ::= 165261

vmvcAimTemplateRemovedEvent OBJECT IDENTIFIER ::= { traps 165262 }
vmvcAimTemplateRemovedTrap TRAP-TYPE
    ENTERPRISE sysmgmt
    VARIABLES {
        vmvcAimStatServerName,
        vmvcAimStatHostDCName,
        vmvcAimStatHostClusterName,
        vmvcAimStatHostName,
        vmvcAimStatTemplateName,
        vmvcAimStatTemplateIndex,
        vmvcAimStatTemplateVMFolderId,
        vmvcAimStatTemplateHostID,
        vmvcAimStatVCName,
        vmvcAimStatTemplateVCName,
        vmvcAimStatTemplateVCUUID
    }
    DESCRIPTION
        "The specified Template was removed.
         Enabled with Trap Enable Flag 0x1."
    ::= 165262

vmvcAimTemplateRenamedEvent OBJECT IDENTIFIER ::= { traps 165263 }
vmvcAimTemplateRenamedTrap TRAP-TYPE
    ENTERPRISE sysmgmt
    VARIABLES {
        vmvcAimStatServerName,
        vmvcAimStatHostDCName,
        vmvcAimStatHostClusterName,
        vmvcAimStatHostName,
        vmvcAimStatTemplateName,
        vmvcAimStatTemplateIndex,
        vmvcAimStatTemplateVMFolderId,
        vmvcAimStatTemplateHostID,
        vmvcAimStatVCName,
        vmvcAimStatTemplateVCName,
        vmvcAimStatTemplateVCUUID
    }
    DESCRIPTION
        "The specified Template has been renamed.  The new name is 
         located within the varbind list.
         Enabled with Trap Enable Flag 0x1."
    ::= 165263

vmvcAimResourcePoolMemStateChangeEvent OBJECT IDENTIFIER ::= { traps 165264 }
vmvcAimResourcePoolMemStateChangeTrap TRAP-TYPE
    ENTERPRISE sysmgmt
    VARIABLES {
        vmvcAimStatServerName,
        vmvcAimStatDatacenterName,
        vmvcAimStatClusterName,
        vmvcAimStatHostName,
        vmvcAimStatResourcePoolName,
        vmvcAimStatResourcePoolIndexPath,
        vmvcAimStatResourcePoolName,
        vmvcAimStatResourcePoolMemState,
        vmvcAimStatResourcePoolIndex,
        vmvcAimStatResourcePoolParentId,
        vmvcAimStatResourcePoolType,
        vmvcAimStatVCName,
        vmvcAimStatResourcePoolVCName,
        vmvcAimStatResourcePoolVCUUID
    }
    DESCRIPTION
        "Memory state of the monitored resource pool has changed.
         Enabled with Trap Enable Flag 0x2."
    ::= 165264

vmvcAimResourcePoolHealthStateChangeEvent OBJECT IDENTIFIER ::= { traps 165265 }
vmvcAimResourcePoolHealthStateChangeTrap TRAP-TYPE
    ENTERPRISE sysmgmt
    VARIABLES {
        vmvcAimStatServerName,
        vmvcAimStatDatacenterName,
        vmvcAimStatClusterName,
        vmvcAimStatHostName,
        vmvcAimStatResourcePoolName,
        vmvcAimStatResourcePoolIndexPath,
        vmvcAimStatResourcePoolName,
        vmvcAimStatResourcePoolState,
        vmvcAimStatResourcePoolIndex,
        vmvcAimStatResourcePoolParentId,
        vmvcAimStatResourcePoolType,
        vmvcAimStatVCName,
        vmvcAimStatResourcePoolVCName,
        vmvcAimStatResourcePoolVCUUID
    }
    DESCRIPTION
        "Health state of the monitored resource pool has changed.
         Enabled with Trap Enable Flag 0x2."
    ::= 165265

vmvcAimCustomizationSpecAddedEvent OBJECT IDENTIFIER ::= { traps 165266 }
vmvcAimCustomizationSpecAddedTrap TRAP-TYPE
    ENTERPRISE sysmgmt
    VARIABLES {
        vmvcAimStatServerName,
        vmvcAimStatCustomizationSpecName,
        vmvcAimStatCustomizationSpecType,
        vmvcAimStatCustomizationSpecLastUpdated,
        vmvcAimStatCustomizationSpecChgVer,
        vmvcAimStatVCName,
        vmvcAimStatCustomizationSpecLastUpdateTimeSec,
        vmvcAimStatCustomizationSpecUID,
        vmvcAimStatCustomizationSpecHostName,
        vmvcAimStatCustomizationSpecPrimaryDNSServer,
        vmvcAimStatCustomizationSpecSecondaryDNSServer,
        vmvcAimStatCustomizationSpecTertiaryDNSServer,
        vmvcAimStatCustomizationSpecDomainName,
        vmvcAimStatCustomizationSpecDNSSearchSuffixes,
        vmvcAimStatCustomizationSpecVCName,
        vmvcAimStatCustomizationSpecVCUUID
    }
    DESCRIPTION
        "A new Customization Specification have been detected and 
         added.
         Enabled with Trap Enable Flag 0x1."
    ::= 165266

vmvcAimCustomizationSpecRemovedEvent OBJECT IDENTIFIER ::= { traps 165267 }
vmvcAimCustomizationSpecRemovedTrap TRAP-TYPE
    ENTERPRISE sysmgmt
    VARIABLES {
        vmvcAimStatServerName,
        vmvcAimStatCustomizationSpecName,
        vmvcAimStatVCName,
        vmvcAimStatCustomizationSpecUID,
        vmvcAimStatCustomizationSpecVCName,
        vmvcAimStatCustomizationSpecVCUUID
    }
    DESCRIPTION
        "The designated Customization Specification has been removed.
         Enabled with Trap Enable Flag 0x1."
    ::= 165267

vmvcAimVMMemStateChangeEvent OBJECT IDENTIFIER ::= { traps 165268 }
vmvcAimVMMemStateChangeTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMMemoryState,
        vmvcAimStatVMMemoryPercentage,
        vmvcAimStatVMMemoryWarnThreshold,
        vmvcAimStatVMMemoryCritThreshold,
        vmvcAimStatVMHostID,
        vmvcAimStatVMResourcePoolId,
        vmvcAimStatVMIndex,
        vmvcAimStatVCName,
        vmvcAimStatVMVCName,
        vmvcAimStatVMVCUUID
    }
    DESCRIPTION
        "The state of the specified monitored VM has changed.  The memory new
         state, as well as the thresholds and the actual value, are
         supplied.
         Enabled with Trap Enable Flag 0x2."
    ::= 165268

vmvcAimVMPowerStateChangeEvent OBJECT IDENTIFIER ::= { traps 165269 }
vmvcAimVMPowerStateChangeTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMPowerState,
        vmvcAimStatVMHostID,
        vmvcAimStatVMResourcePoolId,
        vmvcAimStatVMIndex,
        vmvcAimStatVMPowerStatus,
        vmvcAimStatVMAlertPowerOffStatus,
        vmvcAimStatVCName,
        vmvcAimStatVMVCName,
        vmvcAimStatVMVCUUID
    }
    DESCRIPTION
        "The state of the specified monitored VM has changed.  The new
         power state and power status is supplied.
         Enabled with Trap Enable Flag 0x1."
    ::= 165269

vmvcAimVMHBStateChangeEvent OBJECT IDENTIFIER ::= { traps 165270 }
vmvcAimVMHBStateChangeTrap TRAP-TYPE
    ENTERPRISE sysmgmt
    VARIABLES {
        vmvcAimStatServerName,
        vmvcAimStatResourcePoolIndexPath,
        vmvcAimStatHostDCName,
        vmvcAimStatHostClusterName,
        vmvcAimStatHostName,
        vmvcAimStatVMName,
        vmvcAimStatResourcePoolName,
        vmvcAimStatVMConfigFileName,
        vmvcAimStatVMGuestOS,
        vmvcAimStatVMHeartbeatState,
        vmvcAimStatVMHostID,
        vmvcAimStatVMResourcePoolId,
        vmvcAimStatVMIndex,
        vmvcAimStatVCName,
        vmvcAimStatVMVCName,
        vmvcAimStatVMVCUUID
    }
    DESCRIPTION
        "The state of the specified monitored VM has changed.  The new
         Heart Beat state is supplied.
         Enabled with Trap Enable Flag 0x2."
    ::= 165270

vmvcAimDatastoreAddedEvent OBJECT IDENTIFIER ::= { traps 165271 }
vmvcAimDatastoreAddedTrap TRAP-TYPE
    ENTERPRISE sysmgmt
    VARIABLES {
        vmvcAimStatServerName,
        vmvcAimStatDatastoreName,
        vmvcAimStatDatastoreFreeSpace,
        vmvcAimStatDatastoreMaxFileSize,
        vmvcAimStatDatastoreType,
        vmvcAimStatDatastoreMultiHostAccess,
        vmvcAimStatDatastoreAccessible,
        vmvcAimStatDatastoreMonitor,
        vmvcAimStatDatastoreFreeSpaceAlert,
        vmvcAimStatDatastoreFreeSpaceWarnThresh,
        vmvcAimStatDatastoreFreeSpaceCritThresh,
        vmvcAimStatDatastoreFreeSpaceState,
        vmvcAimStatDatastoreAccessibleAlert,
        vmvcAimStatDatastoreAccessState,
        vmvcAimStatDatastoreURL,
        vmvcAimStatDatastoreCapacity,
        vmvcAimStatDatastoreFreeSpacePct,
        vmvcAimStatDatastoreHostList,
        vmvcAimStatDatastoreIndex,
        vmvcAimStatVCName,
        vmvcAimStatDatastoreVCName,
        vmvcAimStatDatastoreVCUUID
    }
    DESCRIPTION
        "A New Datastore has been detected and added.
         Enabled with Trap Enable Flag 0x1."
    ::= 165271

vmvcAimDatastoreRemovedEvent OBJECT IDENTIFIER ::= { traps 165272 }
vmvcAimDatastoreRemovedTrap TRAP-TYPE
    ENTERPRISE sysmgmt
    VARIABLES {
        vmvcAimStatServerName,
        vmvcAimStatDatastoreName,
        vmvcAimStatDatastoreHostList,
        vmvcAimStatDatastoreIndex,
        vmvcAimStatVCName,
        vmvcAimStatDatastoreVCName,
        vmvcAimStatDatastoreVCUUID
    }
    DESCRIPTION
        "The designated Datastore has been removed.
         Enabled with Trap Enable Flag 0x1."
    ::= 165272

vmvcAimDatastoreAccessibleStateChangeEvent OBJECT IDENTIFIER ::= { traps 165273 }
vmvcAimDatastoreAccessibleStateChangeTrap TRAP-TYPE
    ENTERPRISE sysmgmt
    VARIABLES {
        vmvcAimStatServerName,
        vmvcAimStatDatastoreName,
        vmvcAimStatDatastoreAccessState,
        vmvcAimStatDatastoreAccessible,
        vmvcAimStatDatastoreHostList,
        vmvcAimStatDatastoreIndex,
        vmvcAimStatVCName,
        vmvcAimStatDatastoreVCName,
        vmvcAimStatDatastoreVCUUID
    }
    DESCRIPTION
        "Accessible state of the monitored datastore has changed.
         Enabled with Trap Enable Flag 0x2."
    ::= 165273

vmvcAimDatastoreConfigChangeEvent OBJECT IDENTIFIER ::= { traps 165274 }
vmvcAimDatastoreConfigChangeTrap TRAP-TYPE
    ENTERPRISE sysmgmt
    VARIABLES {
        vmvcAimStatServerName,
        vmvcAimStatDatastoreName,
        vmvcAimStatDatastoreFreeSpaceAlert,
        vmvcAimStatDatastoreFreeSpaceWarnThresh,
        vmvcAimStatDatastoreFreeSpaceCritThresh,
        vmvcAimStatDatastoreAccessibleAlert,
        vmvcAimStatDatastoreMonitor,
        vmvcAimStatDatastoreHostList,
        vmvcAimStatDatastoreIndex,
        vmvcAimStatVCName,
        vmvcAimStatDatastoreVCName,
        vmvcAimStatDatastoreVCUUID
    }
    DESCRIPTION
        "The monitoring configuration for the specified datastore has 
         been changed.
         Enabled with Trap Enable Flag 0x4."
    ::= 165274

vmvcAimDatastoreRenamedEvent OBJECT IDENTIFIER ::= { traps 165275 }
vmvcAimDatastoreRenamedTrap TRAP-TYPE
    ENTERPRISE sysmgmt
    VARIABLES {
        vmvcAimStatServerName,
        vmvcAimStatDatastoreName,
        vmvcAimStatDatastoreHostList,
        vmvcAimStatDatastoreIndex,
        vmvcAimStatVCName,
        vmvcAimStatDatastoreVCName,
        vmvcAimStatDatastoreVCUUID
    }
    DESCRIPTION
        "The specified Datastore has been renamed.  The new name is 
         located within the varbind list.
         Enabled with Trap Enable Flag 0x1."
    ::= 165275

vmvcAimDatastoreFreeSpaceStateChangeEvent OBJECT IDENTIFIER ::= { traps 165276 }
vmvcAimDatastoreFreeSpaceStateChangeTrap TRAP-TYPE
    ENTERPRISE sysmgmt
    VARIABLES {
        vmvcAimStatServerName,
        vmvcAimStatDatastoreName,
        vmvcAimStatDatastoreFreeSpaceState,
        vmvcAimStatDatastoreFreeSpacePct,
        vmvcAimStatDatastoreFreeSpaceWarnThresh,
        vmvcAimStatDatastoreFreeSpaceCritThresh,
        vmvcAimStatDatastoreHostList,
        vmvcAimStatDatastoreIndex,
        vmvcAimStatVCName,
        vmvcAimStatDatastoreVCName,
        vmvcAimStatDatastoreVCUUID
    }
    DESCRIPTION
        "Free Space state of the monitored datastore has changed.
         Enabled with Trap Enable Flag 0x2."
    ::= 165276

vmvcAimDCFolderAddedEvent OBJECT IDENTIFIER ::= { traps 165277 }
vmvcAimDCFolderAddedTrap TRAP-TYPE
    ENTERPRISE sysmgmt
    VARIABLES {
        vmvcAimStatServerName,
        vmvcAimStatDatacenterFolderIndex,
        vmvcAimStatDatacenterFolderName,
        vmvcAimStatDatacenterFolderParentId,
        vmvcAimStatDatacenterFolderParentPath,
        vmvcAimStatVCName,
        vmvcAimStatDatacenterFolderVCName,
        vmvcAimStatDatacenterFolderVCUUID
    }
    DESCRIPTION
        "A new DC Folder has been added to VC.
         Enabled with Trap Enable Flag 0x1."
    ::= 165277

vmvcAimDCFolderRemovedEvent OBJECT IDENTIFIER ::= { traps 165278 }
vmvcAimDCFolderRemovedTrap TRAP-TYPE
    ENTERPRISE sysmgmt
    VARIABLES {
        vmvcAimStatServerName,
        vmvcAimStatDatacenterFolderIndex,
        vmvcAimStatDatacenterFolderName,
        vmvcAimStatDatacenterFolderParentId,
        vmvcAimStatDatacenterFolderParentPath,
        vmvcAimStatVCName,
        vmvcAimStatDatacenterFolderVCName,
        vmvcAimStatDatacenterFolderVCUUID
    }
    DESCRIPTION
        "The specified DC Folder has been removed from VC.
         Enabled with Trap Enable Flag 0x1."
    ::= 165278

vmvcAimDCFolderConfigChangeEvent OBJECT IDENTIFIER ::= { traps 165279 }
vmvcAimDCFolderConfigChangeTrap TRAP-TYPE
    ENTERPRISE sysmgmt
    VARIABLES {
        vmvcAimStatServerName,
        vmvcAimStatDatacenterFolderIndex,
        vmvcAimStatDatacenterFolderName,
        vmvcAimStatDatacenterFolderParentId,
        vmvcAimStatDatacenterFolderParentPath,
        vmvcAimStatVCName,
        vmvcAimStatDatacenterFolderVCName,
        vmvcAimStatDatacenterFolderVCUUID
    }
    DESCRIPTION
        "The monitoring configuration for the specified DC Folder has been
         modified.  This does not include changes to monitoring thresholds.
         Enabled with Trap Enable Flag 0x1."
    ::= 165279

vmvcAimCPUSensorStateChangeEvent OBJECT IDENTIFIER ::= { traps 165281 }
vmvcAimCPUSensorStateChangeTrap TRAP-TYPE
    ENTERPRISE sysmgmt
    VARIABLES {
        vmvcAimStatServerName,
        vmvcAimStatCPUSensorHostName,
        vmvcAimStatCPUSensorName,
        vmvcAimStatCPUSensorState,
        vmvcAimStatCPUSensorStatus,
        vmvcAimStatCPUSensorHostIndex,
        vmvcAimStatVCName,
        vmvcAimStatCPUSensorVCName,
        vmvcAimStatCPUSensorVCUUID
    }
    DESCRIPTION
        "The state of the monitored CPU sensor has changed.
         Enabled with Trap Enable Flag 0x2."
    ::= 165281

vmvcAimMemSensorStateChangeEvent OBJECT IDENTIFIER ::= { traps 165282 }
vmvcAimMemSensorStateChangeTrap TRAP-TYPE
    ENTERPRISE sysmgmt
    VARIABLES {
        vmvcAimStatServerName,
        vmvcAimStatMemSensorHostName,
        vmvcAimStatMemSensorName,
        vmvcAimStatMemSensorState,
        vmvcAimStatMemSensorStatus,
        vmvcAimStatMemSensorHostIndex,
        vmvcAimStatVCName,
        vmvcAimStatMemSensorVCName,
        vmvcAimStatMemSensorVCUUID
    }
    DESCRIPTION
        "The state of the monitored Memory sensor has changed.
         Enabled with Trap Enable Flag 0x2."
    ::= 165282

vmvcAimFanSensorStateChangeEvent OBJECT IDENTIFIER ::= { traps 165283 }
vmvcAimFanSensorStateChangeTrap TRAP-TYPE
    ENTERPRISE sysmgmt
    VARIABLES {
        vmvcAimStatServerName,
        vmvcAimStatFanSensorHostName,
        vmvcAimStatFanSensorName,
        vmvcAimStatFanSensorState,
        vmvcAimStatFanSensorRPM,
        vmvcAimStatFanSensorHostIndex,
        vmvcAimStatVCName,
        vmvcAimStatFanSensorVCName,
        vmvcAimStatFanSensorVCUUID
    }
    DESCRIPTION
        "The state of the monitored Fan sensor has changed.
         Enabled with Trap Enable Flag 0x2."
    ::= 165283

vmvcAimVoltageSensorStateChangeEvent OBJECT IDENTIFIER ::= { traps 165284 }
vmvcAimVoltageSensorStateChangeTrap TRAP-TYPE
    ENTERPRISE sysmgmt
    VARIABLES {
        vmvcAimStatServerName,
        vmvcAimStatVoltageSensorHostName,
        vmvcAimStatVoltageSensorName,
        vmvcAimStatVoltageSensorState,
        vmvcAimStatVoltageSensorVoltage,
        vmvcAimStatVoltageSensorHostIndex,
        vmvcAimStatVCName,
        vmvcAimStatVoltageSensorVCName,
        vmvcAimStatVoltageSensorVCUUID
    }
    DESCRIPTION
        "The state of the monitored Voltage sensor has changed.
         Enabled with Trap Enable Flag 0x2."
    ::= 165284

vmvcAimTempSensorStateChangeEvent OBJECT IDENTIFIER ::= { traps 165285 }
vmvcAimTempSensorStateChangeTrap TRAP-TYPE
    ENTERPRISE sysmgmt
    VARIABLES {
        vmvcAimStatServerName,
        vmvcAimStatTempSensorHostName,
        vmvcAimStatTempSensorName,
        vmvcAimStatTempSensorState,
        vmvcAimStatTempSensorTemp,
        vmvcAimStatTempSensorHostIndex,
        vmvcAimStatVCName,
        vmvcAimStatTempSensorVCName,
        vmvcAimStatTempSensorVCUUID
    }
    DESCRIPTION
        "The state of the monitored Temperature sensor has changed.
         Enabled with Trap Enable Flag 0x2."
    ::= 165285

vmvcAimPowerSensorStateChangeEvent OBJECT IDENTIFIER ::= { traps 165286 }
vmvcAimPowerSensorStateChangeTrap TRAP-TYPE
    ENTERPRISE sysmgmt
    VARIABLES {
        vmvcAimStatServerName,
        vmvcAimStatPowerSensorHostName,
        vmvcAimStatPowerSensorName,
        vmvcAimStatPowerSensorState,
        vmvcAimStatPowerSensorWatts,
        vmvcAimStatPowerSensorHostIndex,
        vmvcAimStatVCName,
        vmvcAimStatPowerSensorVCName,
        vmvcAimStatPowerSensorVCUUID
    }
    DESCRIPTION
        "The state of the monitored Power sensor has changed.
         Enabled with Trap Enable Flag 0x2."
    ::= 165286

vmvcAimSnapshotAddedEvent OBJECT IDENTIFIER ::= { traps 165287 }
vmvcAimSnapshotAddedTrap TRAP-TYPE
    ENTERPRISE sysmgmt
    VARIABLES {
        vmvcAimStatServerName,
        vmvcAimStatSnapshotParent,
        vmvcAimStatSnapshotName,
        vmvcAimStatSnapshotID,
        vmvcAimStatSnapshotVMIndex,
        vmvcAimStatSnapshotDescription,
        vmvcAimStatSnapshotMemoryState,
        vmvcAimStatSnapshotQuiesce,
        vmvcAimStatSnapshotCurrent,
        vmvcAimStatVCName,
        vmvcAimStatSnapshotVCName,
        vmvcAimStatSnapshotVCUUID
    }
    DESCRIPTION
        "A new Snapshot has been detected and added.
         Enabled with Trap Enable Flag 0x1."
    ::= 165287

vmvcAimSnapshotRemovedEvent OBJECT IDENTIFIER ::= { traps 165288 }
vmvcAimSnapshotRemovedTrap TRAP-TYPE
    ENTERPRISE sysmgmt
    VARIABLES {
        vmvcAimStatServerName,
        vmvcAimStatSnapshotParent,
        vmvcAimStatSnapshotName,
        vmvcAimStatSnapshotID,
        vmvcAimStatSnapshotVMIndex,
        vmvcAimStatVCName,
        vmvcAimStatSnapshotVCName,
        vmvcAimStatSnapshotVCUUID
    }
    DESCRIPTION
        "The specified Snapshot has been removed.
         Enabled with Trap Enable Flag 0x1."
    ::= 165288

vmvcAimSnapshotCurrentUpdateEvent OBJECT IDENTIFIER ::= { traps 165289 }
vmvcAimSnapshotCurrentUpdateTrap TRAP-TYPE
    ENTERPRISE sysmgmt
    VARIABLES {
        vmvcAimStatServerName,
        vmvcAimStatSnapshotParent,
        vmvcAimStatSnapshotName,
        vmvcAimStatSnapshotID,
        vmvcAimStatSnapshotVMIndex,
        vmvcAimStatSnapshotCurrent,
        vmvcAimStatVCName,
        vmvcAimStatSnapshotVCName,
        vmvcAimStatSnapshotVCUUID
    }
    DESCRIPTION
        "The specified Snapshot current status has changed.
         Enabled with Trap Enable Flag 0x1."
    ::= 165289

vmvcAimHostDiskAddedEvent OBJECT IDENTIFIER ::= { traps 165291 }
vmvcAimHostDiskAddedTrap TRAP-TYPE
    ENTERPRISE sysmgmt
    VARIABLES {
        vmvcAimStatServerName,
        vmvcAimStatHostDiskName,
        vmvcAimStatHostDiskHostID,
        vmvcAimStatHostDiskBusResets,
        vmvcAimStatHostDiskCmdAborted,
        vmvcAimStatHostDiskRead,
        vmvcAimStatHostDiskWrite,
        vmvcAimStatHostDiskKBPSRead,
        vmvcAimStatHostDiskKBPSWrite,
        vmvcAimStatHostDiskDatastoreName,
        vmvcAimStatVCName,
        vmvcAimStatHostDiskVCName,
        vmvcAimStatHostDiskVCUUID
    }
    DESCRIPTION
        "A new Disk has been detected and added to Host.
         Enabled with Trap Enable Flag 0x1."
    ::= 165291

vmvcAimHostDiskRemovedEvent OBJECT IDENTIFIER ::= { traps 165292 }
vmvcAimHostDiskRemovedTrap TRAP-TYPE
    ENTERPRISE sysmgmt
    VARIABLES {
        vmvcAimStatServerName,
        vmvcAimStatHostDiskName,
        vmvcAimStatHostDiskHostID,
        vmvcAimStatHostDiskDatastoreName,
        vmvcAimStatVCName,
        vmvcAimStatHostDiskVCName,
        vmvcAimStatHostDiskVCUUID
    }
    DESCRIPTION
        "The specified Disk has been removed.  However,
         this trap does not trigger when a Host is removed, as 
         HostRemovedEvent will take precedence.
         Enabled with Trap Enable Flag 0x1."
    ::= 165292

vmvcAimServerTotalCPUStateChangeEvent OBJECT IDENTIFIER ::= { traps 165293 }
vmvcAimServerTotalCPUStateChangeTrap TRAP-TYPE
    ENTERPRISE sysmgmt
    VARIABLES {
        vmvcAimStatServerName,
        vmvcAimStatServerTotalCPUState,
        vmvcAimStatServerTotalCPUUsage,
        vmvcAimStatServerTotalCPUUsageWarnThresh,
        vmvcAimStatServerTotalCPUUsageCritThresh,
        vmvcAimStatVCName,
        vmvcAimStatVCTotalCPUState,
        vmvcAimStatVCTotalCPUUsage,
        vmvcAimStatVCTotalCPUUsageWarn,
        vmvcAimStatVCTotalCPUUsageCrit,
        vmvcAimStatVCUUID
    }
    DESCRIPTION
        "VC Server Total CPU State has been changed.
         Enabled with Trap Enable Flag 0x2."
    ::= 165293

vmvcAimServerTotalMemStateChangeEvent OBJECT IDENTIFIER ::= { traps 165294 }
vmvcAimServerTotalMemStateChangeTrap TRAP-TYPE
    ENTERPRISE sysmgmt
    VARIABLES {
        vmvcAimStatServerName,
        vmvcAimStatServerTotalMemState,
        vmvcAimStatServerTotalMemUsage,
        vmvcAimStatServerTotalMemWarnThres,
        vmvcAimStatServerTotalMemCritThres,
        vmvcAimStatVCName,
        vmvcAimStatVCTotalMemState,
        vmvcAimStatVCTotalMemUsage,
        vmvcAimStatVCTotalMemWarn,
        vmvcAimStatVCTotalMemCrit,
        vmvcAimStatVCUUID
    }
    DESCRIPTION
        "VC Server Total Memory State has been changed.
         Enabled with Trap Enable Flag 0x2."
    ::= 165294

vmvcAimServerTotalDSFreeSpaceStateChangeEvent OBJECT IDENTIFIER ::= { traps 165295 }
vmvcAimServerTotalDSFreeSpaceStateChangeTrap TRAP-TYPE
    ENTERPRISE sysmgmt
    VARIABLES {
        vmvcAimStatServerName,
        vmvcAimStatServerTotalDatastoreFreeSpaceState,
        vmvcAimStatServerTotalDatastoreFreeSpacePct,
        vmvcAimStatServerTotalDatastoreFreeSpaceWarnThresh,
        vmvcAimStatServerTotalDatastoreFreeSpaceCritThresh,
        vmvcAimStatVCName,
        vmvcAimStatVCTotalDatastoreFreeSpaceState,
        vmvcAimStatVCTotalDatastoreFreeSpacePct,
        vmvcAimStatVCTotalDatastoreFreeSpaceWarn,
        vmvcAimStatVCTotalDatastoreFreeSpaceCrit,
        vmvcAimStatVCUUID
    }
    DESCRIPTION
        "VC Server Total DataStore FreeSpace State has been changed.
         Enabled with Trap Enable Flag 0x2."
    ::= 165295

vmvcAimSCSIControllerAddedEvent OBJECT IDENTIFIER ::= { traps 165296 }
vmvcAimSCSIControllerAddedTrap TRAP-TYPE
    ENTERPRISE sysmgmt
    VARIABLES {
        vmvcAimStatServerName,
        vmvcAimStatSCSIControllerVMID,
        vmvcAimStatSCSIControllerName,
        vmvcAimStatSCSIControllerKey,
        vmvcAimStatSCSIControllerControllerKey,
        vmvcAimStatSCSIControllerSummary,
        vmvcAimStatSCSIControllerBusNumber,
        vmvcAimStatSCSIControllerUnitNumber,
        vmvcAimStatVCName,
        vmvcAimStatSCSIControllerVCName,
        vmvcAimStatSCSIControllerVCUUID
    }
    DESCRIPTION
        "A new SCSI Controller has been detected and added to VM.
         Enabled with Trap Enable Flag 0x1."
    ::= 165296

vmvcAimSCSIControllerRemovedEvent OBJECT IDENTIFIER ::= { traps 165297 }
vmvcAimSCSIControllerRemovedTrap TRAP-TYPE
    ENTERPRISE sysmgmt
    VARIABLES {
        vmvcAimStatServerName,
        vmvcAimStatSCSIControllerVMID,
        vmvcAimStatSCSIControllerName,
        vmvcAimStatSCSIControllerKey,
        vmvcAimStatSCSIControllerControllerKey,
        vmvcAimStatVCName,
        vmvcAimStatSCSIControllerVCName,
        vmvcAimStatSCSIControllerVCUUID
    }
    DESCRIPTION
        "The specified SCSI Controller has been removed. However, 
         this trap does not trigger when VM removed, as VMRemovedEvent 
         will take precedence.
         Enabled with Trap Enable Flag 0x1."
    ::= 165297

vmvcAimVCAddedEvent OBJECT IDENTIFIER ::= { traps 165900 }
vmvcAimVCAddedTrap TRAP-TYPE
    ENTERPRISE sysmgmt
    VARIABLES {
        vmvcAimStatVCName,
        vmvcAimConfigVCHostName,
        vmvcAimConfigVCProtocol,
        vmvcAimConfigVCPort,
        vmvcAimConfigVCPollInterval,
        vmvcAimConfigVCRefreshInterval,
        vmvcAimStatVCProduct,
        vmvcAimStatVCOSType,
        vmvcAimStatVCVer,
        vmvcAimStatVCAPIVer,
        vmvcAimStatVCBuild,
        vmvcAimStatVCProdLine,
        vmvcAimStatVCState,
        vmvcAimStatVCTotalCPUState,
        vmvcAimStatVCTotalMemState,
        vmvcAimStatVCTotalDatastoreFreeSpaceState,
        vmvcAimConfigVCRowStatus,
        vmvcAimStatVCUUID
    }
    DESCRIPTION
        "A VC was added to this AIM.  Information on this
         VC is specified within the varbind list.
         Enabled with Trap Enable Flag 0x1."
    ::= 165900

vmvcAimVCRemovedEvent OBJECT IDENTIFIER ::= { traps 165901 }
vmvcAimVCRemovedTrap TRAP-TYPE
    ENTERPRISE sysmgmt
    VARIABLES {
        vmvcAimStatVCName,
        vmvcAimConfigVCHostName,
        vmvcAimStatVCUUID
    }
    DESCRIPTION
        "A VC was removed from this AIM.  The VC Name
         removed is specified within the varbind list.
         Enabled with Trap Enable Flag 0x1."
    ::= 165901

vmvcAimStorageSensorStateChangeEvent OBJECT IDENTIFIER ::= { traps 165905 }
vmvcAimStorageSensorStateChangeTrap TRAP-TYPE
    ENTERPRISE sysmgmt
    VARIABLES {
        vmvcAimStatVCName,
        vmvcAimStatStorageSensorHostName,
        vmvcAimStatStorageSensorName,
        vmvcAimStatStorageSensorState,
        vmvcAimStatStorageSensorStatus,
        vmvcAimStatStorageSensorHostIndex,
        vmvcAimStatStorageSensorVCName,
        vmvcAimStatStorageSensorVCUUID
    }
    DESCRIPTION
        "The state of the monitored Storage sensor has changed.
         Enabled with Trap Enable Flag 0x2."
    ::= 165905

vmvcAimHostPowerStateEvent OBJECT IDENTIFIER ::= { traps 165910 }
vmvcAimHostPowerStateTrap TRAP-TYPE
    ENTERPRISE sysmgmt
    VARIABLES {
        vmvcAimStatVCName,
        vmvcAimStatHostDCName,
        vmvcAimStatHostClusterName,
        vmvcAimStatHostName,
        vmvcAimStatHostPowerStatus,
        vmvcAimStatHostDCIndex,
        vmvcAimStatHostClusterId,
        vmvcAimStatHostID,
        vmvcAimStatHostVCName,
        vmvcAimStatHostVCUUID
    }
    DESCRIPTION
        "The Power Status of the specified host has changed.  The
         new power value is specified within the varbind list.
         Enabled with Trap Enable Flag 0x1."
    ::= 165910

vmvcAimVSwitchAddedEvent OBJECT IDENTIFIER ::= { traps 165915 }
vmvcAimVSwitchAddedTrap TRAP-TYPE
    ENTERPRISE sysmgmt
    VARIABLES {
        vmvcAimStatSwitchVCName,
        vmvcAimStatSwitchName,
        vmvcAimStatSwitchHost,
        vmvcAimStatSwitchIndex,
        vmvcAimStatSwitchState,
        vmvcAimStatSwitchPortgroup,
        vmvcAimStatSwitchBridgeType,
        vmvcAimStatSwitchBridgePNic,
        vmvcAimStatSwitchMonitor,
        vmvcAimStatSwitchAlert,
        vmvcAimStatSwitchHostName,
        vmvcAimStatSwitchVCUUID
    }
    DESCRIPTION
        "The specified Virtual Switch was added.
         Enabled with Trap Enable Flag 0x1."
    ::= 165915

vmvcAimVSwitchRemovedEvent OBJECT IDENTIFIER ::= { traps 165916 }
vmvcAimVSwitchRemovedTrap TRAP-TYPE
    ENTERPRISE sysmgmt
    VARIABLES {
        vmvcAimStatSwitchVCName,
        vmvcAimStatSwitchName,
        vmvcAimStatSwitchHost,
        vmvcAimStatSwitchIndex,
        vmvcAimStatSwitchHostName,
        vmvcAimStatSwitchVCUUID
    }
    DESCRIPTION
        "The specified Virtual Switch was removed.
         Enabled with Trap Enable Flag 0x1."
    ::= 165916

vmvcAimVSwitchConfigChangeEvent OBJECT IDENTIFIER ::= { traps 165917 }
vmvcAimVSwitchConfigChangeTrap TRAP-TYPE
    ENTERPRISE sysmgmt
    VARIABLES {
        vmvcAimStatSwitchVCName,
        vmvcAimStatSwitchName,
        vmvcAimStatSwitchHost,
        vmvcAimStatSwitchIndex,
        vmvcAimStatSwitchMonitor,
        vmvcAimStatSwitchAlert,
        vmvcAimStatSwitchHostName,
        vmvcAimStatSwitchVCUUID
    }
    DESCRIPTION
        "Monitoring configuration for the specified Virtual Switch was changed.
         Enabled with Trap Enable Flag 0x4."
    ::= 165917

vmvcAimVMGuestDiskAddedEvent OBJECT IDENTIFIER ::= { traps 165920 }
vmvcAimVMGuestDiskAddedTrap TRAP-TYPE
    ENTERPRISE sysmgmt
    VARIABLES {
        vmvcAimStatVCName,
        vmvcAimStatVMGuestDiskVMID,
        vmvcAimStatVMGuestDiskVMName,
        vmvcAimStatVMGuestDiskPath,
        vmvcAimStatVMGuestDiskCapacity,
        vmvcAimStatVMGuestDiskFreeSpace,
        vmvcAimStatVMGuestDiskUsagePct,
        vmvcAimStatVMGuestDiskMonitor,
        vmvcAimStatVMGuestDiskAlert,
        vmvcAimStatVMGuestDiskUsageWarnThresh,
        vmvcAimStatVMGuestDiskUsageCritThresh,
        vmvcAimStatVMGuestDiskState,
        vmvcAimStatVMGuestDiskVCName,
        vmvcAimStatVMGuestDiskVCUUID
    }
    DESCRIPTION
        "The specified Guest Disk has been detected and added.
         Enabled with Trap Enable Flag 0x1."
    ::= 165920

vmvcAimVMGuestDiskRemovedEvent OBJECT IDENTIFIER ::= { traps 165921 }
vmvcAimVMGuestDiskRemovedTrap TRAP-TYPE
    ENTERPRISE sysmgmt
    VARIABLES {
        vmvcAimStatVCName,
        vmvcAimStatVMGuestDiskVMID,
        vmvcAimStatVMGuestDiskVMName,
        vmvcAimStatVMGuestDiskPath,
        vmvcAimStatVMGuestDiskVCName,
        vmvcAimStatVMGuestDiskVCUUID
    }
    DESCRIPTION
        "The specified Guest Disk has been removed.
         Enabled with Trap Enable Flag 0x1."
    ::= 165921

vmvcAimVMGuestDiskStateChangeEvent OBJECT IDENTIFIER ::= { traps 165922 }
vmvcAimVMGuestDiskStateChangeTrap TRAP-TYPE
    ENTERPRISE sysmgmt
    VARIABLES {
        vmvcAimStatVCName,
        vmvcAimStatVMGuestDiskVMID,
        vmvcAimStatVMGuestDiskVMName,
        vmvcAimStatVMGuestDiskPath,
        vmvcAimStatVMGuestDiskUsagePct,
        vmvcAimStatVMGuestDiskMonitor,
        vmvcAimStatVMGuestDiskAlert,
        vmvcAimStatVMGuestDiskUsageWarnThresh,
        vmvcAimStatVMGuestDiskUsageCritThresh,
        vmvcAimStatVMGuestDiskState,
        vmvcAimStatVMGuestDiskVCName,
        vmvcAimStatVMGuestDiskVCUUID
    }
    DESCRIPTION
        "Disk Usage Monitoring State has changed.
         Enabled with Trap Enable Flag 0x2."
    ::= 165922

vmvcAimVMGuestDiskConfigChangeEvent OBJECT IDENTIFIER ::= { traps 165923 }
vmvcAimVMGuestDiskConfigChangeTrap TRAP-TYPE
    ENTERPRISE sysmgmt
    VARIABLES {
        vmvcAimStatVCName,
        vmvcAimStatVMGuestDiskVMID,
        vmvcAimStatVMGuestDiskVMName,
        vmvcAimStatVMGuestDiskPath,
        vmvcAimStatVMGuestDiskUsagePct,
        vmvcAimStatVMGuestDiskMonitor,
        vmvcAimStatVMGuestDiskAlert,
        vmvcAimStatVMGuestDiskUsageWarnThresh,
        vmvcAimStatVMGuestDiskUsageCritThresh,
        vmvcAimStatVMGuestDiskVCName,
        vmvcAimStatVMGuestDiskVCUUID
    }
    DESCRIPTION
        "Monitor or monitoring thresholds have been modified for VM Guest disk.
         Enabled with Trap Enable Flag 0x4."
    ::= 165923

vmvcAimHostVNICAddedEvent OBJECT IDENTIFIER ::= { traps 165925 }
vmvcAimHostVNICAddedTrap TRAP-TYPE
    ENTERPRISE sysmgmt
    VARIABLES {
        vmvcAimStatHostVNICVCName,
        vmvcAimStatHostVNICName,
        vmvcAimStatHostVNICHostIndex,
        vmvcAimStatHostVNICHostName,
        vmvcAimStatHostVNICPortgroup,
        vmvcAimStatHostVNICMAC,
        vmvcAimStatHostVNICIp,
        vmvcAimStatHostVNICType,
        vmvcAimStatHostVNICIpV6,
        vmvcAimStatHostVNICDVPortGroupIndex,
        vmvcAimStatHostVNICDVPortKey,
        vmvcAimStatHostVNICVCUUID
    }
    DESCRIPTION
        "The specified Host VNIC has been detected and added.
         Enabled with Trap Enable Flag 0x1."
    ::= 165925

vmvcAimHostVNICRemovedEvent OBJECT IDENTIFIER ::= { traps 165926 }
vmvcAimHostVNICRemovedTrap TRAP-TYPE
    ENTERPRISE sysmgmt
    VARIABLES {
        vmvcAimStatHostVNICVCName,
        vmvcAimStatHostVNICName,
        vmvcAimStatHostVNICHostIndex,
        vmvcAimStatHostVNICHostName,
        vmvcAimStatHostVNICVCUUID
    }
    DESCRIPTION
        "The specified Host VNIC has been removed.  However,
         this trap does not trigger when a Host is removed, as 
         HostRemovedEvent will take precedence.
         Enabled with Trap Enable Flag 0x1."
    ::= 165926

vmvcAimPortGroupAddedEvent OBJECT IDENTIFIER ::= { traps 165930 }
vmvcAimPortGroupAddedTrap TRAP-TYPE
    ENTERPRISE sysmgmt
    VARIABLES {
        vmvcAimStatPGVCName,
        vmvcAimStatPGName,
        vmvcAimStatPGHostIndex,
        vmvcAimStatPGVlanId,
        vmvcAimStatPGVSwitchName,
        vmvcAimStatPGPorts,
        vmvcAimStatPGHostName,
        vmvcAimStatPGVCUUID
    }
    DESCRIPTION
        "The specified Port Group has been detected and added.
         Enabled with Trap Enable Flag 0x1."
    ::= 165930

vmvcAimPortGroupRemovedEvent OBJECT IDENTIFIER ::= { traps 165931 }
vmvcAimPortGroupRemovedTrap TRAP-TYPE
    ENTERPRISE sysmgmt
    VARIABLES {
        vmvcAimStatPGVCName,
        vmvcAimStatPGName,
        vmvcAimStatPGHostIndex,
        vmvcAimStatPGVCUUID
    }
    DESCRIPTION
        "The specified Port Group has been removed.
         Enabled with Trap Enable Flag 0x1."
    ::= 165931

vmvcAimPortGroupVCConfigChangeEvent OBJECT IDENTIFIER ::= { traps 165932 }
vmvcAimPortGroupVCConfigChangeTrap TRAP-TYPE
    ENTERPRISE sysmgmt
    VARIABLES {
        vmvcAimStatPGVCName,
        vmvcAimStatPGName,
        vmvcAimStatPGHostIndex,
        vmvcAimStatPGVlanId,
        vmvcAimStatPGVSwitchName,
        vmvcAimStatPGPorts,
        vmvcAimStatPGHostName,
        vmvcAimStatPGVCUUID
    }
    DESCRIPTION
        "The specified Port Group has been detected and added.
         Enabled with Trap Enable Flag 0x1."
    ::= 165932

vmvcAimDistribVSwitchAddedEvent OBJECT IDENTIFIER ::= { traps 165935 }
vmvcAimDistribVSwitchAddedTrap TRAP-TYPE
    ENTERPRISE sysmgmt
    VARIABLES {
        vmvcAimStatDVSwitchVCName,
        vmvcAimStatDVSwitchIndex,
        vmvcAimStatDVSwitchName,
        vmvcAimStatDVSwitchUUID,
        vmvcAimStatDVSwitchDCName,
        vmvcAimStatDVSwitchDCIndex,
        vmvcAimStatDVSwitchParentPath,
        vmvcAimStatDVSwitchOverallStatus,
        vmvcAimStatDVSwitchMonitor,
        vmvcAimStatDVSwitchAlert,
        vmvcAimStatDVSwitchState,
        vmvcAimStatDVSwitchProductClass,
        vmvcAimStatDVSwitchProductName,
        vmvcAimStatDVSwitchProductVendor,
        vmvcAimStatDVSwitchProductVersion,
        vmvcAimStatDVSwitchHost,
        vmvcAimStatDVSwitchNumPorts,
        vmvcAimStatDVSwitchMaxPorts,
        vmvcAimStatDVSwitchDVPortGroup,
        vmvcAimStatDVSwitchDVUplinkPortGroup,
        vmvcAimStatDVSwitchVCUUID
    }
    DESCRIPTION
        "The specified Distributed Virtual Switch has been detected and added.
         Enabled with Trap Enable Flag 0x1."
    ::= 165935

vmvcAimDistribVSwitchRemovedEvent OBJECT IDENTIFIER ::= { traps 165936 }
vmvcAimDistribVSwitchRemovedTrap TRAP-TYPE
    ENTERPRISE sysmgmt
    VARIABLES {
        vmvcAimStatDVSwitchVCName,
        vmvcAimStatDVSwitchIndex,
        vmvcAimStatDVSwitchName,
        vmvcAimStatDVSwitchUUID,
        vmvcAimStatDVSwitchDCName,
        vmvcAimStatDVSwitchDCIndex,
        vmvcAimStatDVSwitchVCUUID
    }
    DESCRIPTION
        "The specified Distributed Virtual Switch has been removed.
         Enabled with Trap Enable Flag 0x1."
    ::= 165936

vmvcAimDistribVSwitchStateChangeEvent OBJECT IDENTIFIER ::= { traps 165937 }
vmvcAimDistribVSwitchStateChangeTrap TRAP-TYPE
    ENTERPRISE sysmgmt
    VARIABLES {
        vmvcAimStatDVSwitchVCName,
        vmvcAimStatDVSwitchIndex,
        vmvcAimStatDVSwitchName,
        vmvcAimStatDVSwitchUUID,
        vmvcAimStatDVSwitchDCName,
        vmvcAimStatDVSwitchDCIndex,
        vmvcAimStatDVSwitchOverallStatus,
        vmvcAimStatDVSwitchMonitor,
        vmvcAimStatDVSwitchAlert,
        vmvcAimStatDVSwitchState,
        vmvcAimStatDVSwitchVCUUID
    }
    DESCRIPTION
        "Monitoring State of specified Distributed Virtual Switch has changed.
         Enabled with Trap Enable Flag 0x2."
    ::= 165937

vmvcAimDistribVSwitchConfigChangeEvent OBJECT IDENTIFIER ::= { traps 165938 }
vmvcAimDistribVSwitchConfigChangeTrap TRAP-TYPE
    ENTERPRISE sysmgmt
    VARIABLES {
        vmvcAimStatDVSwitchVCName,
        vmvcAimStatDVSwitchIndex,
        vmvcAimStatDVSwitchName,
        vmvcAimStatDVSwitchUUID,
        vmvcAimStatDVSwitchDCName,
        vmvcAimStatDVSwitchDCIndex,
        vmvcAimStatDVSwitchOverallStatus,
        vmvcAimStatDVSwitchMonitor,
        vmvcAimStatDVSwitchAlert,
        vmvcAimStatDVSwitchVCUUID
    }
    DESCRIPTION
        "Monitor configuration has been modified for specified Distributed Virtual Switch.
         Enabled with Trap Enable Flag 0x4."
    ::= 165938

vmvcAimDistribVSwitchVCConfigChangeEvent OBJECT IDENTIFIER ::= { traps 165939 }
vmvcAimDistribVSwitchVCConfigChangeTrap TRAP-TYPE
    ENTERPRISE sysmgmt
    VARIABLES {
        vmvcAimStatDVSwitchVCName,
        vmvcAimStatDVSwitchIndex,
        vmvcAimStatDVSwitchName,
        vmvcAimStatDVSwitchUUID,
        vmvcAimStatDVSwitchDCName,
        vmvcAimStatDVSwitchDCIndex,
        vmvcAimStatDVSwitchParentPath,
        vmvcAimStatDVSwitchProductClass,
        vmvcAimStatDVSwitchProductName,
        vmvcAimStatDVSwitchProductVendor,
        vmvcAimStatDVSwitchProductVersion,
        vmvcAimStatDVSwitchHost,
        vmvcAimStatDVSwitchNumPorts,
        vmvcAimStatDVSwitchMaxPorts,
        vmvcAimStatDVSwitchDVPortGroup,
        vmvcAimStatDVSwitchDVUplinkPortGroup,
        vmvcAimStatDVSwitchVLanID,
        vmvcAimStatDVSwitchPrivateVLanID,
        vmvcAimStatDVSwitchVCUUID
    }
    DESCRIPTION
        "The specified Distributed Virtual Switch has been reconfigured in VC.
         This does not apply to Port Policy Changes.
         Enabled with Trap Enable Flag 0x1."
    ::= 165939

vmvcAimDVPortGroupAddedEvent OBJECT IDENTIFIER ::= { traps 165940 }
vmvcAimDVPortGroupAddedTrap TRAP-TYPE
    ENTERPRISE sysmgmt
    VARIABLES {
        vmvcAimStatDVPGVCName,
        vmvcAimStatDVPGIndex,
        vmvcAimStatDVPGName,
        vmvcAimStatDVPGDVSwitchName,
        vmvcAimStatDVPGDVSwitchIndex,
        vmvcAimStatDVPGDCName,
        vmvcAimStatDVPGDCIndex,
        vmvcAimStatDVPGHost,
        vmvcAimStatDVPGNumPorts,
        vmvcAimStatDVPGPortKeys,
        vmvcAimStatDVPGUplink,
        vmvcAimStatDVPGOverallStatus,
        vmvcAimStatDVPGVLanID,
        vmvcAimStatDVPGPrivateVLanID,
        vmvcAimStatDVPGVLanTrunkRange,
        vmvcAimStatDVPGVCUUID
    }
    DESCRIPTION
        "The specified DV Port Group has been detected and added.
         Enabled with Trap Enable Flag 0x1."
    ::= 165940

vmvcAimDVPortGroupRemovedEvent OBJECT IDENTIFIER ::= { traps 165941 }
vmvcAimDVPortGroupRemovedTrap TRAP-TYPE
    ENTERPRISE sysmgmt
    VARIABLES {
        vmvcAimStatDVPGVCName,
        vmvcAimStatDVPGIndex,
        vmvcAimStatDVPGName,
        vmvcAimStatDVPGDVSwitchName,
        vmvcAimStatDVPGDVSwitchIndex,
        vmvcAimStatDVPGDCName,
        vmvcAimStatDVPGDCIndex,
		vmvcAimStatDVPGUplink,
        vmvcAimStatDVPGVCUUID
    }
    DESCRIPTION
        "The specified DV Port Group has been removed.
         Enabled with Trap Enable Flag 0x1."
    ::= 165941

vmvcAimDVPortGroupVCConfigChangeEvent OBJECT IDENTIFIER ::= { traps 165942 }
vmvcAimDVPortGroupVCConfigChangeTrap TRAP-TYPE
    ENTERPRISE sysmgmt
    VARIABLES {
        vmvcAimStatDVPGVCName,
        vmvcAimStatDVPGIndex,
        vmvcAimStatDVPGName,
        vmvcAimStatDVPGDVSwitchName,
        vmvcAimStatDVPGDVSwitchIndex,
        vmvcAimStatDVPGDCName,
        vmvcAimStatDVPGDCIndex,
        vmvcAimStatDVPGHost,
        vmvcAimStatDVPGNumPorts,
        vmvcAimStatDVPGPortKeys,
        vmvcAimStatDVPGUplink,
        vmvcAimStatDVPGVLanID,
        vmvcAimStatDVPGPrivateVLanID,
        vmvcAimStatDVPGVLanTrunkRange,
        vmvcAimStatDVPGVCUUID
    }
    DESCRIPTION
        "The specified DV Port Group has been reconfigured in VC.
         This does not apply to Port Policy Changes.
         Enabled with Trap Enable Flag 0x1."
    ::= 165942

vmvcAimDVUplinkPortGroupAddedEvent OBJECT IDENTIFIER ::= { traps 165943 }
vmvcAimDVUplinkPortGroupAddedTrap TRAP-TYPE
    ENTERPRISE sysmgmt
    VARIABLES {
        vmvcAimStatDVPGVCName,
        vmvcAimStatDVPGIndex,
        vmvcAimStatDVPGName,
        vmvcAimStatDVPGDVSwitchName,
        vmvcAimStatDVPGDVSwitchIndex,
        vmvcAimStatDVPGDCName,
        vmvcAimStatDVPGDCIndex,
        vmvcAimStatDVPGHost,
        vmvcAimStatDVPGNumPorts,
        vmvcAimStatDVPGPortKeys,
        vmvcAimStatDVPGUplink,
        vmvcAimStatDVPGOverallStatus,
        vmvcAimStatDVPGVLanID,
        vmvcAimStatDVPGPrivateVLanID,
        vmvcAimStatDVPGVLanTrunkRange,
        vmvcAimStatDVPGVCUUID
    }
    DESCRIPTION
        "The specified DV Uplink Port Group has been detected and added.
         Enabled with Trap Enable Flag 0x1."
    ::= 165943

vmvcAimDVUplinkPortGroupRemovedEvent OBJECT IDENTIFIER ::= { traps 165944 }
vmvcAimDVUplinkPortGroupRemovedTrap TRAP-TYPE
    ENTERPRISE sysmgmt
    VARIABLES {
        vmvcAimStatDVPGVCName,
        vmvcAimStatDVPGIndex,
        vmvcAimStatDVPGName,
        vmvcAimStatDVPGDVSwitchName,
        vmvcAimStatDVPGDVSwitchIndex,
        vmvcAimStatDVPGDCName,
        vmvcAimStatDVPGDCIndex,
		vmvcAimStatDVPGUplink,
        vmvcAimStatDVPGVCUUID
    }
    DESCRIPTION
        "The specified DV Uplink Port Group has been removed.
         Enabled with Trap Enable Flag 0x1."
    ::= 165944

vmvcAimDVUplinkPortGroupVCConfigChangeEvent OBJECT IDENTIFIER ::= { traps 165945 }
vmvcAimDVUplinkPortGroupVCConfigChangeTrap TRAP-TYPE
    ENTERPRISE sysmgmt
    VARIABLES {
        vmvcAimStatDVPGVCName,
        vmvcAimStatDVPGIndex,
        vmvcAimStatDVPGName,
        vmvcAimStatDVPGDVSwitchName,
        vmvcAimStatDVPGDVSwitchIndex,
        vmvcAimStatDVPGDCName,
        vmvcAimStatDVPGDCIndex,
        vmvcAimStatDVPGHost,
        vmvcAimStatDVPGNumPorts,
        vmvcAimStatDVPGPortKeys,
        vmvcAimStatDVPGUplink,
        vmvcAimStatDVPGVLanID,
        vmvcAimStatDVPGPrivateVLanID,
        vmvcAimStatDVPGVLanTrunkRange,
        vmvcAimStatDVPGVCUUID
    }
    DESCRIPTION
        "The specified DV Uplink Port Group has been reconfigured in VC.
         This does not apply to Port Policy Changes.
         Enabled with Trap Enable Flag 0x1."
    ::= 165945

vmvcAimDistribVSwitchPortPolicyChangeEvent OBJECT IDENTIFIER ::= { traps 165950 }
vmvcAimDistribVSwitchPortPolicyChangeTrap TRAP-TYPE
    ENTERPRISE sysmgmt
    VARIABLES {
        vmvcAimStatDVSwitchVCName,
        vmvcAimStatDVSwitchIndex,
        vmvcAimStatDVSwitchName,
        vmvcAimStatDVSwitchUUID,
        vmvcAimStatDVSwitchDCName,
        vmvcAimStatDVSwitchDCIndex,
        vmvcAimStatDVSwitchPolicySecurityAllowPromis,
        vmvcAimStatDVSwitchPolicySecurityForgedTransmit,
        vmvcAimStatDVSwitchPolicySecurityMACChanges,
        vmvcAimStatDVSwitchPolicyShapingInAvgBandWidth,
        vmvcAimStatDVSwitchPolicyShapingInBurstSize,
        vmvcAimStatDVSwitchPolicyShapingInEnabled,
        vmvcAimStatDVSwitchPolicyShapingInPeakBandWidth,
        vmvcAimStatDVSwitchPolicyShapingOutAvgBandWidth,
        vmvcAimStatDVSwitchPolicyShapingOutBurstSize,
        vmvcAimStatDVSwitchPolicyShapingOutEnabled,
        vmvcAimStatDVSwitchPolicyShapingOutPeakBandWidth,
        vmvcAimStatDVSwitchUplinkTeamActivePort,
        vmvcAimStatDVSwitchUplinkTeamStandByPort,
        vmvcAimStatDVSwitchUplinkTeamNotifySwitch,
        vmvcAimStatDVSwitchUplinkTeamPolicy,
        vmvcAimStatDVSwitchUplinkTeamReversePolicy,
        vmvcAimStatDVSwitchUplinkTeamRollingOrder,
        vmvcAimStatDVSwitchUplinkTeamFailureChkBeacon,
        vmvcAimStatDVSwitchUplinkTeamFailureChkDuplex,
        vmvcAimStatDVSwitchUplinkTeamFailureChkErrPct,
        vmvcAimStatDVSwitchUplinkTeamFailureChkSpeed,
        vmvcAimStatDVSwitchUplinkTeamFailureFullDuplex,
        vmvcAimStatDVSwitchUplinkTeamFailurePercentage,
        vmvcAimStatDVSwitchUplinkTeamFailureSpeed,
        vmvcAimStatDVSwitchVCUUID
    }
    DESCRIPTION
        "The specified DVSwitch has had its Port Policy modified in VC.
         Enabled with Trap Enable Flag 0x1."
    ::= 165950

vmvcAimDVPortGroupPortPolicyChangeEvent OBJECT IDENTIFIER ::= { traps 165951 }
vmvcAimDVPortGroupPortPolicyChangeTrap TRAP-TYPE
    ENTERPRISE sysmgmt
    VARIABLES {
        vmvcAimStatDVPGVCName,
        vmvcAimStatDVPGIndex,
        vmvcAimStatDVPGName,
        vmvcAimStatDVPGDVSwitchName,
        vmvcAimStatDVPGDVSwitchIndex,
        vmvcAimStatDVPGDCName,
        vmvcAimStatDVPGDCIndex,
        vmvcAimStatDVPGPolicySecurityAllowPromis,
        vmvcAimStatDVPGPolicySecurityForgedTransmit,
        vmvcAimStatDVPGPolicySecurityMACChanges,
        vmvcAimStatDVPGPolicyShapingInAvgBandWidth,
        vmvcAimStatDVPGPolicyShapingInBurstSize,
        vmvcAimStatDVPGPolicyShapingInEnabled,
        vmvcAimStatDVPGPolicyShapingInPeakBandWidth,
        vmvcAimStatDVPGPolicyShapingOutAvgBandWidth,
        vmvcAimStatDVPGPolicyShapingOutBurstSize,
        vmvcAimStatDVPGPolicyShapingOutEnabled,
        vmvcAimStatDVPGPolicyShapingOutPeakBandWidth,
        vmvcAimStatDVPGUplinkTeamActivePort,
        vmvcAimStatDVPGUplinkTeamStandByPort,
        vmvcAimStatDVPGUplinkTeamNotifySwitch,
        vmvcAimStatDVPGUplinkTeamPolicy,
        vmvcAimStatDVPGUplinkTeamReversePolicy,
        vmvcAimStatDVPGUplinkTeamRollingOrder,
        vmvcAimStatDVPGUplinkTeamFailureChkBeacon,
        vmvcAimStatDVPGUplinkTeamFailureChkDuplex,
        vmvcAimStatDVPGUplinkTeamFailureChkErrPct,
        vmvcAimStatDVPGUplinkTeamFailureChkSpeed,
        vmvcAimStatDVPGUplinkTeamFailureFullDuplex,
        vmvcAimStatDVPGUplinkTeamFailurePercentage,
        vmvcAimStatDVPGUplinkTeamFailureSpeed,
        vmvcAimStatDVPGVCUUID
    }
    DESCRIPTION
        "The specified DV Port Group has had its Port Policy modified in VC.
         Enabled with Trap Enable Flag 0x1."
    ::= 165951

vmvcAimHostFTConfigChangeEvent OBJECT IDENTIFIER ::= { traps 165955 }
vmvcAimHostFTConfigChangeTrap TRAP-TYPE
    ENTERPRISE sysmgmt
    VARIABLES {
        vmvcAimStatServerName,
        vmvcAimStatHostVCName,
        vmvcAimStatHostDCName,
        vmvcAimStatHostDCIndex,
        vmvcAimStatHostClusterName,
        vmvcAimStatHostClusterId,
        vmvcAimStatHostName,
        vmvcAimStatHostID,
        vmvcAimStatHostFaultToleranceConf,
        vmvcAimStatHostFaultToleranceVersion,
        vmvcAimStatHostTotalFTPrimaryVM,
        vmvcAimStatHostPoweredOnFTPrimaryVM,
        vmvcAimStatHostTotalFTSecondaryVM,
        vmvcAimStatHostPoweredOnFTSecondaryVM,
        vmvcAimStatHostVCUUID
    }
    DESCRIPTION
        "A Host had its Fault Tolerance Configuration Changed.  All applicable
         attributes are within this varbind list.
         Enabled with Trap Enable Flag 0x1."
    ::= 165955

vmvcAimVMFTConfigChangeEvent OBJECT IDENTIFIER ::= { traps 165956 }
vmvcAimVMFTConfigChangeTrap TRAP-TYPE
    ENTERPRISE sysmgmt
    VARIABLES {
        vmvcAimStatServerName,
        vmvcAimStatVMVCName,
        vmvcAimStatVMIndex,
        vmvcAimStatVMName,
        vmvcAimStatVMHostName,
        vmvcAimStatVMHostID,
        vmvcAimStatVMFaultToleranceStatus,
        vmvcAimStatVMFTActivityState,
        vmvcAimStatVMFaultToleranceRole,
        vmvcAimStatVMFTSiblingIndex,
        vmvcAimStatVMFTSiblingHostIndex,
        vmvcAimStatVMFTSiblingHostName,
        vmvcAimStatVMFTSiblingHostUID,
        vmvcAimStatVMFTTotalSiblingCPU,
        vmvcAimStatVMFTTotalSiblingMemory,
        vmvcAimStatVMVCUUID
    }
    DESCRIPTION
        "A VM has had its Fault Tolerance Configuration Changed.  The specifics of this
         change are specified within the varbind list.
         Enabled with Trap Enable Flag 0x1."
    ::= 165956

vmvcAimVMFTFailoverEvent OBJECT IDENTIFIER ::= { traps 165957 }
vmvcAimVMFTFailoverTrap TRAP-TYPE
    ENTERPRISE sysmgmt
    VARIABLES {
        vmvcAimStatServerName,
        vmvcAimStatVMVCName,
        vmvcAimStatVMIndex,
        vmvcAimStatVMName,
        vmvcAimStatVMHostName,
        vmvcAimStatVMHostID,
        vmvcAimStatVMFaultToleranceStatus,
        vmvcAimStatVMFTActivityState,
        vmvcAimStatVMFaultToleranceRole,
        vmvcAimStatVMFTSiblingIndex,
        vmvcAimStatVMFTSiblingHostIndex,
        vmvcAimStatVMFTSiblingHostName,
        vmvcAimStatVMFTSiblingHostUID,
        vmvcAimStatVMFTTotalSiblingCPU,
        vmvcAimStatVMFTTotalSiblingMemory,
        vmvcAimStatVMVCUUID
    }
    DESCRIPTION
        "A Fault Tolerant VM has has failed over to its secondary VM.  Specifics of the NEW 
         primary VM are specified within the varbind list.
         Enabled with Trap Enable Flag 0x1."
    ::= 165957

vmvcAimVMVCConfigChangeEvent OBJECT IDENTIFIER ::= { traps 165958 }
vmvcAimVMVCConfigChangeTrap TRAP-TYPE
    ENTERPRISE sysmgmt
    VARIABLES {
        vmvcAimStatVMVCName,
        vmvcAimStatVMIndex,
        vmvcAimStatVMName,
        vmvcAimStatVMHostName,
        vmvcAimStatVMHostID,
        vmvcAimStatVMCPUSharesAssigned,
        vmvcAimStatVMMemorySharesAssigned,
        vmvcAimStatVMMemoryMin,
        vmvcAimStatVMMemoryMax,
        vmvcAimStatVMDatastore,
        vmvcAimStatVMNetwork,
        vmvcAimStatVMCPUCount,
        vmvcAimStatVMCPUConfiguredMin,
        vmvcAimStatVMCPUConfiguredMax,
        vmvcAimStatVMCPUShares,
        vmvcAimStatVMConfiguredMemory,
        vmvcAimStatVMMemorySize,
        vmvcAimStatVMCPUReservation,
        vmvcAimStatVMMemoryReservation,
        vmvcAimStatVMVCUUID
    }
    DESCRIPTION
        "The specified VM has had a configuration change within vCenter applied to it.  These
         changes are things like Memory Reservation, CPU Shares, etc.  This trap is a notification
         of this detected change.  Current values for the above attributes are sent.
         Enabled with Trap Enable Flag 0x1."
    ::= 165958

vmvcAimCustSpecNICAddedEvent OBJECT IDENTIFIER ::= { traps 165960 }
vmvcAimCustSpecNICAddedTrap TRAP-TYPE
    ENTERPRISE sysmgmt
    VARIABLES {
        vmvcAimStatCustomSpecNICUID,
        vmvcAimStatCustomSpecName,
        vmvcAimStatCustomSpecNICOrder,
        vmvcAimStatCustomSpecNICType,
        vmvcAimStatCustomSpecNICIPAddress,
        vmvcAimStatCustomSpecNICSubnetMask,
        vmvcAimStatCustomSpecNICGateway,
        vmvcAimStatCustomSpecNICAlternateGateway,
        vmvcAimStatCustomSpecNICDNS,
        vmvcAimStatCustomSpecNICAlternateDNS,
        vmvcAimStatCustomSpecNICPrimaryWINSServer,
        vmvcAimStatCustomSpecNICSecondaryWINSServer,
        vmvcAimStatCustomSpecNICVCName,
        vmvcAimStatCustomSpecUID,
        vmvcAimStatCustomSpecNICVCUUID
    }
    DESCRIPTION
        "A Customization Specification NIC Entry has been added.
         Enabled with Trap Enable Flag 0x1."
    ::= 165960

vmvcAimCustSpecNICRemovedEvent OBJECT IDENTIFIER ::= { traps 165961 }
vmvcAimCustSpecNICRemovedTrap TRAP-TYPE
    ENTERPRISE sysmgmt
    VARIABLES {
        vmvcAimStatCustomSpecName,
        vmvcAimStatCustomSpecNICOrder,
        vmvcAimStatCustomSpecNICVCName,
        vmvcAimStatCustomSpecUID,
        vmvcAimStatCustomSpecNICVCUUID
    }
    DESCRIPTION
        "A Customization Specification NIC Entry has been removed.
         Enabled with Trap Enable Flag 0x1."
    ::= 165961

vmvcAimResourcePoolVCConfigChangeEvent OBJECT IDENTIFIER ::= { traps 165962 }
vmvcAimResourcePoolVCConfigChangeTrap TRAP-TYPE
    ENTERPRISE sysmgmt
    VARIABLES {
        vmvcAimStatResourcePoolVCName,
        vmvcAimStatResourcePoolIndex,
        vmvcAimStatResourcePoolName,
        vmvcAimStatResourcePoolCPUExpandReservation,
        vmvcAimStatResourcePoolCPUMax,
        vmvcAimStatResourcePoolCPUMin,
        vmvcAimStatResourcePoolCPUShares,
        vmvcAimStatResourcePoolMemExpandReservation,
        vmvcAimStatResourcePoolMemMax,
        vmvcAimStatResourcePoolMemMin,
        vmvcAimStatResourcePoolMemShares,
        vmvcAimStatResourcePoolCfgChgVersion,
        vmvcAimStatResourcePoolCPUReserveUsed,
        vmvcAimStatResourcePoolCPUReserveUsedForVM,
        vmvcAimStatResourcePoolCPUUnReserveForPool,
        vmvcAimStatResourcePoolCPUUnReserveForVM,
        vmvcAimStatResourcePoolMemReserveUsed,
        vmvcAimStatResourcePoolMemReserveUsedForVM,
        vmvcAimStatResourcePoolMemUnReserveForPool,
        vmvcAimStatResourcePoolMemUnReserveForVM,
        vmvcAimStatResourcePoolType,
        vmvcAimStatResourcePoolVCUUID
    }
    DESCRIPTION
        "The specified ResourcePool has had a configuration change within vCenter applied to it.
         These changes are things like Memory Reservation, CPU Shares, etc.  This trap is a
         notification of this detected change.  Current values for the above attributes are sent.
         Enabled with Trap Enable Flag 0x1."
    ::= 165962

vmvcAimVAppAddedEvent OBJECT IDENTIFIER ::= { traps 165963 }
vmvcAimVAppAddedTrap TRAP-TYPE
    ENTERPRISE sysmgmt
    VARIABLES {
        vmvcAimStatResourcePoolIndex,
        vmvcAimStatResourcePoolVCName,
        vmvcAimStatResourcePoolType,
        vmvcAimStatResourcePoolName,
        vmvcAimStatResourcePoolIndexPath,
        vmvcAimStatResourcePoolParentPath,
        vmvcAimStatResourcePoolComputeResourceName,
        vmvcAimStatResourcePoolComputeResourcePath,
        vmvcAimStatResourcePoolCPUExpandReservation,
        vmvcAimStatResourcePoolMemExpandReservation,
        vmvcAimStatResourcePoolCPUShares,
        vmvcAimStatResourcePoolMemShares,
        vmvcAimStatResourcePoolCfgChgVersion,
        vmvcAimStatResourcePoolStatus,
        vmvcAimStatResourcePoolCPUUnReserveForPool,
        vmvcAimStatResourcePoolCPUUnReserveForVM,
        vmvcAimStatResourcePoolCPUReserveUsed,
        vmvcAimStatResourcePoolCPUReserveUsedForVM,
        vmvcAimStatResourcePoolMemUnReserveForPool,
        vmvcAimStatResourcePoolMemUnReserveForVM,
        vmvcAimStatResourcePoolMemReserveUsed,
        vmvcAimStatResourcePoolMemReserveUsedForVM,
        vmvcAimStatResourcePoolCPUMax,
        vmvcAimStatResourcePoolCPUMin,
        vmvcAimStatResourcePoolCPUMaxUsage,
        vmvcAimStatResourcePoolCPUOverAllUsage,
        vmvcAimStatResourcePoolMemMax,
        vmvcAimStatResourcePoolMemMin,
        vmvcAimStatResourcePoolMemMaxUsage,
        vmvcAimStatResourcePoolMemOverAllUsage,
        vmvcAimStatResourcePoolMonitor,
        vmvcAimStatResourcePoolAlert,
        vmvcAimStatResourcePoolParentId,
        vmvcAimStatResourcePoolComputeResourceId,
        vmvcAimStatResourcePoolState,
        vmvcAimStatVAppIndex,
        vmvcAimStatVAppName,
        vmvcAimStatVAppVCName,
        vmvcAimStatVAppParentVApp,
        vmvcAimStatVAppOperatingStatus,
        vmvcAimStatVAppInstallBootRequired,
        vmvcAimStatVAppIpAllocationPolicy,
        vmvcAimStatVAppSupportedIpProtocol,
        vmvcAimStatVAppIpProtocol,
        vmvcAimStatVAppProductAppURL,
        vmvcAimStatVAppProductVersion,
        vmvcAimStatVAppProductFullVersion,
        vmvcAimStatVAppProductName,
        vmvcAimStatVAppProductURL,
        vmvcAimStatVAppProductVendor,
        vmvcAimStatVAppProductVendorURL,
        vmvcAimStatVAppStartAction,
        vmvcAimStatVAppStartOrder,
        vmvcAimStatVAppStopAction,
        vmvcAimStatVAppVCUUID,
        vmvcAimStatResourcePoolVCUUID
    }
    DESCRIPTION
        "The specified vApp has been added.  This trap will be sent when a vApp is created, instead of
         the ResourcePoolAddedTrap, and will have all attributes from both the ResourcePool Table and the
         vApp Table specified.
         Enabled with Trap Enable Flag 0x1."
    ::= 165963

vmvcAimVAppRemovedEvent OBJECT IDENTIFIER ::= { traps 165964 }
vmvcAimVAppRemovedTrap TRAP-TYPE
    ENTERPRISE sysmgmt
    VARIABLES {
        vmvcAimStatResourcePoolIndex,
        vmvcAimStatResourcePoolVCName,
        vmvcAimStatResourcePoolType,
        vmvcAimStatResourcePoolName,
        vmvcAimStatResourcePoolIndexPath,
        vmvcAimStatResourcePoolParentId,
        vmvcAimStatVAppIndex,
        vmvcAimStatVAppName,
        vmvcAimStatVAppVCName,
        vmvcAimStatVAppParentVApp,
        vmvcAimStatVAppVCUUID,
        vmvcAimStatResourcePoolVCUUID
    }
    DESCRIPTION
        "The specified vApp has been removed.  This trap will be sent when a vApp is destroyed, instead of
         the ResourcePoolRemovedTrap, and will have the appropriate attributes from both the ResourcePool Table
         and the vApp Table specified.
         Enabled with Trap Enable Flag 0x1."
    ::= 165964

vmvcAimVAppVCConfigChangeEvent OBJECT IDENTIFIER ::= { traps 165965 }
vmvcAimVAppVCConfigChangeTrap TRAP-TYPE
    ENTERPRISE sysmgmt
    VARIABLES {
        vmvcAimStatResourcePoolIndex,
        vmvcAimStatResourcePoolVCName,
        vmvcAimStatResourcePoolType,
        vmvcAimStatVAppIndex,
        vmvcAimStatVAppName,
        vmvcAimStatVAppVCName,
        vmvcAimStatVAppParentVApp,
        vmvcAimStatVAppOperatingStatus,
        vmvcAimStatVAppInstallBootRequired,
        vmvcAimStatVAppIpAllocationPolicy,
        vmvcAimStatVAppSupportedIpProtocol,
        vmvcAimStatVAppIpProtocol,
        vmvcAimStatVAppProductAppURL,
        vmvcAimStatVAppProductVersion,
        vmvcAimStatVAppProductFullVersion,
        vmvcAimStatVAppProductName,
        vmvcAimStatVAppProductURL,
        vmvcAimStatVAppProductVendor,
        vmvcAimStatVAppProductVendorURL,
        vmvcAimStatVAppStartAction,
        vmvcAimStatVAppStartOrder,
        vmvcAimStatVAppStopAction,
        vmvcAimStatVAppVCUUID,
        vmvcAimStatResourcePoolVCUUID
    }
    DESCRIPTION
        "The specified vApp has had a configuration change within vCenter applied to it.  This trap is 
         a notification of this detected change.  Please note that this trap is only sent when vApp-specific
         attributes have been changed.  Current values for the above attributes are sent.
         Enabled with Trap Enable Flag 0x1."
    ::= 165965

vmvcAimVMAddedTovAppEvent OBJECT IDENTIFIER ::= { traps 165966 }
vmvcAimVMAddedTovAppTrap TRAP-TYPE
    ENTERPRISE sysmgmt
    VARIABLES {
        vmvcAimStatVMvAppIndex,
        vmvcAimStatVMvAppName,
        vmvcAimStatVMvAppVCName,
        vmvcAimStatVMvAppOptions,
        vmvcAimStatVMvAppParentVApp,
        vmvcAimStatVMvAppInstallBootRequired,
        vmvcAimStatVMvAppInstallBootStopDelay,
        vmvcAimStatVMvAppIpAllocationPolicy,
        vmvcAimStatVMvAppSupportedIpProtocol,
        vmvcAimStatVMvAppIpProtocol,
        vmvcAimStatVMvAppProductAppURL,
        vmvcAimStatVMvAppProductVersion,
        vmvcAimStatVMvAppProductFullVersion,
        vmvcAimStatVMvAppProductName,
        vmvcAimStatVMvAppProductURL,
        vmvcAimStatVMvAppProductVendor,
        vmvcAimStatVMvAppProductVendorURL,
        vmvcAimStatVMvAppStartAction,
        vmvcAimStatVMvAppStartOrder,
        vmvcAimStatVMvAppStartDelay,
        vmvcAimStatVMvAppStartWaitForGuest,
        vmvcAimStatVMvAppStopAction,
        vmvcAimStatVMvAppStopDelay,
        vmvcAimStatVMvAppVCUUID
    }
    DESCRIPTION
        "The specified VM has been added to a vApp.  The specifics of the vApp information for this VM
         are specified in the delivered attributes.
         Enabled with Trap Enable Flag 0x1."
    ::= 165966

vmvcAimVMRemovedFromvAppEvent OBJECT IDENTIFIER ::= { traps 165967 }
vmvcAimVMRemovedFromvAppTrap TRAP-TYPE
    ENTERPRISE sysmgmt
    VARIABLES {
        vmvcAimStatVMvAppIndex,
        vmvcAimStatVMvAppName,
        vmvcAimStatVMvAppVCName,
        vmvcAimStatVMvAppParentVApp,
        vmvcAimStatVMvAppVCUUID
    }
    DESCRIPTION
        "The specified VM has been removed from its parent vApp.  The vApp it has been removed from is a
         delivered attribute.
         Enabled with Trap Enable Flag 0x1."
    ::= 165967

vmvcAimVMvAppVCConfigChangeEvent OBJECT IDENTIFIER ::= { traps 165968 }
vmvcAimVMvAppVCConfigChangeTrap TRAP-TYPE
    ENTERPRISE sysmgmt
    VARIABLES {
        vmvcAimStatVMvAppIndex,
        vmvcAimStatVMvAppName,
        vmvcAimStatVMvAppVCName,
        vmvcAimStatVMvAppOptions,
        vmvcAimStatVMvAppParentVApp,
        vmvcAimStatVMvAppInstallBootRequired,
        vmvcAimStatVMvAppInstallBootStopDelay,
        vmvcAimStatVMvAppIpAllocationPolicy,
        vmvcAimStatVMvAppSupportedIpProtocol,
        vmvcAimStatVMvAppIpProtocol,
        vmvcAimStatVMvAppProductAppURL,
        vmvcAimStatVMvAppProductVersion,
        vmvcAimStatVMvAppProductFullVersion,
        vmvcAimStatVMvAppProductName,
        vmvcAimStatVMvAppProductURL,
        vmvcAimStatVMvAppProductVendor,
        vmvcAimStatVMvAppProductVendorURL,
        vmvcAimStatVMvAppStartAction,
        vmvcAimStatVMvAppStartOrder,
        vmvcAimStatVMvAppStartDelay,
        vmvcAimStatVMvAppStartWaitForGuest,
        vmvcAimStatVMvAppStopAction,
        vmvcAimStatVMvAppStopDelay,
        vmvcAimStatVMvAppVCUUID
    }
    DESCRIPTION
        "The specified VM has had a vApp configuration change within vCenter applied to it.  This 
         trap is a notification of this detected change.  Current values for the above attributes are sent.
         Enabled with Trap Enable Flag 0x1."
    ::= 165968

vmvcAimNetFolderAddedEvent OBJECT IDENTIFIER ::= { traps 165970 }
vmvcAimNetFolderAddedTrap TRAP-TYPE
    ENTERPRISE sysmgmt
    VARIABLES {
        vmvcAimStatNetworkFolderIndex,
        vmvcAimStatNetworkFolderName,
        vmvcAimStatNetworkFolderVCName,
        vmvcAimStatNetworkFolderParentId,
        vmvcAimStatNetworkFolderParentPath,
        vmvcAimStatNetworkFolderVCUUID
    }
    DESCRIPTION
        "A new Network Folder has been added to VC.
         Enabled with Trap Enable Flag 0x1."
    ::= 165970

vmvcAimNetFolderRemovedEvent OBJECT IDENTIFIER ::= { traps 165971 }
vmvcAimNetFolderRemovedTrap TRAP-TYPE
    ENTERPRISE sysmgmt
    VARIABLES {
        vmvcAimStatNetworkFolderIndex,
        vmvcAimStatNetworkFolderName,
        vmvcAimStatNetworkFolderVCName,
        vmvcAimStatNetworkFolderParentId,
        vmvcAimStatNetworkFolderParentPath,
        vmvcAimStatNetworkFolderVCUUID
    }
    DESCRIPTION
        "The specified Network Folder has been removed from VC.
         Enabled with Trap Enable Flag 0x1."
    ::= 165971

vmvcAimNetFolderConfigChangeEvent OBJECT IDENTIFIER ::= { traps 165972 }
vmvcAimNetFolderConfigChangeTrap TRAP-TYPE
    ENTERPRISE sysmgmt
    VARIABLES {
        vmvcAimStatNetworkFolderIndex,
        vmvcAimStatNetworkFolderName,
        vmvcAimStatNetworkFolderVCName,
        vmvcAimStatNetworkFolderParentId,
        vmvcAimStatNetworkFolderParentPath,
        vmvcAimStatNetworkFolderVCUUID
    }
    DESCRIPTION
        "The configuration information for the specified Network Folder has been modified.
         Enabled with Trap Enable Flag 0x1."
    ::= 165972

END
