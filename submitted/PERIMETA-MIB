PERIMETA-MIB DEFINITIONS ::= BEGIN

IMPORTS
        MODULE-IDENTITY, OBJECT-TYPE, Unsigned32
                                            FROM SNMPv2-SMI
        DisplayString
                                            FROM SNMPv2-TC
        CounterBasedGauge64
                                            FROM HCNUM-TC;

  perimeta MODULE-IDENTITY
        LAST-UPDATED "201712180000Z"
        ORGANIZATION "Metaswitch"
        CONTACT-INFO
          "Metaswitch
           100 Church Street
           Enfield
           EN2 6BQ
           United Kingdom
           Tel: +44 20 8366 1177"
        DESCRIPTION  "This MIB module defines the perimeta module
                      and children object types, including tables
                      for global statistics and per-object
                      statistics."

        REVISION      "201712180000Z" -- 18 Dec 2017
        DESCRIPTION   "New statistics for Perimeta V4.3.20"

        REVISION      "201711210000Z" -- 21 Nov 2017
        DESCRIPTION   "New statistics for Perimeta V4.3.00"

        REVISION      "201612010000Z" -- 01 Dec 2016
        DESCRIPTION   "Registration of new per-adjacency
                       per-method statistics table for V4.2."

        REVISION      "201504301200Z" -- 30 April 2015
        DESCRIPTION   "New statistics for Perimeta V3.8."

        REVISION      "201411131200Z" -- 13 Nov 2014
        DESCRIPTION   "New statistics for Perimeta V3.7 and a
                       couple of small syntax fixes."

        REVISION      "201401081200Z" -- 08 Jan 2014
        DESCRIPTION   "Per-account stats and Gauge stats for
                       Perimeta V3.6."

        REVISION      "201311271200Z" -- 27 Nov 2013
        DESCRIPTION   "New statistics for Perimeta V3.5."

        REVISION      "201305290854Z" -- 29 May 2013
        DESCRIPTION   "Registration of new global statistics and
                       the new per-adjacency statistics table for
                       V3.4."

        REVISION      "201107220000Z" -- 22 July 2011
        DESCRIPTION   "Registration of initial global statistics
                       and the Perimeta Info table."

        ::= { dataConnection 8 }

-- /**********************************************************/
-- /* The object identifier subtree for the Perimeta MIBs.   */
-- /**********************************************************/

memberBody      OBJECT IDENTIFIER ::= { iso 2 }
gb              OBJECT IDENTIFIER ::= { memberBody 826 }
gbNational      OBJECT IDENTIFIER ::= { gb 0 }
gbNatCompany    OBJECT IDENTIFIER ::= { gbNational 1 }
dataConnection  OBJECT IDENTIFIER ::= { gbNatCompany 1578918 }

-- /**********************************************************/
-- /* MIB tables.                                            */
-- /**********************************************************/

-- /**********************************************************/
-- /* MIB Info Section                                       */
-- /**********************************************************/

  perimetaInfo   OBJECT-TYPE
    SYNTAX SEQUENCE OF PerimetaInfo
    MAX-ACCESS not-accessible
    STATUS current
    DESCRIPTION "This table holds general information about 'Perimeta'.
    It is neither creatable nor deletable."
    ::= { perimeta 1 }

  PerimetaInfo ::= SEQUENCE
  {
    infoPerimetaName DisplayString,
    infoVersion DisplayString,
    infoPlatform DisplayString,
    infoEquipmentIdentifier DisplayString
  }

  infoPerimetaName OBJECT-TYPE
    SYNTAX       DisplayString (SIZE(1..32))
    MAX-ACCESS   not-accessible
    STATUS       current
    DESCRIPTION  "Corresponds to the name of the Perimeta.
    This is an index field."
    ::= { perimetaInfo 1 }

  infoVersion OBJECT-TYPE
    SYNTAX       DisplayString
    MAX-ACCESS   read-only
    STATUS       current
    DESCRIPTION  "Perimeta MIB Version"
    ::= { perimetaInfo 2 }

  infoPlatform OBJECT-TYPE
    SYNTAX       DisplayString (SIZE(1..32))
    MAX-ACCESS   read-only
    STATUS       current
    DESCRIPTION  "Perimeta Hardware Platform"
    ::= { perimetaInfo 3 }

  infoEquipmentIdentifier OBJECT-TYPE
    SYNTAX       DisplayString (SIZE(1..64))
    MAX-ACCESS   read-only
    STATUS       current
    DESCRIPTION  "Unique identifier for this Perimeta instance"
    ::= { perimetaInfo 4 }

-- /**********************************************************/
-- /* MIB table for 'Perimeta Global Statistics'             */
-- /*                                                        */
-- /* These statistics may be cached by Perimeta, and may be */
-- /* up to five minutes old when retrieved.  The time that  */
-- /* they were retrieved is given by                        */
-- /* globalStatsCollectionTime.                             */
-- /*                                                        */
-- /* See "Statistics monitored by Perimeta" in the          */
-- /* "Operations And Maintenance Guide" for more            */
-- /* information.                                           */
-- /**********************************************************/

  perimetaGlobalStatsTable OBJECT-TYPE
    SYNTAX       SEQUENCE OF PerimetaGlobalStatsEntry
    MAX-ACCESS   not-accessible
    STATUS       current
    DESCRIPTION  "This table is a child of 'Perimeta'.
                  This table is neither creatable nor deletable."
    ::= { perimeta  2 }

  perimetaGlobalStatsEntry OBJECT-TYPE
    SYNTAX       PerimetaGlobalStatsEntry
    MAX-ACCESS   not-accessible
    STATUS       current
    DESCRIPTION  "An entry in the table of global statistics."
    INDEX  { globalStatsSummaryPeriod }
    ::= {  perimetaGlobalStatsTable  1  }

  PerimetaGlobalStatsEntry  ::=  SEQUENCE
  {
    globalStatsSummaryPeriod                      INTEGER,
    globalStatsCollectionTime                     Unsigned32,
    globalStatSIPMessagesRcvd                     CounterBasedGauge64,
    globalStatSIPMessagesSent                     CounterBasedGauge64,
    globalStatSIPInvitesRcvd                      CounterBasedGauge64,
    globalStatSIPInvitesSent                      CounterBasedGauge64,
    globalStatSIPByesRcvd                         CounterBasedGauge64,
    globalStatSIPByesSent                         CounterBasedGauge64,
    globalStatSIPCancelsRcvd                      CounterBasedGauge64,
    globalStatSIPCancelsSent                      CounterBasedGauge64,
    globalStatSIPRegistersRcvd                    CounterBasedGauge64,
    globalStatSIPRegistersSent                    CounterBasedGauge64,
    globalStatSIPSubscribesRcvd                   CounterBasedGauge64,
    globalStatSIPSubscribesSent                   CounterBasedGauge64,
    globalStatSIPCongestionQOldestPkt             CounterBasedGauge64,
    globalStatSIPCongestionQLevel                 CounterBasedGauge64,
    globalStatSIPCongestionQMaxPktDelay           CounterBasedGauge64,
    globalStatSIPCongestionQPktsDropped           CounterBasedGauge64,
    globalStatSIPCongestionQPktsAccepted          CounterBasedGauge64,
    globalStatSIP1XXResponsesSent                 CounterBasedGauge64,
    globalStatSIP1XXResponsesRcvd                 CounterBasedGauge64,
    globalStatSIP2XXResponsesSent                 CounterBasedGauge64,
    globalStatSIP2XXResponsesRcvd                 CounterBasedGauge64,
    globalStatSIP3XXResponsesSent                 CounterBasedGauge64,
    globalStatSIP3XXResponsesRcvd                 CounterBasedGauge64,
    globalStatSIP4XXResponsesSent                 CounterBasedGauge64,
    globalStatSIP4XXResponsesRcvd                 CounterBasedGauge64,
    globalStatSIP5XXResponsesSent                 CounterBasedGauge64,
    globalStatSIP5XXResponsesRcvd                 CounterBasedGauge64,
    globalStatSIP6XXResponsesSent                 CounterBasedGauge64,
    globalStatSIP6XXResponsesRcvd                 CounterBasedGauge64,
    globalStatRTPOctetsSentRate                   CounterBasedGauge64,
    globalStatRTPOctetsRcvdRate                   CounterBasedGauge64,
    globalStatRTPOctetsDiscardedPercent           CounterBasedGauge64,
    globalStatRTPPktsSentRate                     CounterBasedGauge64,
    globalStatRTPPktsReceivedRate                 CounterBasedGauge64,
    globalStatRTPPktsDiscardedPercent             CounterBasedGauge64,
    globalStatActiveSessions                      CounterBasedGauge64,
    globalStatPktsRcvd                            CounterBasedGauge64,
    globalStatPktsRcvdRate                        CounterBasedGauge64,
    globalStatSignalingPktsRcvd                   CounterBasedGauge64,
    globalStatSignalingPktsRcvdRate               CounterBasedGauge64,
    globalStatMediaPktsRcvd                       CounterBasedGauge64,
    globalStatMediaPktsRcvdRate                   CounterBasedGauge64,
    globalStatOtherPktsRcvd                       CounterBasedGauge64,
    globalStatOtherPktsRcvdRate                   CounterBasedGauge64,
    globalStatSignalingPktsSent                   CounterBasedGauge64,
    globalStatSignalingPktsSentRate               CounterBasedGauge64,
    globalStatSignalingPktsAccptd                 CounterBasedGauge64,
    globalStatSignalingPktsAccptdRate             CounterBasedGauge64,
    globalStatSignalingPktsDropped                CounterBasedGauge64,
    globalStatSignalingPktsDroppedRate            CounterBasedGauge64,
    globalStatPriority1SigPktsRcvd                CounterBasedGauge64,
    globalStatPriority1SigPktsRcvdRate            CounterBasedGauge64,
    globalStatPriority1SigPktsAccptd              CounterBasedGauge64,
    globalStatPriority1SigPktsAccptdRate          CounterBasedGauge64,
    globalStatPriority1SigPktsDropped             CounterBasedGauge64,
    globalStatPriority1SigPktsDroppedRate         CounterBasedGauge64,
    globalStatPriority2SigPktsRcvd                CounterBasedGauge64,
    globalStatPriority2SigPktsRcvdRate            CounterBasedGauge64,
    globalStatPriority2SigPktsAccptd              CounterBasedGauge64,
    globalStatPriority2SigPktsAccptdRate          CounterBasedGauge64,
    globalStatPriority2SigPktsDropped             CounterBasedGauge64,
    globalStatPriority2SigPktsDroppedRate         CounterBasedGauge64,
    globalStatPriority3SigPktsRcvd                CounterBasedGauge64,
    globalStatPriority3SigPktsRcvdRate            CounterBasedGauge64,
    globalStatPriority3SigPktsAccptd              CounterBasedGauge64,
    globalStatPriority3SigPktsAccptdRate          CounterBasedGauge64,
    globalStatPriority3SigPktsDropped             CounterBasedGauge64,
    globalStatPriority3SigPktsDroppedRate         CounterBasedGauge64,
    globalStatUnknownIPVersionSigPktsDropped      CounterBasedGauge64,
    globalStatUnknownIPVersionSigPktsDroppedRate  CounterBasedGauge64,
    globalStatBlacklistedSigPktsDropped           CounterBasedGauge64,
    globalStatBlacklistedSigPktsDroppedRate       CounterBasedGauge64,
    globalStatNoServicePortSigPktsDropped         CounterBasedGauge64,
    globalStatNoServicePortSigPktsDroppedRate     CounterBasedGauge64,
    globalStatFixedRateLimitSigPktsDropped        CounterBasedGauge64,
    globalStatFixedRateLimitSigPktsDroppedRate    CounterBasedGauge64,
    globalStatAdaptiveRateLimitSigPktsDropped     CounterBasedGauge64,
    globalStatAdaptiveRateLimitSigPktsDroppedRate CounterBasedGauge64,
    globalStatCongestedSigPktsDropped             CounterBasedGauge64,
    globalStatCongestedSigPktsDroppedRate         CounterBasedGauge64,
    globalStatBadICMPSigPktsDropped               CounterBasedGauge64,
    globalStatBadICMPSigPktsDroppedRate           CounterBasedGauge64,
    globalStatTCPSYNSigPktsDropped                CounterBasedGauge64,
    globalStatTCPSYNSigPktsDroppedRate            CounterBasedGauge64,
    globalStatCallSetupFailurePercent             CounterBasedGauge64,
    globalStatNumberAnalysisCallSetupFailPercent  CounterBasedGauge64,
    globalStatRoutingCallSetupFailurePercent      CounterBasedGauge64,
    globalStatCapacityControlCallStpFailrePrcnt   CounterBasedGauge64,
    globalStatActiveCalls                         CounterBasedGauge64,
    globalStatActivatingCalls                     CounterBasedGauge64,
    globalStatDeactivatingCalls                   CounterBasedGauge64,
    globalStatCallAttemptRate                     CounterBasedGauge64,
    globalStatCallAttemptFailureRate              CounterBasedGauge64,
    globalStatActiveCallFailuresPercent           CounterBasedGauge64,
    globalStatActiveEmergencyCalls                CounterBasedGauge64,
    globalStatActiveIPSecCalls                    CounterBasedGauge64,
    globalStatActiveSubscribers                   CounterBasedGauge64,
    globalStatRXCallSetupFailureRate              CounterBasedGauge64,
    globalStatRXRenegotiationAttemptRate          CounterBasedGauge64,
    globalStatRXRenegotiationFailureRate          CounterBasedGauge64,
    globalStatMalformedDiameterPktsRcvdRate       CounterBasedGauge64,
    globalStatDiameterPktsRcvdRate                CounterBasedGauge64,
    globalStatMalformedDiameterPktsRcvdPercent    CounterBasedGauge64,
    globalStatDiamAnswrMsgsUnknwnHopByHopIDRcvdRate CounterBasedGauge64,
    globalStatDiamPktsUnknwnCommandCodeRcvdRate   CounterBasedGauge64,
    globalStatDiamAnswrMsgsWthPrtclErrRcvdRate    CounterBasedGauge64,
    globalStatDiamTrnsprtReqsWthTransntFailrsRate CounterBasedGauge64,
    globalStatDiamTrnsprtReqsWthPermFailrsRate    CounterBasedGauge64,
    globalStatDiamTrnsprtReqsWthUnexpctdFailrRate CounterBasedGauge64,
    globalStatSIPSignalingRate                    CounterBasedGauge64,
    globalStatUsedSessionPerc                     CounterBasedGauge64,
    globalStatPriority4SigPktsRcvd                CounterBasedGauge64,
    globalStatPriority4SigPktsRcvdRate            CounterBasedGauge64,
    globalStatPriority4SigPktsAccptd              CounterBasedGauge64,
    globalStatPriority4SigPktsAccptdRate          CounterBasedGauge64,
    globalStatPriority4SigPktsDropped             CounterBasedGauge64,
    globalStatPriority4SigPktsDroppedRate         CounterBasedGauge64,
    globalStatPriority5SigPktsRcvd                CounterBasedGauge64,
    globalStatPriority5SigPktsRcvdRate            CounterBasedGauge64,
    globalStatPriority5SigPktsAccptd              CounterBasedGauge64,
    globalStatPriority5SigPktsAccptdRate          CounterBasedGauge64,
    globalStatPriority5SigPktsDropped             CounterBasedGauge64,
    globalStatPriority5SigPktsDroppedRate         CounterBasedGauge64,
    globalStatPriority6SigPktsRcvd                CounterBasedGauge64,
    globalStatPriority6SigPktsRcvdRate            CounterBasedGauge64,
    globalStatPriority6SigPktsAccptd              CounterBasedGauge64,
    globalStatPriority6SigPktsAccptdRate          CounterBasedGauge64,
    globalStatPriority6SigPktsDropped             CounterBasedGauge64,
    globalStatPriority6SigPktsDroppedRate         CounterBasedGauge64,
    globalStatPriority1SigBytesRcvd               CounterBasedGauge64,
    globalStatPriority1SigBytesRcvdRate           CounterBasedGauge64,
    globalStatPriority1SigBytesAccptd             CounterBasedGauge64,
    globalStatPriority1SigBytesAccptdRate         CounterBasedGauge64,
    globalStatPriority1SigBytesDropped            CounterBasedGauge64,
    globalStatPriority1SigBytesDroppedRate        CounterBasedGauge64,
    globalStatPriority2SigBytesRcvd               CounterBasedGauge64,
    globalStatPriority2SigBytesRcvdRate           CounterBasedGauge64,
    globalStatPriority2SigBytesAccptd             CounterBasedGauge64,
    globalStatPriority2SigBytesAccptdRate         CounterBasedGauge64,
    globalStatPriority2SigBytesDropped            CounterBasedGauge64,
    globalStatPriority2SigBytesDroppedRate        CounterBasedGauge64,
    globalStatPriority3SigBytesRcvd               CounterBasedGauge64,
    globalStatPriority3SigBytesRcvdRate           CounterBasedGauge64,
    globalStatPriority3SigBytesAccptd             CounterBasedGauge64,
    globalStatPriority3SigBytesAccptdRate         CounterBasedGauge64,
    globalStatPriority3SigBytesDropped            CounterBasedGauge64,
    globalStatPriority3SigBytesDroppedRate        CounterBasedGauge64,
    globalStatPriority4SigBytesRcvd               CounterBasedGauge64,
    globalStatPriority4SigBytesRcvdRate           CounterBasedGauge64,
    globalStatPriority4SigBytesAccptd             CounterBasedGauge64,
    globalStatPriority4SigBytesAccptdRate         CounterBasedGauge64,
    globalStatPriority4SigBytesDropped            CounterBasedGauge64,
    globalStatPriority4SigBytesDroppedRate        CounterBasedGauge64,
    globalStatPriority5SigBytesRcvd               CounterBasedGauge64,
    globalStatPriority5SigBytesRcvdRate           CounterBasedGauge64,
    globalStatPriority5SigBytesAccptd             CounterBasedGauge64,
    globalStatPriority5SigBytesAccptdRate         CounterBasedGauge64,
    globalStatPriority5SigBytesDropped            CounterBasedGauge64,
    globalStatPriority5SigBytesDroppedRate        CounterBasedGauge64,
    globalStatPriority6SigBytesRcvd               CounterBasedGauge64,
    globalStatPriority6SigBytesRcvdRate           CounterBasedGauge64,
    globalStatPriority6SigBytesAccptd             CounterBasedGauge64,
    globalStatPriority6SigBytesAccptdRate         CounterBasedGauge64,
    globalStatPriority6SigBytesDropped            CounterBasedGauge64,
    globalStatPriority6SigBytesDroppedRate        CounterBasedGauge64,
    globalStatActiveSrtpIwCalls                   CounterBasedGauge64,
    globalStatActiveEmergencySessions             CounterBasedGauge64,
    globalStatUnclassPktRate                      CounterBasedGauge64,
    globalStatCPUMaxSig                           CounterBasedGauge64,
    globalStatCPUMaxSipMsg                        CounterBasedGauge64,
    globalStatCPUMaxCore                          CounterBasedGauge64,
    globalStatFreeMem                             CounterBasedGauge64,
    globalStatMediaPktSentRate                    CounterBasedGauge64,
    globalStatIncomingQueueErr                    CounterBasedGauge64,
    globalStatPktSentRate                         CounterBasedGauge64,
    globalStatUsedCapacityPerc                    CounterBasedGauge64,
    globalStatsOverallCapacityPerc                CounterBasedGauge64,
    globalStatTotalIPsecCallsMade                 CounterBasedGauge64,
    globalStatSRTPIWSessions                      CounterBasedGauge64,
    globalStatActiveCallsTranscTrig               CounterBasedGauge64,
    globalStatActiveCallsTranscUsed               CounterBasedGauge64,
    globalStatCallsTriggeredTransc                CounterBasedGauge64,
    globalStatCallsUsedTransc                     CounterBasedGauge64,
    globalStatActiveH323Calls                     CounterBasedGauge64,
    globalStatTCPMediaPktsRcvdCount               CounterBasedGauge64,
    globalStatTCPMediaPktsRcvdRate                CounterBasedGauge64,
    globalStatTCPMediaBytesRcvdCount              CounterBasedGauge64,
    globalStatTCPMediaRcvBandWidth                CounterBasedGauge64,
    globalStatTCPMediaPktsFwdCount                CounterBasedGauge64,
    globalStatTCPMediaPktsFwdRate                 CounterBasedGauge64,
    globalStatTCPMediaBytesFwdCount               CounterBasedGauge64,
    globalStatTCPMediaFwdBandWidth                CounterBasedGauge64,
    globalStatTCPMedPktsDropCount                 CounterBasedGauge64,
    globalStatTCPMediaDropRate                    CounterBasedGauge64,
    globalStatActiveSubscriptions                 CounterBasedGauge64,
    globalStatMSRPSessions                        CounterBasedGauge64,
    globalStatTCPSessions                         CounterBasedGauge64,
    globalStatInbandDtmfCalls                     CounterBasedGauge64,
    globalStatUsedAdvancedCapacityPerc            CounterBasedGauge64,
    globalStatDspPktsRcvd                         CounterBasedGauge64,
    globalStatDspPktsRcvdRate                     CounterBasedGauge64,
    globalStatDspOctetsRcvd                       CounterBasedGauge64,
    globalStatDspOctetsRcvdRate                   CounterBasedGauge64,
    globalStatDspPcmForwarded                     CounterBasedGauge64,
    globalStatDspPcmForwardRate                   CounterBasedGauge64,
    globalStatDspPcmRcvd                          CounterBasedGauge64,
    globalStatDspPcmRcvdRate                      CounterBasedGauge64,
    globalStatDspPktsSent                         CounterBasedGauge64,
    globalStatDspPktsSentRate                     CounterBasedGauge64,
    globalStatDspOctetsSent                       CounterBasedGauge64,
    globalStatDspOctetsSentRate                   CounterBasedGauge64,
    globalStatDspRxUnexpCodec                     CounterBasedGauge64,
    globalStatDspRxUnexpPtype                     CounterBasedGauge64,
    globalStatDspRxIntFails                       CounterBasedGauge64,
    globalStatDspRxInvalLen                       CounterBasedGauge64,
    globalStatDspRxMisordered                     CounterBasedGauge64,
    globalStatDspRxSeqLost                        CounterBasedGauge64,
    globalStatDspUnderruns                        CounterBasedGauge64,
    globalStatDspOverruns                         CounterBasedGauge64,
    globalStatDspRxIntBuffErrs                    CounterBasedGauge64,
    globalStatDspTxInvalid                        CounterBasedGauge64,
    globalStatDspTxGaps                           CounterBasedGauge64,
    globalStatDspTxNoRtp                          CounterBasedGauge64,
    globalStatDspChecksumFails                    CounterBasedGauge64,
    globalStatDspRxMipsDrops                      CounterBasedGauge64,
    globalStatDspTxMipsDrops                      CounterBasedGauge64,
    globalStatDspInbandTones                      CounterBasedGauge64,
    globalStatDspRxTones                          CounterBasedGauge64,
    globalStatDspRxUnsupTones                     CounterBasedGauge64,
    globalStatDspTxTones                          CounterBasedGauge64,
    globalStatDspMaxPdv                           CounterBasedGauge64,
    globalStatDspBoardTemp                        CounterBasedGauge64,
    globalStatDspCpuUsage                         CounterBasedGauge64,
    globalStatDspNumFlowpairs                     CounterBasedGauge64,
    globalStatDspNumInbandFlowpairs               CounterBasedGauge64,
    globalStatDspRtpPktsDropped                   CounterBasedGauge64,
    globalStatDspMaxAllocLatency                  CounterBasedGauge64,
    globalStatDspMaxModifyLatency                 CounterBasedGauge64,
    globalStatDspMaxDeleteLatency                 CounterBasedGauge64,
    globalStatDspMaxStatsLatency                  CounterBasedGauge64,
    globalStatDspAvgAllocLatency                  CounterBasedGauge64,
    globalStatDspAvgModifyLatency                 CounterBasedGauge64,
    globalStatDspAvgDeleteLatency                 CounterBasedGauge64,
    globalStatDspAvgStatsLatency                  CounterBasedGauge64,
    globalStatCodecActiveTranscPCMU               CounterBasedGauge64,
    globalStatCodecActiveTranscPCMA               CounterBasedGauge64,
    globalStatCodecActiveTranscG729               CounterBasedGauge64,
    globalStatCodecActiveTranscG722               CounterBasedGauge64,
    globalStatCodecActiveTranscSILK8              CounterBasedGauge64,
    globalStatCodecActiveTranscAMR                CounterBasedGauge64,
    globalStatCodecActiveTranscAMRWB              CounterBasedGauge64,
    globalStatActiveT38FaxTranscSessions          CounterBasedGauge64,
    globalStatDspNumFaxFlowpairs                  CounterBasedGauge64,
    globalStatActiveCallsFaxTranscUsed            CounterBasedGauge64,
    globalStatTotalFaxToneFlowpairs               CounterBasedGauge64,
    globalStatSIPCongestionInvDropCnt             CounterBasedGauge64,
    globalStatSIPCongestionSubDropCnt             CounterBasedGauge64,
    globalStatSIPCongestionInvDropRate            CounterBasedGauge64,
    globalStatSIPCongestionSubDropRate            CounterBasedGauge64,
    globalStatUndersizedDropped                   CounterBasedGauge64,
    globalStatSigDisUndersizeRate                 CounterBasedGauge64,
    globalStatESRVCCAnchoredCalls                 CounterBasedGauge64,
    globalStatESRVCCTransfersOK                   CounterBasedGauge64,
    globalStatESRVCCTransfersFailed               CounterBasedGauge64,
    globalStatESRVCCCurSubscribers                CounterBasedGauge64,
    globalStatESRVCCNumRejects                    CounterBasedGauge64,
    globalStatCodecActiveTranscG723               CounterBasedGauge64,
    globalStatInbandInjectCount                   CounterBasedGauge64,
    globalStatActiveMSRPCalls                     CounterBasedGauge64,
    globalStatActiveMSRPSIWCalls                  CounterBasedGauge64,
    globalStatActiveMSRPSPtCalls                  CounterBasedGauge64,
    globalStatMSRPSIWSessRate                     CounterBasedGauge64,
    globalStatMSRPSPtSessRate                     CounterBasedGauge64,
    globalStatCodecActiveTranscG72616             CounterBasedGauge64,
    globalStatCodecActiveTranscG72624             CounterBasedGauge64,
    globalStatCodecActiveTranscG72632             CounterBasedGauge64,
    globalStatCodecActiveTranscG72640             CounterBasedGauge64,
    globalStatCodecActiveTranscG729AB             CounterBasedGauge64,
    globalStatAllocatedMediaSessions              CounterBasedGauge64,
    globalStatCoupledMediaSessions                CounterBasedGauge64,
    globalStatTotalInbandDtmfFlowpairs            CounterBasedGauge64,
    globalStatTotalAdvancedMRUUsage               CounterBasedGauge64,
    globalStatDSPPCIE8120Utilization              CounterBasedGauge64,
    globalStatTcCodecFailures                     CounterBasedGauge64,
    globalStatTotalH323Calls                      CounterBasedGauge64,
    globalStatTotalAudioTranscCalls               CounterBasedGauge64,
    globalStatRPG1B1RcvdCompression               CounterBasedGauge64,
    globalStatRPG1B1TransCompression              CounterBasedGauge64,
    globalStatRPG2B1RcvdCompression               CounterBasedGauge64,
    globalStatRPG2B1TransCompression              CounterBasedGauge64,
    globalStatRPG3B1RcvdCompression               CounterBasedGauge64,
    globalStatRPG3B1TransCompression              CounterBasedGauge64,
    globalStatRPG4B1RcvdCompression               CounterBasedGauge64,
    globalStatRPG4B1TransCompression              CounterBasedGauge64,
    globalStatRPG5B1RcvdCompression               CounterBasedGauge64,
    globalStatRPG5B1TransCompression              CounterBasedGauge64,
    globalStatRPG6B1RcvdCompression               CounterBasedGauge64,
    globalStatRPG6B1TransCompression              CounterBasedGauge64,
    globalStatRPG7B1RcvdCompression               CounterBasedGauge64,
    globalStatRPG7B1TransCompression              CounterBasedGauge64,
    globalStatRPG8B1RcvdCompression               CounterBasedGauge64,
    globalStatRPG8B1TransCompression              CounterBasedGauge64,
    globalStatIBG1MB1RcvdCompression              CounterBasedGauge64,
    globalStatIBG1MB1TransCompression             CounterBasedGauge64,
    globalStatIBG2MB1RcvdCompression              CounterBasedGauge64,
    globalStatIBG2MB1TransCompression             CounterBasedGauge64,
    globalStatIBG1B1RcvdCompression               CounterBasedGauge64,
    globalStatIBG1B1TransCompression              CounterBasedGauge64,
    globalStatIBG2B1RcvdCompression               CounterBasedGauge64,
    globalStatIBG2B1TransCompression              CounterBasedGauge64,
    globalStatIPG1B1RcvdCompression               CounterBasedGauge64,
    globalStatIPG1B1TransCompression              CounterBasedGauge64,
    globalStatIFXG1B1RcvdCompression              CounterBasedGauge64,
    globalStatIFXG1B1TransCompression             CounterBasedGauge64,
    globalStatIFXG2B1RcvdCompression              CounterBasedGauge64,
    globalStatIFXG2B1TransCompression             CounterBasedGauge64,
    globalStatRPXG1B1RcvdCompression              CounterBasedGauge64,
    globalStatRPXG1B1TransCompression             CounterBasedGauge64,
    globalStatRPXG2B1RcvdCompression              CounterBasedGauge64,
    globalStatRPXG2B1TransCompression             CounterBasedGauge64,
    globalStatRPXG3B1RcvdCompression              CounterBasedGauge64,
    globalStatRPXG3B1TransCompression             CounterBasedGauge64,
    globalStatRPXG4B1RcvdCompression              CounterBasedGauge64,
    globalStatRPXG4B1TransCompression             CounterBasedGauge64,
    globalStatRPG1B2RcvdCompression               CounterBasedGauge64,
    globalStatRPG1B2TransCompression              CounterBasedGauge64,
    globalStatRPG2B2RcvdCompression               CounterBasedGauge64,
    globalStatRPG2B2TransCompression              CounterBasedGauge64,
    globalStatRPG3B2RcvdCompression               CounterBasedGauge64,
    globalStatRPG3B2TransCompression              CounterBasedGauge64,
    globalStatRPG4B2RcvdCompression               CounterBasedGauge64,
    globalStatRPG4B2TransCompression              CounterBasedGauge64,
    globalStatRPG5B2RcvdCompression               CounterBasedGauge64,
    globalStatRPG5B2TransCompression              CounterBasedGauge64,
    globalStatRPG6B2RcvdCompression               CounterBasedGauge64,
    globalStatRPG6B2TransCompression              CounterBasedGauge64,
    globalStatRPG7B2RcvdCompression               CounterBasedGauge64,
    globalStatRPG7B2TransCompression              CounterBasedGauge64,
    globalStatRPG8B2RcvdCompression               CounterBasedGauge64,
    globalStatRPG8B2TransCompression              CounterBasedGauge64,
    globalStatIBG1MB2RcvdCompression              CounterBasedGauge64,
    globalStatIBG1MB2TransCompression             CounterBasedGauge64,
    globalStatIBG2MB2RcvdCompression              CounterBasedGauge64,
    globalStatIBG2MB2TransCompression             CounterBasedGauge64,
    globalStatIBG1B2RcvdCompression               CounterBasedGauge64,
    globalStatIBG1B2TransCompression              CounterBasedGauge64,
    globalStatIBG2B2RcvdCompression               CounterBasedGauge64,
    globalStatIBG2B2TransCompression              CounterBasedGauge64,
    globalStatIPG1B2RcvdCompression               CounterBasedGauge64,
    globalStatIPG1B2TransCompression              CounterBasedGauge64,
    globalStatIFXG1B2RcvdCompression              CounterBasedGauge64,
    globalStatIFXG1B2TransCompression             CounterBasedGauge64,
    globalStatIFXG2B2RcvdCompression              CounterBasedGauge64,
    globalStatIFXG2B2TransCompression             CounterBasedGauge64,
    globalStatRPXG1B2RcvdCompression              CounterBasedGauge64,
    globalStatRPXG1B2TransCompression             CounterBasedGauge64,
    globalStatRPXG2B2RcvdCompression              CounterBasedGauge64,
    globalStatRPXG2B2TransCompression             CounterBasedGauge64,
    globalStatRPXG3B2RcvdCompression              CounterBasedGauge64,
    globalStatRPXG3B2TransCompression             CounterBasedGauge64,
    globalStatRPXG4B2RcvdCompression              CounterBasedGauge64,
    globalStatRPXG4B2TransCompression             CounterBasedGauge64,
    globalStatSigH248RequestsSent                 CounterBasedGauge64,
    globalStatSigH248RequestsRcvd                 CounterBasedGauge64,
    globalStatSigH248RepliesSent                  CounterBasedGauge64,
    globalStatSigH248RepliesRcvd                  CounterBasedGauge64,
    globalStatSigH248RequestsFailed               CounterBasedGauge64,
    globalStatSigH248RequestsRetried              CounterBasedGauge64,
    globalStatSigH248RepliesRetried               CounterBasedGauge64,
    globalStatMedH248RequestsSent                 CounterBasedGauge64,
    globalStatMedH248RequestsRcvd                 CounterBasedGauge64,
    globalStatMedH248RepliesSent                  CounterBasedGauge64,
    globalStatMedH248RepliesRcvd                  CounterBasedGauge64,
    globalStatMedH248RequestsFailed               CounterBasedGauge64,
    globalStatMedH248RequestsRetried              CounterBasedGauge64,
    globalStatMedH248RepliesRetried               CounterBasedGauge64,
    globalStatExcessTcpConns                      CounterBasedGauge64,
    globalStatTlsHShakeQueued                     CounterBasedGauge64,
    globalStatTlsHShakeInit                       CounterBasedGauge64,
    globalStatTlsHShakeComp                       CounterBasedGauge64,
    globalStatTlsHShakeRej                        CounterBasedGauge64,
    globalStatTlsHShakeFail                       CounterBasedGauge64,
    globalStatTlsProtErrs                         CounterBasedGauge64,
    globalStatTlsRenegs                           CounterBasedGauge64,
    globalStatTlsSegDecoded                       CounterBasedGauge64,
    globalStatTlsBytesDecoded                     CounterBasedGauge64,
    globalStatTlsSegEncoded                       CounterBasedGauge64,
    globalStatTlsBytesEncoded                     CounterBasedGauge64,
    globalStatActiveTcpConns                      CounterBasedGauge64,
    globalStatActiveTlsConns                      CounterBasedGauge64,
    globalStatHShakeTlsConns                      CounterBasedGauge64,
    globalStatTcpTermNoData                       CounterBasedGauge64,
    globalStatTcpTermNotAuth                      CounterBasedGauge64,
    globalStatTcpTermUnauth                       CounterBasedGauge64,
    globalStatMediaCapacityAlloc                  CounterBasedGauge64,
    globalStatCallAttempts                        CounterBasedGauge64,
    globalStatCallAttemptSignalFailurePercent     CounterBasedGauge64,
    globalStatRPG1B1RcvdPacketRate                CounterBasedGauge64,
    globalStatRPG1B1TransPacketRate               CounterBasedGauge64,
    globalStatRPG1B1RcvdByteRate                  CounterBasedGauge64,
    globalStatRPG1B1TransByteRate                 CounterBasedGauge64,
    globalStatRPG1B1RcvdErrorRate                 CounterBasedGauge64,
    globalStatRPG1B1TransErrorRate                CounterBasedGauge64,
    globalStatRPG1B1RcvdDropPacketRate            CounterBasedGauge64,
    globalStatRPG1B1TransDropPacketRate           CounterBasedGauge64,
    globalStatRPG1B1RcvdMulticastRate             CounterBasedGauge64,
    globalStatRPG1B1TransCollisionRate            CounterBasedGauge64,
    globalStatRPG1B1RcvdLengthErrRate             CounterBasedGauge64,
    globalStatRPG1B1RcvdOverrunErrRate            CounterBasedGauge64,
    globalStatRPG1B1RcvdCRCErrRate                CounterBasedGauge64,
    globalStatRPG1B1RcvdFrameErrRate              CounterBasedGauge64,
    globalStatRPG1B1RcvdFifoFrameErrRate          CounterBasedGauge64,
    globalStatRPG1B1RcvdMissedFrameErrRate        CounterBasedGauge64,
    globalStatRPG1B1TransAbortErrRate             CounterBasedGauge64,
    globalStatRPG1B1TransCarrierErrRate           CounterBasedGauge64,
    globalStatRPG1B1TransFifoErrRate              CounterBasedGauge64,
    globalStatRPG1B1TransHtbtErrRate              CounterBasedGauge64,
    globalStatRPG1B1TransWindowErrRate            CounterBasedGauge64,
    globalStatRPG2B1RcvdPacketRate                CounterBasedGauge64,
    globalStatRPG2B1TransPacketRate               CounterBasedGauge64,
    globalStatRPG2B1RcvdByteRate                  CounterBasedGauge64,
    globalStatRPG2B1TransByteRate                 CounterBasedGauge64,
    globalStatRPG2B1RcvdErrorRate                 CounterBasedGauge64,
    globalStatRPG2B1TransErrorRate                CounterBasedGauge64,
    globalStatRPG2B1RcvdDropPacketRate            CounterBasedGauge64,
    globalStatRPG2B1TransDropPacketRate           CounterBasedGauge64,
    globalStatRPG2B1RcvdMulticastRate             CounterBasedGauge64,
    globalStatRPG2B1TransCollisionRate            CounterBasedGauge64,
    globalStatRPG2B1RcvdLengthErrRate             CounterBasedGauge64,
    globalStatRPG2B1RcvdOverrunErrRate            CounterBasedGauge64,
    globalStatRPG2B1RcvdCRCErrRate                CounterBasedGauge64,
    globalStatRPG2B1RcvdFrameErrRate              CounterBasedGauge64,
    globalStatRPG2B1RcvdFifoFrameErrRate          CounterBasedGauge64,
    globalStatRPG2B1RcvdMissedFrameErrRate        CounterBasedGauge64,
    globalStatRPG2B1TransAbortErrRate             CounterBasedGauge64,
    globalStatRPG2B1TransCarrierErrRate           CounterBasedGauge64,
    globalStatRPG2B1TransFifoErrRate              CounterBasedGauge64,
    globalStatRPG2B1TransHtbtErrRate              CounterBasedGauge64,
    globalStatRPG2B1TransWindowErrRate            CounterBasedGauge64,
    globalStatRPG3B1RcvdPacketRate                CounterBasedGauge64,
    globalStatRPG3B1TransPacketRate               CounterBasedGauge64,
    globalStatRPG3B1RcvdByteRate                  CounterBasedGauge64,
    globalStatRPG3B1TransByteRate                 CounterBasedGauge64,
    globalStatRPG3B1RcvdErrorRate                 CounterBasedGauge64,
    globalStatRPG3B1TransErrorRate                CounterBasedGauge64,
    globalStatRPG3B1RcvdDropPacketRate            CounterBasedGauge64,
    globalStatRPG3B1TransDropPacketRate           CounterBasedGauge64,
    globalStatRPG3B1RcvdMulticastRate             CounterBasedGauge64,
    globalStatRPG3B1TransCollisionRate            CounterBasedGauge64,
    globalStatRPG3B1RcvdLengthErrRate             CounterBasedGauge64,
    globalStatRPG3B1RcvdOverrunErrRate            CounterBasedGauge64,
    globalStatRPG3B1RcvdCRCErrRate                CounterBasedGauge64,
    globalStatRPG3B1RcvdFrameErrRate              CounterBasedGauge64,
    globalStatRPG3B1RcvdFifoFrameErrRate          CounterBasedGauge64,
    globalStatRPG3B1RcvdMissedFrameErrRate        CounterBasedGauge64,
    globalStatRPG3B1TransAbortErrRate             CounterBasedGauge64,
    globalStatRPG3B1TransCarrierErrRate           CounterBasedGauge64,
    globalStatRPG3B1TransFifoErrRate              CounterBasedGauge64,
    globalStatRPG3B1TransHtbtErrRate              CounterBasedGauge64,
    globalStatRPG3B1TransWindowErrRate            CounterBasedGauge64,
    globalStatRPG4B1RcvdPacketRate                CounterBasedGauge64,
    globalStatRPG4B1TransPacketRate               CounterBasedGauge64,
    globalStatRPG4B1RcvdByteRate                  CounterBasedGauge64,
    globalStatRPG4B1TransByteRate                 CounterBasedGauge64,
    globalStatRPG4B1RcvdErrorRate                 CounterBasedGauge64,
    globalStatRPG4B1TransErrorRate                CounterBasedGauge64,
    globalStatRPG4B1RcvdDropPacketRate            CounterBasedGauge64,
    globalStatRPG4B1TransDropPacketRate           CounterBasedGauge64,
    globalStatRPG4B1RcvdMulticastRate             CounterBasedGauge64,
    globalStatRPG4B1TransCollisionRate            CounterBasedGauge64,
    globalStatRPG4B1RcvdLengthErrRate             CounterBasedGauge64,
    globalStatRPG4B1RcvdOverrunErrRate            CounterBasedGauge64,
    globalStatRPG4B1RcvdCRCErrRate                CounterBasedGauge64,
    globalStatRPG4B1RcvdFrameErrRate              CounterBasedGauge64,
    globalStatRPG4B1RcvdFifoFrameErrRate          CounterBasedGauge64,
    globalStatRPG4B1RcvdMissedFrameErrRate        CounterBasedGauge64,
    globalStatRPG4B1TransAbortErrRate             CounterBasedGauge64,
    globalStatRPG4B1TransCarrierErrRate           CounterBasedGauge64,
    globalStatRPG4B1TransFifoErrRate              CounterBasedGauge64,
    globalStatRPG4B1TransHtbtErrRate              CounterBasedGauge64,
    globalStatRPG4B1TransWindowErrRate            CounterBasedGauge64,
    globalStatRPG5B1RcvdPacketRate                CounterBasedGauge64,
    globalStatRPG5B1TransPacketRate               CounterBasedGauge64,
    globalStatRPG5B1RcvdByteRate                  CounterBasedGauge64,
    globalStatRPG5B1TransByteRate                 CounterBasedGauge64,
    globalStatRPG5B1RcvdErrorRate                 CounterBasedGauge64,
    globalStatRPG5B1TransErrorRate                CounterBasedGauge64,
    globalStatRPG5B1RcvdDropPacketRate            CounterBasedGauge64,
    globalStatRPG5B1TransDropPacketRate           CounterBasedGauge64,
    globalStatRPG5B1RcvdMulticastRate             CounterBasedGauge64,
    globalStatRPG5B1TransCollisionRate            CounterBasedGauge64,
    globalStatRPG5B1RcvdLengthErrRate             CounterBasedGauge64,
    globalStatRPG5B1RcvdOverrunErrRate            CounterBasedGauge64,
    globalStatRPG5B1RcvdCRCErrRate                CounterBasedGauge64,
    globalStatRPG5B1RcvdFrameErrRate              CounterBasedGauge64,
    globalStatRPG5B1RcvdFifoFrameErrRate          CounterBasedGauge64,
    globalStatRPG5B1RcvdMissedFrameErrRate        CounterBasedGauge64,
    globalStatRPG5B1TransAbortErrRate             CounterBasedGauge64,
    globalStatRPG5B1TransCarrierErrRate           CounterBasedGauge64,
    globalStatRPG5B1TransFifoErrRate              CounterBasedGauge64,
    globalStatRPG5B1TransHtbtErrRate              CounterBasedGauge64,
    globalStatRPG5B1TransWindowErrRate            CounterBasedGauge64,
    globalStatRPG6B1RcvdPacketRate                CounterBasedGauge64,
    globalStatRPG6B1TransPacketRate               CounterBasedGauge64,
    globalStatRPG6B1RcvdByteRate                  CounterBasedGauge64,
    globalStatRPG6B1TransByteRate                 CounterBasedGauge64,
    globalStatRPG6B1RcvdErrorRate                 CounterBasedGauge64,
    globalStatRPG6B1TransErrorRate                CounterBasedGauge64,
    globalStatRPG6B1RcvdDropPacketRate            CounterBasedGauge64,
    globalStatRPG6B1TransDropPacketRate           CounterBasedGauge64,
    globalStatRPG6B1RcvdMulticastRate             CounterBasedGauge64,
    globalStatRPG6B1TransCollisionRate            CounterBasedGauge64,
    globalStatRPG6B1RcvdLengthErrRate             CounterBasedGauge64,
    globalStatRPG6B1RcvdOverrunErrRate            CounterBasedGauge64,
    globalStatRPG6B1RcvdCRCErrRate                CounterBasedGauge64,
    globalStatRPG6B1RcvdFrameErrRate              CounterBasedGauge64,
    globalStatRPG6B1RcvdFifoFrameErrRate          CounterBasedGauge64,
    globalStatRPG6B1RcvdMissedFrameErrRate        CounterBasedGauge64,
    globalStatRPG6B1TransAbortErrRate             CounterBasedGauge64,
    globalStatRPG6B1TransCarrierErrRate           CounterBasedGauge64,
    globalStatRPG6B1TransFifoErrRate              CounterBasedGauge64,
    globalStatRPG6B1TransHtbtErrRate              CounterBasedGauge64,
    globalStatRPG6B1TransWindowErrRate            CounterBasedGauge64,
    globalStatRPG7B1RcvdPacketRate                CounterBasedGauge64,
    globalStatRPG7B1TransPacketRate               CounterBasedGauge64,
    globalStatRPG7B1RcvdByteRate                  CounterBasedGauge64,
    globalStatRPG7B1TransByteRate                 CounterBasedGauge64,
    globalStatRPG7B1RcvdErrorRate                 CounterBasedGauge64,
    globalStatRPG7B1TransErrorRate                CounterBasedGauge64,
    globalStatRPG7B1RcvdDropPacketRate            CounterBasedGauge64,
    globalStatRPG7B1TransDropPacketRate           CounterBasedGauge64,
    globalStatRPG7B1RcvdMulticastRate             CounterBasedGauge64,
    globalStatRPG7B1TransCollisionRate            CounterBasedGauge64,
    globalStatRPG7B1RcvdLengthErrRate             CounterBasedGauge64,
    globalStatRPG7B1RcvdOverrunErrRate            CounterBasedGauge64,
    globalStatRPG7B1RcvdCRCErrRate                CounterBasedGauge64,
    globalStatRPG7B1RcvdFrameErrRate              CounterBasedGauge64,
    globalStatRPG7B1RcvdFifoFrameErrRate          CounterBasedGauge64,
    globalStatRPG7B1RcvdMissedFrameErrRate        CounterBasedGauge64,
    globalStatRPG7B1TransAbortErrRate             CounterBasedGauge64,
    globalStatRPG7B1TransCarrierErrRate           CounterBasedGauge64,
    globalStatRPG7B1TransFifoErrRate              CounterBasedGauge64,
    globalStatRPG7B1TransHtbtErrRate              CounterBasedGauge64,
    globalStatRPG7B1TransWindowErrRate            CounterBasedGauge64,
    globalStatRPG8B1RcvdPacketRate                CounterBasedGauge64,
    globalStatRPG8B1TransPacketRate               CounterBasedGauge64,
    globalStatRPG8B1RcvdByteRate                  CounterBasedGauge64,
    globalStatRPG8B1TransByteRate                 CounterBasedGauge64,
    globalStatRPG8B1RcvdErrorRate                 CounterBasedGauge64,
    globalStatRPG8B1TransErrorRate                CounterBasedGauge64,
    globalStatRPG8B1RcvdDropPacketRate            CounterBasedGauge64,
    globalStatRPG8B1TransDropPacketRate           CounterBasedGauge64,
    globalStatRPG8B1RcvdMulticastRate             CounterBasedGauge64,
    globalStatRPG8B1TransCollisionRate            CounterBasedGauge64,
    globalStatRPG8B1RcvdLengthErrRate             CounterBasedGauge64,
    globalStatRPG8B1RcvdOverrunErrRate            CounterBasedGauge64,
    globalStatRPG8B1RcvdCRCErrRate                CounterBasedGauge64,
    globalStatRPG8B1RcvdFrameErrRate              CounterBasedGauge64,
    globalStatRPG8B1RcvdFifoFrameErrRate          CounterBasedGauge64,
    globalStatRPG8B1RcvdMissedFrameErrRate        CounterBasedGauge64,
    globalStatRPG8B1TransAbortErrRate             CounterBasedGauge64,
    globalStatRPG8B1TransCarrierErrRate           CounterBasedGauge64,
    globalStatRPG8B1TransFifoErrRate              CounterBasedGauge64,
    globalStatRPG8B1TransHtbtErrRate              CounterBasedGauge64,
    globalStatRPG8B1TransWindowErrRate            CounterBasedGauge64,
    globalStatIBG1MB1RcvdPacketRate               CounterBasedGauge64,
    globalStatIBG1MB1TransPacketRate              CounterBasedGauge64,
    globalStatIBG1MB1RcvdByteRate                 CounterBasedGauge64,
    globalStatIBG1MB1TransByteRate                CounterBasedGauge64,
    globalStatIBG1MB1RcvdErrorRate                CounterBasedGauge64,
    globalStatIBG1MB1TransErrorRate               CounterBasedGauge64,
    globalStatIBG1MB1RcvdDropPacketRate           CounterBasedGauge64,
    globalStatIBG1MB1TransDropPacketRate          CounterBasedGauge64,
    globalStatIBG1MB1RcvdMulticastRate            CounterBasedGauge64,
    globalStatIBG1MB1TransCollisionRate           CounterBasedGauge64,
    globalStatIBG1MB1RcvdLengthErrRate            CounterBasedGauge64,
    globalStatIBG1MB1RcvdOverrunErrRate           CounterBasedGauge64,
    globalStatIBG1MB1RcvdCRCErrRate               CounterBasedGauge64,
    globalStatIBG1MB1RcvdFrameErrRate             CounterBasedGauge64,
    globalStatIBG1MB1RcvdFifoFrameErrRate         CounterBasedGauge64,
    globalStatIBG1MB1RcvdMissedFrameErrRate       CounterBasedGauge64,
    globalStatIBG1MB1TransAbortErrRate            CounterBasedGauge64,
    globalStatIBG1MB1TransCarrierErrRate          CounterBasedGauge64,
    globalStatIBG1MB1TransFifoErrRate             CounterBasedGauge64,
    globalStatIBG1MB1TransHtbtErrRate             CounterBasedGauge64,
    globalStatIBG1MB1TransWindowErrRate           CounterBasedGauge64,
    globalStatIBG2MB1RcvdPacketRate               CounterBasedGauge64,
    globalStatIBG2MB1TransPacketRate              CounterBasedGauge64,
    globalStatIBG2MB1RcvdByteRate                 CounterBasedGauge64,
    globalStatIBG2MB1TransByteRate                CounterBasedGauge64,
    globalStatIBG2MB1RcvdErrorRate                CounterBasedGauge64,
    globalStatIBG2MB1TransErrorRate               CounterBasedGauge64,
    globalStatIBG2MB1RcvdDropPacketRate           CounterBasedGauge64,
    globalStatIBG2MB1TransDropPacketRate          CounterBasedGauge64,
    globalStatIBG2MB1RcvdMulticastRate            CounterBasedGauge64,
    globalStatIBG2MB1TransCollisionRate           CounterBasedGauge64,
    globalStatIBG2MB1RcvdLengthErrRate            CounterBasedGauge64,
    globalStatIBG2MB1RcvdOverrunErrRate           CounterBasedGauge64,
    globalStatIBG2MB1RcvdCRCErrRate               CounterBasedGauge64,
    globalStatIBG2MB1RcvdFrameErrRate             CounterBasedGauge64,
    globalStatIBG2MB1RcvdFifoFrameErrRate         CounterBasedGauge64,
    globalStatIBG2MB1RcvdMissedFrameErrRate       CounterBasedGauge64,
    globalStatIBG2MB1TransAbortErrRate            CounterBasedGauge64,
    globalStatIBG2MB1TransCarrierErrRate          CounterBasedGauge64,
    globalStatIBG2MB1TransFifoErrRate             CounterBasedGauge64,
    globalStatIBG2MB1TransHtbtErrRate             CounterBasedGauge64,
    globalStatIBG2MB1TransWindowErrRate           CounterBasedGauge64,
    globalStatIBG1B1RcvdPacketRate                CounterBasedGauge64,
    globalStatIBG1B1TransPacketRate               CounterBasedGauge64,
    globalStatIBG1B1RcvdByteRate                  CounterBasedGauge64,
    globalStatIBG1B1TransByteRate                 CounterBasedGauge64,
    globalStatIBG1B1RcvdErrorRate                 CounterBasedGauge64,
    globalStatIBG1B1TransErrorRate                CounterBasedGauge64,
    globalStatIBG1B1RcvdDropPacketRate            CounterBasedGauge64,
    globalStatIBG1B1TransDropPacketRate           CounterBasedGauge64,
    globalStatIBG1B1RcvdMulticastRate             CounterBasedGauge64,
    globalStatIBG1B1TransCollisionRate            CounterBasedGauge64,
    globalStatIBG1B1RcvdLengthErrRate             CounterBasedGauge64,
    globalStatIBG1B1RcvdOverrunErrRate            CounterBasedGauge64,
    globalStatIBG1B1RcvdCRCErrRate                CounterBasedGauge64,
    globalStatIBG1B1RcvdFrameErrRate              CounterBasedGauge64,
    globalStatIBG1B1RcvdFifoFrameErrRate          CounterBasedGauge64,
    globalStatIBG1B1RcvdMissedFrameErrRate        CounterBasedGauge64,
    globalStatIBG1B1TransAbortErrRate             CounterBasedGauge64,
    globalStatIBG1B1TransCarrierErrRate           CounterBasedGauge64,
    globalStatIBG1B1TransFifoErrRate              CounterBasedGauge64,
    globalStatIBG1B1TransHtbtErrRate              CounterBasedGauge64,
    globalStatIBG1B1TransWindowErrRate            CounterBasedGauge64,
    globalStatIBG2B1RcvdPacketRate                CounterBasedGauge64,
    globalStatIBG2B1TransPacketRate               CounterBasedGauge64,
    globalStatIBG2B1RcvdByteRate                  CounterBasedGauge64,
    globalStatIBG2B1TransByteRate                 CounterBasedGauge64,
    globalStatIBG2B1RcvdErrorRate                 CounterBasedGauge64,
    globalStatIBG2B1TransErrorRate                CounterBasedGauge64,
    globalStatIBG2B1RcvdDropPacketRate            CounterBasedGauge64,
    globalStatIBG2B1TransDropPacketRate           CounterBasedGauge64,
    globalStatIBG2B1RcvdMulticastRate             CounterBasedGauge64,
    globalStatIBG2B1TransCollisionRate            CounterBasedGauge64,
    globalStatIBG2B1RcvdLengthErrRate             CounterBasedGauge64,
    globalStatIBG2B1RcvdOverrunErrRate            CounterBasedGauge64,
    globalStatIBG2B1RcvdCRCErrRate                CounterBasedGauge64,
    globalStatIBG2B1RcvdFrameErrRate              CounterBasedGauge64,
    globalStatIBG2B1RcvdFifoFrameErrRate          CounterBasedGauge64,
    globalStatIBG2B1RcvdMissedFrameErrRate        CounterBasedGauge64,
    globalStatIBG2B1TransAbortErrRate             CounterBasedGauge64,
    globalStatIBG2B1TransCarrierErrRate           CounterBasedGauge64,
    globalStatIBG2B1TransFifoErrRate              CounterBasedGauge64,
    globalStatIBG2B1TransHtbtErrRate              CounterBasedGauge64,
    globalStatIBG2B1TransWindowErrRate            CounterBasedGauge64,
    globalStatIPG1B1RcvdPacketRate                CounterBasedGauge64,
    globalStatIPG1B1TransPacketRate               CounterBasedGauge64,
    globalStatIPG1B1RcvdByteRate                  CounterBasedGauge64,
    globalStatIPG1B1TransByteRate                 CounterBasedGauge64,
    globalStatIPG1B1RcvdErrorRate                 CounterBasedGauge64,
    globalStatIPG1B1TransErrorRate                CounterBasedGauge64,
    globalStatIPG1B1RcvdDropPacketRate            CounterBasedGauge64,
    globalStatIPG1B1TransDropPacketRate           CounterBasedGauge64,
    globalStatIPG1B1RcvdMulticastRate             CounterBasedGauge64,
    globalStatIPG1B1TransCollisionRate            CounterBasedGauge64,
    globalStatIPG1B1RcvdLengthErrRate             CounterBasedGauge64,
    globalStatIPG1B1RcvdOverrunErrRate            CounterBasedGauge64,
    globalStatIPG1B1RcvdCRCErrRate                CounterBasedGauge64,
    globalStatIPG1B1RcvdFrameErrRate              CounterBasedGauge64,
    globalStatIPG1B1RcvdFifoFrameErrRate          CounterBasedGauge64,
    globalStatIPG1B1RcvdMissedFrameErrRate        CounterBasedGauge64,
    globalStatIPG1B1TransAbortErrRate             CounterBasedGauge64,
    globalStatIPG1B1TransCarrierErrRate           CounterBasedGauge64,
    globalStatIPG1B1TransFifoErrRate              CounterBasedGauge64,
    globalStatIPG1B1TransHtbtErrRate              CounterBasedGauge64,
    globalStatIPG1B1TransWindowErrRate            CounterBasedGauge64,
    globalStatIFXG1B1RcvdPacketRate               CounterBasedGauge64,
    globalStatIFXG1B1TransPacketRate              CounterBasedGauge64,
    globalStatIFXG1B1RcvdByteRate                 CounterBasedGauge64,
    globalStatIFXG1B1TransByteRate                CounterBasedGauge64,
    globalStatIFXG1B1RcvdErrorRate                CounterBasedGauge64,
    globalStatIFXG1B1TransErrorRate               CounterBasedGauge64,
    globalStatIFXG1B1RcvdDropPacketRate           CounterBasedGauge64,
    globalStatIFXG1B1TransDropPacketRate          CounterBasedGauge64,
    globalStatIFXG1B1RcvdMulticastRate            CounterBasedGauge64,
    globalStatIFXG1B1TransCollisionRate           CounterBasedGauge64,
    globalStatIFXG1B1RcvdLengthErrRate            CounterBasedGauge64,
    globalStatIFXG1B1RcvdOverrunErrRate           CounterBasedGauge64,
    globalStatIFXG1B1RcvdCRCErrRate               CounterBasedGauge64,
    globalStatIFXG1B1RcvdFrameErrRate             CounterBasedGauge64,
    globalStatIFXG1B1RcvdFifoFrameErrRate         CounterBasedGauge64,
    globalStatIFXG1B1RcvdMissedFrameErrRate       CounterBasedGauge64,
    globalStatIFXG1B1TransAbortErrRate            CounterBasedGauge64,
    globalStatIFXG1B1TransCarrierErrRate          CounterBasedGauge64,
    globalStatIFXG1B1TransFifoErrRate             CounterBasedGauge64,
    globalStatIFXG1B1TransHtbtErrRate             CounterBasedGauge64,
    globalStatIFXG1B1TransWindowErrRate           CounterBasedGauge64,
    globalStatIFXG2B1RcvdPacketRate               CounterBasedGauge64,
    globalStatIFXG2B1TransPacketRate              CounterBasedGauge64,
    globalStatIFXG2B1RcvdByteRate                 CounterBasedGauge64,
    globalStatIFXG2B1TransByteRate                CounterBasedGauge64,
    globalStatIFXG2B1RcvdErrorRate                CounterBasedGauge64,
    globalStatIFXG2B1TransErrorRate               CounterBasedGauge64,
    globalStatIFXG2B1RcvdDropPacketRate           CounterBasedGauge64,
    globalStatIFXG2B1TransDropPacketRate          CounterBasedGauge64,
    globalStatIFXG2B1RcvdMulticastRate            CounterBasedGauge64,
    globalStatIFXG2B1TransCollisionRate           CounterBasedGauge64,
    globalStatIFXG2B1RcvdLengthErrRate            CounterBasedGauge64,
    globalStatIFXG2B1RcvdOverrunErrRate           CounterBasedGauge64,
    globalStatIFXG2B1RcvdCRCErrRate               CounterBasedGauge64,
    globalStatIFXG2B1RcvdFrameErrRate             CounterBasedGauge64,
    globalStatIFXG2B1RcvdFifoFrameErrRate         CounterBasedGauge64,
    globalStatIFXG2B1RcvdMissedFrameErrRate       CounterBasedGauge64,
    globalStatIFXG2B1TransAbortErrRate            CounterBasedGauge64,
    globalStatIFXG2B1TransCarrierErrRate          CounterBasedGauge64,
    globalStatIFXG2B1TransFifoErrRate             CounterBasedGauge64,
    globalStatIFXG2B1TransHtbtErrRate             CounterBasedGauge64,
    globalStatIFXG2B1TransWindowErrRate           CounterBasedGauge64,
    globalStatRPXG1B1RcvdPacketRate               CounterBasedGauge64,
    globalStatRPXG1B1TransPacketRate              CounterBasedGauge64,
    globalStatRPXG1B1RcvdByteRate                 CounterBasedGauge64,
    globalStatRPXG1B1TransByteRate                CounterBasedGauge64,
    globalStatRPXG1B1RcvdErrorRate                CounterBasedGauge64,
    globalStatRPXG1B1TransErrorRate               CounterBasedGauge64,
    globalStatRPXG1B1RcvdDropPacketRate           CounterBasedGauge64,
    globalStatRPXG1B1TransDropPacketRate          CounterBasedGauge64,
    globalStatRPXG1B1RcvdMulticastRate            CounterBasedGauge64,
    globalStatRPXG1B1TransCollisionRate           CounterBasedGauge64,
    globalStatRPXG1B1RcvdLengthErrRate            CounterBasedGauge64,
    globalStatRPXG1B1RcvdOverrunErrRate           CounterBasedGauge64,
    globalStatRPXG1B1RcvdCRCErrRate               CounterBasedGauge64,
    globalStatRPXG1B1RcvdFrameErrRate             CounterBasedGauge64,
    globalStatRPXG1B1RcvdFifoFrameErrRate         CounterBasedGauge64,
    globalStatRPXG1B1RcvdMissedFrameErrRate       CounterBasedGauge64,
    globalStatRPXG1B1TransAbortErrRate            CounterBasedGauge64,
    globalStatRPXG1B1TransCarrierErrRate          CounterBasedGauge64,
    globalStatRPXG1B1TransFifoErrRate             CounterBasedGauge64,
    globalStatRPXG1B1TransHtbtErrRate             CounterBasedGauge64,
    globalStatRPXG1B1TransWindowErrRate           CounterBasedGauge64,
    globalStatRPXG2B1RcvdPacketRate               CounterBasedGauge64,
    globalStatRPXG2B1TransPacketRate              CounterBasedGauge64,
    globalStatRPXG2B1RcvdByteRate                 CounterBasedGauge64,
    globalStatRPXG2B1TransByteRate                CounterBasedGauge64,
    globalStatRPXG2B1RcvdErrorRate                CounterBasedGauge64,
    globalStatRPXG2B1TransErrorRate               CounterBasedGauge64,
    globalStatRPXG2B1RcvdDropPacketRate           CounterBasedGauge64,
    globalStatRPXG2B1TransDropPacketRate          CounterBasedGauge64,
    globalStatRPXG2B1RcvdMulticastRate            CounterBasedGauge64,
    globalStatRPXG2B1TransCollisionRate           CounterBasedGauge64,
    globalStatRPXG2B1RcvdLengthErrRate            CounterBasedGauge64,
    globalStatRPXG2B1RcvdOverrunErrRate           CounterBasedGauge64,
    globalStatRPXG2B1RcvdCRCErrRate               CounterBasedGauge64,
    globalStatRPXG2B1RcvdFrameErrRate             CounterBasedGauge64,
    globalStatRPXG2B1RcvdFifoFrameErrRate         CounterBasedGauge64,
    globalStatRPXG2B1RcvdMissedFrameErrRate       CounterBasedGauge64,
    globalStatRPXG2B1TransAbortErrRate            CounterBasedGauge64,
    globalStatRPXG2B1TransCarrierErrRate          CounterBasedGauge64,
    globalStatRPXG2B1TransFifoErrRate             CounterBasedGauge64,
    globalStatRPXG2B1TransHtbtErrRate             CounterBasedGauge64,
    globalStatRPXG2B1TransWindowErrRate           CounterBasedGauge64,
    globalStatRPXG3B1RcvdPacketRate               CounterBasedGauge64,
    globalStatRPXG3B1TransPacketRate              CounterBasedGauge64,
    globalStatRPXG3B1RcvdByteRate                 CounterBasedGauge64,
    globalStatRPXG3B1TransByteRate                CounterBasedGauge64,
    globalStatRPXG3B1RcvdErrorRate                CounterBasedGauge64,
    globalStatRPXG3B1TransErrorRate               CounterBasedGauge64,
    globalStatRPXG3B1RcvdDropPacketRate           CounterBasedGauge64,
    globalStatRPXG3B1TransDropPacketRate          CounterBasedGauge64,
    globalStatRPXG3B1RcvdMulticastRate            CounterBasedGauge64,
    globalStatRPXG3B1TransCollisionRate           CounterBasedGauge64,
    globalStatRPXG3B1RcvdLengthErrRate            CounterBasedGauge64,
    globalStatRPXG3B1RcvdOverrunErrRate           CounterBasedGauge64,
    globalStatRPXG3B1RcvdCRCErrRate               CounterBasedGauge64,
    globalStatRPXG3B1RcvdFrameErrRate             CounterBasedGauge64,
    globalStatRPXG3B1RcvdFifoFrameErrRate         CounterBasedGauge64,
    globalStatRPXG3B1RcvdMissedFrameErrRate       CounterBasedGauge64,
    globalStatRPXG3B1TransAbortErrRate            CounterBasedGauge64,
    globalStatRPXG3B1TransCarrierErrRate          CounterBasedGauge64,
    globalStatRPXG3B1TransFifoErrRate             CounterBasedGauge64,
    globalStatRPXG3B1TransHtbtErrRate             CounterBasedGauge64,
    globalStatRPXG3B1TransWindowErrRate           CounterBasedGauge64,
    globalStatRPXG4B1RcvdPacketRate               CounterBasedGauge64,
    globalStatRPXG4B1TransPacketRate              CounterBasedGauge64,
    globalStatRPXG4B1RcvdByteRate                 CounterBasedGauge64,
    globalStatRPXG4B1TransByteRate                CounterBasedGauge64,
    globalStatRPXG4B1RcvdErrorRate                CounterBasedGauge64,
    globalStatRPXG4B1TransErrorRate               CounterBasedGauge64,
    globalStatRPXG4B1RcvdDropPacketRate           CounterBasedGauge64,
    globalStatRPXG4B1TransDropPacketRate          CounterBasedGauge64,
    globalStatRPXG4B1RcvdMulticastRate            CounterBasedGauge64,
    globalStatRPXG4B1TransCollisionRate           CounterBasedGauge64,
    globalStatRPXG4B1RcvdLengthErrRate            CounterBasedGauge64,
    globalStatRPXG4B1RcvdOverrunErrRate           CounterBasedGauge64,
    globalStatRPXG4B1RcvdCRCErrRate               CounterBasedGauge64,
    globalStatRPXG4B1RcvdFrameErrRate             CounterBasedGauge64,
    globalStatRPXG4B1RcvdFifoFrameErrRate         CounterBasedGauge64,
    globalStatRPXG4B1RcvdMissedFrameErrRate       CounterBasedGauge64,
    globalStatRPXG4B1TransAbortErrRate            CounterBasedGauge64,
    globalStatRPXG4B1TransCarrierErrRate          CounterBasedGauge64,
    globalStatRPXG4B1TransFifoErrRate             CounterBasedGauge64,
    globalStatRPXG4B1TransHtbtErrRate             CounterBasedGauge64,
    globalStatRPXG4B1TransWindowErrRate           CounterBasedGauge64,
    globalStatRPG1B2RcvdPacketRate                CounterBasedGauge64,
    globalStatRPG1B2TransPacketRate               CounterBasedGauge64,
    globalStatRPG1B2RcvdByteRate                  CounterBasedGauge64,
    globalStatRPG1B2TransByteRate                 CounterBasedGauge64,
    globalStatRPG1B2RcvdErrorRate                 CounterBasedGauge64,
    globalStatRPG1B2TransErrorRate                CounterBasedGauge64,
    globalStatRPG1B2RcvdDropPacketRate            CounterBasedGauge64,
    globalStatRPG1B2TransDropPacketRate           CounterBasedGauge64,
    globalStatRPG1B2RcvdMulticastRate             CounterBasedGauge64,
    globalStatRPG1B2TransCollisionRate            CounterBasedGauge64,
    globalStatRPG1B2RcvdLengthErrRate             CounterBasedGauge64,
    globalStatRPG1B2RcvdOverrunErrRate            CounterBasedGauge64,
    globalStatRPG1B2RcvdCRCErrRate                CounterBasedGauge64,
    globalStatRPG1B2RcvdFrameErrRate              CounterBasedGauge64,
    globalStatRPG1B2RcvdFifoFrameErrRate          CounterBasedGauge64,
    globalStatRPG1B2RcvdMissedFrameErrRate        CounterBasedGauge64,
    globalStatRPG1B2TransAbortErrRate             CounterBasedGauge64,
    globalStatRPG1B2TransCarrierErrRate           CounterBasedGauge64,
    globalStatRPG1B2TransFifoErrRate              CounterBasedGauge64,
    globalStatRPG1B2TransHtbtErrRate              CounterBasedGauge64,
    globalStatRPG1B2TransWindowErrRate            CounterBasedGauge64,
    globalStatRPG2B2RcvdPacketRate                CounterBasedGauge64,
    globalStatRPG2B2TransPacketRate               CounterBasedGauge64,
    globalStatRPG2B2RcvdByteRate                  CounterBasedGauge64,
    globalStatRPG2B2TransByteRate                 CounterBasedGauge64,
    globalStatRPG2B2RcvdErrorRate                 CounterBasedGauge64,
    globalStatRPG2B2TransErrorRate                CounterBasedGauge64,
    globalStatRPG2B2RcvdDropPacketRate            CounterBasedGauge64,
    globalStatRPG2B2TransDropPacketRate           CounterBasedGauge64,
    globalStatRPG2B2RcvdMulticastRate             CounterBasedGauge64,
    globalStatRPG2B2TransCollisionRate            CounterBasedGauge64,
    globalStatRPG2B2RcvdLengthErrRate             CounterBasedGauge64,
    globalStatRPG2B2RcvdOverrunErrRate            CounterBasedGauge64,
    globalStatRPG2B2RcvdCRCErrRate                CounterBasedGauge64,
    globalStatRPG2B2RcvdFrameErrRate              CounterBasedGauge64,
    globalStatRPG2B2RcvdFifoFrameErrRate          CounterBasedGauge64,
    globalStatRPG2B2RcvdMissedFrameErrRate        CounterBasedGauge64,
    globalStatRPG2B2TransAbortErrRate             CounterBasedGauge64,
    globalStatRPG2B2TransCarrierErrRate           CounterBasedGauge64,
    globalStatRPG2B2TransFifoErrRate              CounterBasedGauge64,
    globalStatRPG2B2TransHtbtErrRate              CounterBasedGauge64,
    globalStatRPG2B2TransWindowErrRate            CounterBasedGauge64,
    globalStatRPG3B2RcvdPacketRate                CounterBasedGauge64,
    globalStatRPG3B2TransPacketRate               CounterBasedGauge64,
    globalStatRPG3B2RcvdByteRate                  CounterBasedGauge64,
    globalStatRPG3B2TransByteRate                 CounterBasedGauge64,
    globalStatRPG3B2RcvdErrorRate                 CounterBasedGauge64,
    globalStatRPG3B2TransErrorRate                CounterBasedGauge64,
    globalStatRPG3B2RcvdDropPacketRate            CounterBasedGauge64,
    globalStatRPG3B2TransDropPacketRate           CounterBasedGauge64,
    globalStatRPG3B2RcvdMulticastRate             CounterBasedGauge64,
    globalStatRPG3B2TransCollisionRate            CounterBasedGauge64,
    globalStatRPG3B2RcvdLengthErrRate             CounterBasedGauge64,
    globalStatRPG3B2RcvdOverrunErrRate            CounterBasedGauge64,
    globalStatRPG3B2RcvdCRCErrRate                CounterBasedGauge64,
    globalStatRPG3B2RcvdFrameErrRate              CounterBasedGauge64,
    globalStatRPG3B2RcvdFifoFrameErrRate          CounterBasedGauge64,
    globalStatRPG3B2RcvdMissedFrameErrRate        CounterBasedGauge64,
    globalStatRPG3B2TransAbortErrRate             CounterBasedGauge64,
    globalStatRPG3B2TransCarrierErrRate           CounterBasedGauge64,
    globalStatRPG3B2TransFifoErrRate              CounterBasedGauge64,
    globalStatRPG3B2TransHtbtErrRate              CounterBasedGauge64,
    globalStatRPG3B2TransWindowErrRate            CounterBasedGauge64,
    globalStatRPG4B2RcvdPacketRate                CounterBasedGauge64,
    globalStatRPG4B2TransPacketRate               CounterBasedGauge64,
    globalStatRPG4B2RcvdByteRate                  CounterBasedGauge64,
    globalStatRPG4B2TransByteRate                 CounterBasedGauge64,
    globalStatRPG4B2RcvdErrorRate                 CounterBasedGauge64,
    globalStatRPG4B2TransErrorRate                CounterBasedGauge64,
    globalStatRPG4B2RcvdDropPacketRate            CounterBasedGauge64,
    globalStatRPG4B2TransDropPacketRate           CounterBasedGauge64,
    globalStatRPG4B2RcvdMulticastRate             CounterBasedGauge64,
    globalStatRPG4B2TransCollisionRate            CounterBasedGauge64,
    globalStatRPG4B2RcvdLengthErrRate             CounterBasedGauge64,
    globalStatRPG4B2RcvdOverrunErrRate            CounterBasedGauge64,
    globalStatRPG4B2RcvdCRCErrRate                CounterBasedGauge64,
    globalStatRPG4B2RcvdFrameErrRate              CounterBasedGauge64,
    globalStatRPG4B2RcvdFifoFrameErrRate          CounterBasedGauge64,
    globalStatRPG4B2RcvdMissedFrameErrRate        CounterBasedGauge64,
    globalStatRPG4B2TransAbortErrRate             CounterBasedGauge64,
    globalStatRPG4B2TransCarrierErrRate           CounterBasedGauge64,
    globalStatRPG4B2TransFifoErrRate              CounterBasedGauge64,
    globalStatRPG4B2TransHtbtErrRate              CounterBasedGauge64,
    globalStatRPG4B2TransWindowErrRate            CounterBasedGauge64,
    globalStatRPG5B2RcvdPacketRate                CounterBasedGauge64,
    globalStatRPG5B2TransPacketRate               CounterBasedGauge64,
    globalStatRPG5B2RcvdByteRate                  CounterBasedGauge64,
    globalStatRPG5B2TransByteRate                 CounterBasedGauge64,
    globalStatRPG5B2RcvdErrorRate                 CounterBasedGauge64,
    globalStatRPG5B2TransErrorRate                CounterBasedGauge64,
    globalStatRPG5B2RcvdDropPacketRate            CounterBasedGauge64,
    globalStatRPG5B2TransDropPacketRate           CounterBasedGauge64,
    globalStatRPG5B2RcvdMulticastRate             CounterBasedGauge64,
    globalStatRPG5B2TransCollisionRate            CounterBasedGauge64,
    globalStatRPG5B2RcvdLengthErrRate             CounterBasedGauge64,
    globalStatRPG5B2RcvdOverrunErrRate            CounterBasedGauge64,
    globalStatRPG5B2RcvdCRCErrRate                CounterBasedGauge64,
    globalStatRPG5B2RcvdFrameErrRate              CounterBasedGauge64,
    globalStatRPG5B2RcvdFifoFrameErrRate          CounterBasedGauge64,
    globalStatRPG5B2RcvdMissedFrameErrRate        CounterBasedGauge64,
    globalStatRPG5B2TransAbortErrRate             CounterBasedGauge64,
    globalStatRPG5B2TransCarrierErrRate           CounterBasedGauge64,
    globalStatRPG5B2TransFifoErrRate              CounterBasedGauge64,
    globalStatRPG5B2TransHtbtErrRate              CounterBasedGauge64,
    globalStatRPG5B2TransWindowErrRate            CounterBasedGauge64,
    globalStatRPG6B2RcvdPacketRate                CounterBasedGauge64,
    globalStatRPG6B2TransPacketRate               CounterBasedGauge64,
    globalStatRPG6B2RcvdByteRate                  CounterBasedGauge64,
    globalStatRPG6B2TransByteRate                 CounterBasedGauge64,
    globalStatRPG6B2RcvdErrorRate                 CounterBasedGauge64,
    globalStatRPG6B2TransErrorRate                CounterBasedGauge64,
    globalStatRPG6B2RcvdDropPacketRate            CounterBasedGauge64,
    globalStatRPG6B2TransDropPacketRate           CounterBasedGauge64,
    globalStatRPG6B2RcvdMulticastRate             CounterBasedGauge64,
    globalStatRPG6B2TransCollisionRate            CounterBasedGauge64,
    globalStatRPG6B2RcvdLengthErrRate             CounterBasedGauge64,
    globalStatRPG6B2RcvdOverrunErrRate            CounterBasedGauge64,
    globalStatRPG6B2RcvdCRCErrRate                CounterBasedGauge64,
    globalStatRPG6B2RcvdFrameErrRate              CounterBasedGauge64,
    globalStatRPG6B2RcvdFifoFrameErrRate          CounterBasedGauge64,
    globalStatRPG6B2RcvdMissedFrameErrRate        CounterBasedGauge64,
    globalStatRPG6B2TransAbortErrRate             CounterBasedGauge64,
    globalStatRPG6B2TransCarrierErrRate           CounterBasedGauge64,
    globalStatRPG6B2TransFifoErrRate              CounterBasedGauge64,
    globalStatRPG6B2TransHtbtErrRate              CounterBasedGauge64,
    globalStatRPG6B2TransWindowErrRate            CounterBasedGauge64,
    globalStatRPG7B2RcvdPacketRate                CounterBasedGauge64,
    globalStatRPG7B2TransPacketRate               CounterBasedGauge64,
    globalStatRPG7B2RcvdByteRate                  CounterBasedGauge64,
    globalStatRPG7B2TransByteRate                 CounterBasedGauge64,
    globalStatRPG7B2RcvdErrorRate                 CounterBasedGauge64,
    globalStatRPG7B2TransErrorRate                CounterBasedGauge64,
    globalStatRPG7B2RcvdDropPacketRate            CounterBasedGauge64,
    globalStatRPG7B2TransDropPacketRate           CounterBasedGauge64,
    globalStatRPG7B2RcvdMulticastRate             CounterBasedGauge64,
    globalStatRPG7B2TransCollisionRate            CounterBasedGauge64,
    globalStatRPG7B2RcvdLengthErrRate             CounterBasedGauge64,
    globalStatRPG7B2RcvdOverrunErrRate            CounterBasedGauge64,
    globalStatRPG7B2RcvdCRCErrRate                CounterBasedGauge64,
    globalStatRPG7B2RcvdFrameErrRate              CounterBasedGauge64,
    globalStatRPG7B2RcvdFifoFrameErrRate          CounterBasedGauge64,
    globalStatRPG7B2RcvdMissedFrameErrRate        CounterBasedGauge64,
    globalStatRPG7B2TransAbortErrRate             CounterBasedGauge64,
    globalStatRPG7B2TransCarrierErrRate           CounterBasedGauge64,
    globalStatRPG7B2TransFifoErrRate              CounterBasedGauge64,
    globalStatRPG7B2TransHtbtErrRate              CounterBasedGauge64,
    globalStatRPG7B2TransWindowErrRate            CounterBasedGauge64,
    globalStatRPG8B2RcvdPacketRate                CounterBasedGauge64,
    globalStatRPG8B2TransPacketRate               CounterBasedGauge64,
    globalStatRPG8B2RcvdByteRate                  CounterBasedGauge64,
    globalStatRPG8B2TransByteRate                 CounterBasedGauge64,
    globalStatRPG8B2RcvdErrorRate                 CounterBasedGauge64,
    globalStatRPG8B2TransErrorRate                CounterBasedGauge64,
    globalStatRPG8B2RcvdDropPacketRate            CounterBasedGauge64,
    globalStatRPG8B2TransDropPacketRate           CounterBasedGauge64,
    globalStatRPG8B2RcvdMulticastRate             CounterBasedGauge64,
    globalStatRPG8B2TransCollisionRate            CounterBasedGauge64,
    globalStatRPG8B2RcvdLengthErrRate             CounterBasedGauge64,
    globalStatRPG8B2RcvdOverrunErrRate            CounterBasedGauge64,
    globalStatRPG8B2RcvdCRCErrRate                CounterBasedGauge64,
    globalStatRPG8B2RcvdFrameErrRate              CounterBasedGauge64,
    globalStatRPG8B2RcvdFifoFrameErrRate          CounterBasedGauge64,
    globalStatRPG8B2RcvdMissedFrameErrRate        CounterBasedGauge64,
    globalStatRPG8B2TransAbortErrRate             CounterBasedGauge64,
    globalStatRPG8B2TransCarrierErrRate           CounterBasedGauge64,
    globalStatRPG8B2TransFifoErrRate              CounterBasedGauge64,
    globalStatRPG8B2TransHtbtErrRate              CounterBasedGauge64,
    globalStatRPG8B2TransWindowErrRate            CounterBasedGauge64,
    globalStatIBG1MB2RcvdPacketRate               CounterBasedGauge64,
    globalStatIBG1MB2TransPacketRate              CounterBasedGauge64,
    globalStatIBG1MB2RcvdByteRate                 CounterBasedGauge64,
    globalStatIBG1MB2TransByteRate                CounterBasedGauge64,
    globalStatIBG1MB2RcvdErrorRate                CounterBasedGauge64,
    globalStatIBG1MB2TransErrorRate               CounterBasedGauge64,
    globalStatIBG1MB2RcvdDropPacketRate           CounterBasedGauge64,
    globalStatIBG1MB2TransDropPacketRate          CounterBasedGauge64,
    globalStatIBG1MB2RcvdMulticastRate            CounterBasedGauge64,
    globalStatIBG1MB2TransCollisionRate           CounterBasedGauge64,
    globalStatIBG1MB2RcvdLengthErrRate            CounterBasedGauge64,
    globalStatIBG1MB2RcvdOverrunErrRate           CounterBasedGauge64,
    globalStatIBG1MB2RcvdCRCErrRate               CounterBasedGauge64,
    globalStatIBG1MB2RcvdFrameErrRate             CounterBasedGauge64,
    globalStatIBG1MB2RcvdFifoFrameErrRate         CounterBasedGauge64,
    globalStatIBG1MB2RcvdMissedFrameErrRate       CounterBasedGauge64,
    globalStatIBG1MB2TransAbortErrRate            CounterBasedGauge64,
    globalStatIBG1MB2TransCarrierErrRate          CounterBasedGauge64,
    globalStatIBG1MB2TransFifoErrRate             CounterBasedGauge64,
    globalStatIBG1MB2TransHtbtErrRate             CounterBasedGauge64,
    globalStatIBG1MB2TransWindowErrRate           CounterBasedGauge64,
    globalStatIBG2MB2RcvdPacketRate               CounterBasedGauge64,
    globalStatIBG2MB2TransPacketRate              CounterBasedGauge64,
    globalStatIBG2MB2RcvdByteRate                 CounterBasedGauge64,
    globalStatIBG2MB2TransByteRate                CounterBasedGauge64,
    globalStatIBG2MB2RcvdErrorRate                CounterBasedGauge64,
    globalStatIBG2MB2TransErrorRate               CounterBasedGauge64,
    globalStatIBG2MB2RcvdDropPacketRate           CounterBasedGauge64,
    globalStatIBG2MB2TransDropPacketRate          CounterBasedGauge64,
    globalStatIBG2MB2RcvdMulticastRate            CounterBasedGauge64,
    globalStatIBG2MB2TransCollisionRate           CounterBasedGauge64,
    globalStatIBG2MB2RcvdLengthErrRate            CounterBasedGauge64,
    globalStatIBG2MB2RcvdOverrunErrRate           CounterBasedGauge64,
    globalStatIBG2MB2RcvdCRCErrRate               CounterBasedGauge64,
    globalStatIBG2MB2RcvdFrameErrRate             CounterBasedGauge64,
    globalStatIBG2MB2RcvdFifoFrameErrRate         CounterBasedGauge64,
    globalStatIBG2MB2RcvdMissedFrameErrRate       CounterBasedGauge64,
    globalStatIBG2MB2TransAbortErrRate            CounterBasedGauge64,
    globalStatIBG2MB2TransCarrierErrRate          CounterBasedGauge64,
    globalStatIBG2MB2TransFifoErrRate             CounterBasedGauge64,
    globalStatIBG2MB2TransHtbtErrRate             CounterBasedGauge64,
    globalStatIBG2MB2TransWindowErrRate           CounterBasedGauge64,
    globalStatIBG1B2RcvdPacketRate                CounterBasedGauge64,
    globalStatIBG1B2TransPacketRate               CounterBasedGauge64,
    globalStatIBG1B2RcvdByteRate                  CounterBasedGauge64,
    globalStatIBG1B2TransByteRate                 CounterBasedGauge64,
    globalStatIBG1B2RcvdErrorRate                 CounterBasedGauge64,
    globalStatIBG1B2TransErrorRate                CounterBasedGauge64,
    globalStatIBG1B2RcvdDropPacketRate            CounterBasedGauge64,
    globalStatIBG1B2TransDropPacketRate           CounterBasedGauge64,
    globalStatIBG1B2RcvdMulticastRate             CounterBasedGauge64,
    globalStatIBG1B2TransCollisionRate            CounterBasedGauge64,
    globalStatIBG1B2RcvdLengthErrRate             CounterBasedGauge64,
    globalStatIBG1B2RcvdOverrunErrRate            CounterBasedGauge64,
    globalStatIBG1B2RcvdCRCErrRate                CounterBasedGauge64,
    globalStatIBG1B2RcvdFrameErrRate              CounterBasedGauge64,
    globalStatIBG1B2RcvdFifoFrameErrRate          CounterBasedGauge64,
    globalStatIBG1B2RcvdMissedFrameErrRate        CounterBasedGauge64,
    globalStatIBG1B2TransAbortErrRate             CounterBasedGauge64,
    globalStatIBG1B2TransCarrierErrRate           CounterBasedGauge64,
    globalStatIBG1B2TransFifoErrRate              CounterBasedGauge64,
    globalStatIBG1B2TransHtbtErrRate              CounterBasedGauge64,
    globalStatIBG1B2TransWindowErrRate            CounterBasedGauge64,
    globalStatIBG2B2RcvdPacketRate                CounterBasedGauge64,
    globalStatIBG2B2TransPacketRate               CounterBasedGauge64,
    globalStatIBG2B2RcvdByteRate                  CounterBasedGauge64,
    globalStatIBG2B2TransByteRate                 CounterBasedGauge64,
    globalStatIBG2B2RcvdErrorRate                 CounterBasedGauge64,
    globalStatIBG2B2TransErrorRate                CounterBasedGauge64,
    globalStatIBG2B2RcvdDropPacketRate            CounterBasedGauge64,
    globalStatIBG2B2TransDropPacketRate           CounterBasedGauge64,
    globalStatIBG2B2RcvdMulticastRate             CounterBasedGauge64,
    globalStatIBG2B2TransCollisionRate            CounterBasedGauge64,
    globalStatIBG2B2RcvdLengthErrRate             CounterBasedGauge64,
    globalStatIBG2B2RcvdOverrunErrRate            CounterBasedGauge64,
    globalStatIBG2B2RcvdCRCErrRate                CounterBasedGauge64,
    globalStatIBG2B2RcvdFrameErrRate              CounterBasedGauge64,
    globalStatIBG2B2RcvdFifoFrameErrRate          CounterBasedGauge64,
    globalStatIBG2B2RcvdMissedFrameErrRate        CounterBasedGauge64,
    globalStatIBG2B2TransAbortErrRate             CounterBasedGauge64,
    globalStatIBG2B2TransCarrierErrRate           CounterBasedGauge64,
    globalStatIBG2B2TransFifoErrRate              CounterBasedGauge64,
    globalStatIBG2B2TransHtbtErrRate              CounterBasedGauge64,
    globalStatIBG2B2TransWindowErrRate            CounterBasedGauge64,
    globalStatIPG1B2RcvdPacketRate                CounterBasedGauge64,
    globalStatIPG1B2TransPacketRate               CounterBasedGauge64,
    globalStatIPG1B2RcvdByteRate                  CounterBasedGauge64,
    globalStatIPG1B2TransByteRate                 CounterBasedGauge64,
    globalStatIPG1B2RcvdErrorRate                 CounterBasedGauge64,
    globalStatIPG1B2TransErrorRate                CounterBasedGauge64,
    globalStatIPG1B2RcvdDropPacketRate            CounterBasedGauge64,
    globalStatIPG1B2TransDropPacketRate           CounterBasedGauge64,
    globalStatIPG1B2RcvdMulticastRate             CounterBasedGauge64,
    globalStatIPG1B2TransCollisionRate            CounterBasedGauge64,
    globalStatIPG1B2RcvdLengthErrRate             CounterBasedGauge64,
    globalStatIPG1B2RcvdOverrunErrRate            CounterBasedGauge64,
    globalStatIPG1B2RcvdCRCErrRate                CounterBasedGauge64,
    globalStatIPG1B2RcvdFrameErrRate              CounterBasedGauge64,
    globalStatIPG1B2RcvdFifoFrameErrRate          CounterBasedGauge64,
    globalStatIPG1B2RcvdMissedFrameErrRate        CounterBasedGauge64,
    globalStatIPG1B2TransAbortErrRate             CounterBasedGauge64,
    globalStatIPG1B2TransCarrierErrRate           CounterBasedGauge64,
    globalStatIPG1B2TransFifoErrRate              CounterBasedGauge64,
    globalStatIPG1B2TransHtbtErrRate              CounterBasedGauge64,
    globalStatIPG1B2TransWindowErrRate            CounterBasedGauge64,
    globalStatIFXG1B2RcvdPacketRate               CounterBasedGauge64,
    globalStatIFXG1B2TransPacketRate              CounterBasedGauge64,
    globalStatIFXG1B2RcvdByteRate                 CounterBasedGauge64,
    globalStatIFXG1B2TransByteRate                CounterBasedGauge64,
    globalStatIFXG1B2RcvdErrorRate                CounterBasedGauge64,
    globalStatIFXG1B2TransErrorRate               CounterBasedGauge64,
    globalStatIFXG1B2RcvdDropPacketRate           CounterBasedGauge64,
    globalStatIFXG1B2TransDropPacketRate          CounterBasedGauge64,
    globalStatIFXG1B2RcvdMulticastRate            CounterBasedGauge64,
    globalStatIFXG1B2TransCollisionRate           CounterBasedGauge64,
    globalStatIFXG1B2RcvdLengthErrRate            CounterBasedGauge64,
    globalStatIFXG1B2RcvdOverrunErrRate           CounterBasedGauge64,
    globalStatIFXG1B2RcvdCRCErrRate               CounterBasedGauge64,
    globalStatIFXG1B2RcvdFrameErrRate             CounterBasedGauge64,
    globalStatIFXG1B2RcvdFifoFrameErrRate         CounterBasedGauge64,
    globalStatIFXG1B2RcvdMissedFrameErrRate       CounterBasedGauge64,
    globalStatIFXG1B2TransAbortErrRate            CounterBasedGauge64,
    globalStatIFXG1B2TransCarrierErrRate          CounterBasedGauge64,
    globalStatIFXG1B2TransFifoErrRate             CounterBasedGauge64,
    globalStatIFXG1B2TransHtbtErrRate             CounterBasedGauge64,
    globalStatIFXG1B2TransWindowErrRate           CounterBasedGauge64,
    globalStatIFXG2B2RcvdPacketRate               CounterBasedGauge64,
    globalStatIFXG2B2TransPacketRate              CounterBasedGauge64,
    globalStatIFXG2B2RcvdByteRate                 CounterBasedGauge64,
    globalStatIFXG2B2TransByteRate                CounterBasedGauge64,
    globalStatIFXG2B2RcvdErrorRate                CounterBasedGauge64,
    globalStatIFXG2B2TransErrorRate               CounterBasedGauge64,
    globalStatIFXG2B2RcvdDropPacketRate           CounterBasedGauge64,
    globalStatIFXG2B2TransDropPacketRate          CounterBasedGauge64,
    globalStatIFXG2B2RcvdMulticastRate            CounterBasedGauge64,
    globalStatIFXG2B2TransCollisionRate           CounterBasedGauge64,
    globalStatIFXG2B2RcvdLengthErrRate            CounterBasedGauge64,
    globalStatIFXG2B2RcvdOverrunErrRate           CounterBasedGauge64,
    globalStatIFXG2B2RcvdCRCErrRate               CounterBasedGauge64,
    globalStatIFXG2B2RcvdFrameErrRate             CounterBasedGauge64,
    globalStatIFXG2B2RcvdFifoFrameErrRate         CounterBasedGauge64,
    globalStatIFXG2B2RcvdMissedFrameErrRate       CounterBasedGauge64,
    globalStatIFXG2B2TransAbortErrRate            CounterBasedGauge64,
    globalStatIFXG2B2TransCarrierErrRate          CounterBasedGauge64,
    globalStatIFXG2B2TransFifoErrRate             CounterBasedGauge64,
    globalStatIFXG2B2TransHtbtErrRate             CounterBasedGauge64,
    globalStatIFXG2B2TransWindowErrRate           CounterBasedGauge64,
    globalStatRPXG1B2RcvdPacketRate               CounterBasedGauge64,
    globalStatRPXG1B2TransPacketRate              CounterBasedGauge64,
    globalStatRPXG1B2RcvdByteRate                 CounterBasedGauge64,
    globalStatRPXG1B2TransByteRate                CounterBasedGauge64,
    globalStatRPXG1B2RcvdErrorRate                CounterBasedGauge64,
    globalStatRPXG1B2TransErrorRate               CounterBasedGauge64,
    globalStatRPXG1B2RcvdDropPacketRate           CounterBasedGauge64,
    globalStatRPXG1B2TransDropPacketRate          CounterBasedGauge64,
    globalStatRPXG1B2RcvdMulticastRate            CounterBasedGauge64,
    globalStatRPXG1B2TransCollisionRate           CounterBasedGauge64,
    globalStatRPXG1B2RcvdLengthErrRate            CounterBasedGauge64,
    globalStatRPXG1B2RcvdOverrunErrRate           CounterBasedGauge64,
    globalStatRPXG1B2RcvdCRCErrRate               CounterBasedGauge64,
    globalStatRPXG1B2RcvdFrameErrRate             CounterBasedGauge64,
    globalStatRPXG1B2RcvdFifoFrameErrRate         CounterBasedGauge64,
    globalStatRPXG1B2RcvdMissedFrameErrRate       CounterBasedGauge64,
    globalStatRPXG1B2TransAbortErrRate            CounterBasedGauge64,
    globalStatRPXG1B2TransCarrierErrRate          CounterBasedGauge64,
    globalStatRPXG1B2TransFifoErrRate             CounterBasedGauge64,
    globalStatRPXG1B2TransHtbtErrRate             CounterBasedGauge64,
    globalStatRPXG1B2TransWindowErrRate           CounterBasedGauge64,
    globalStatRPXG2B2RcvdPacketRate               CounterBasedGauge64,
    globalStatRPXG2B2TransPacketRate              CounterBasedGauge64,
    globalStatRPXG2B2RcvdByteRate                 CounterBasedGauge64,
    globalStatRPXG2B2TransByteRate                CounterBasedGauge64,
    globalStatRPXG2B2RcvdErrorRate                CounterBasedGauge64,
    globalStatRPXG2B2TransErrorRate               CounterBasedGauge64,
    globalStatRPXG2B2RcvdDropPacketRate           CounterBasedGauge64,
    globalStatRPXG2B2TransDropPacketRate          CounterBasedGauge64,
    globalStatRPXG2B2RcvdMulticastRate            CounterBasedGauge64,
    globalStatRPXG2B2TransCollisionRate           CounterBasedGauge64,
    globalStatRPXG2B2RcvdLengthErrRate            CounterBasedGauge64,
    globalStatRPXG2B2RcvdOverrunErrRate           CounterBasedGauge64,
    globalStatRPXG2B2RcvdCRCErrRate               CounterBasedGauge64,
    globalStatRPXG2B2RcvdFrameErrRate             CounterBasedGauge64,
    globalStatRPXG2B2RcvdFifoFrameErrRate         CounterBasedGauge64,
    globalStatRPXG2B2RcvdMissedFrameErrRate       CounterBasedGauge64,
    globalStatRPXG2B2TransAbortErrRate            CounterBasedGauge64,
    globalStatRPXG2B2TransCarrierErrRate          CounterBasedGauge64,
    globalStatRPXG2B2TransFifoErrRate             CounterBasedGauge64,
    globalStatRPXG2B2TransHtbtErrRate             CounterBasedGauge64,
    globalStatRPXG2B2TransWindowErrRate           CounterBasedGauge64,
    globalStatRPXG3B2RcvdPacketRate               CounterBasedGauge64,
    globalStatRPXG3B2TransPacketRate              CounterBasedGauge64,
    globalStatRPXG3B2RcvdByteRate                 CounterBasedGauge64,
    globalStatRPXG3B2TransByteRate                CounterBasedGauge64,
    globalStatRPXG3B2RcvdErrorRate                CounterBasedGauge64,
    globalStatRPXG3B2TransErrorRate               CounterBasedGauge64,
    globalStatRPXG3B2RcvdDropPacketRate           CounterBasedGauge64,
    globalStatRPXG3B2TransDropPacketRate          CounterBasedGauge64,
    globalStatRPXG3B2RcvdMulticastRate            CounterBasedGauge64,
    globalStatRPXG3B2TransCollisionRate           CounterBasedGauge64,
    globalStatRPXG3B2RcvdLengthErrRate            CounterBasedGauge64,
    globalStatRPXG3B2RcvdOverrunErrRate           CounterBasedGauge64,
    globalStatRPXG3B2RcvdCRCErrRate               CounterBasedGauge64,
    globalStatRPXG3B2RcvdFrameErrRate             CounterBasedGauge64,
    globalStatRPXG3B2RcvdFifoFrameErrRate         CounterBasedGauge64,
    globalStatRPXG3B2RcvdMissedFrameErrRate       CounterBasedGauge64,
    globalStatRPXG3B2TransAbortErrRate            CounterBasedGauge64,
    globalStatRPXG3B2TransCarrierErrRate          CounterBasedGauge64,
    globalStatRPXG3B2TransFifoErrRate             CounterBasedGauge64,
    globalStatRPXG3B2TransHtbtErrRate             CounterBasedGauge64,
    globalStatRPXG3B2TransWindowErrRate           CounterBasedGauge64,
    globalStatRPXG4B2RcvdPacketRate               CounterBasedGauge64,
    globalStatRPXG4B2TransPacketRate              CounterBasedGauge64,
    globalStatRPXG4B2RcvdByteRate                 CounterBasedGauge64,
    globalStatRPXG4B2TransByteRate                CounterBasedGauge64,
    globalStatRPXG4B2RcvdErrorRate                CounterBasedGauge64,
    globalStatRPXG4B2TransErrorRate               CounterBasedGauge64,
    globalStatRPXG4B2RcvdDropPacketRate           CounterBasedGauge64,
    globalStatRPXG4B2TransDropPacketRate          CounterBasedGauge64,
    globalStatRPXG4B2RcvdMulticastRate            CounterBasedGauge64,
    globalStatRPXG4B2TransCollisionRate           CounterBasedGauge64,
    globalStatRPXG4B2RcvdLengthErrRate            CounterBasedGauge64,
    globalStatRPXG4B2RcvdOverrunErrRate           CounterBasedGauge64,
    globalStatRPXG4B2RcvdCRCErrRate               CounterBasedGauge64,
    globalStatRPXG4B2RcvdFrameErrRate             CounterBasedGauge64,
    globalStatRPXG4B2RcvdFifoFrameErrRate         CounterBasedGauge64,
    globalStatRPXG4B2RcvdMissedFrameErrRate       CounterBasedGauge64,
    globalStatRPXG4B2TransAbortErrRate            CounterBasedGauge64,
    globalStatRPXG4B2TransCarrierErrRate          CounterBasedGauge64,
    globalStatRPXG4B2TransFifoErrRate             CounterBasedGauge64,
    globalStatRPXG4B2TransHtbtErrRate             CounterBasedGauge64,
    globalStatRPXG4B2TransWindowErrRate           CounterBasedGauge64,
    globalStatDSPPctPktDrop                       CounterBasedGauge64,
    globalStatActiveTranscTotal                   CounterBasedGauge64,
    globalStatActiveTranscGroup1                  CounterBasedGauge64,
    globalStatSIPTotalTransactions                CounterBasedGauge64,
    globalStatPriority7SigPktsRcvd                CounterBasedGauge64,
    globalStatPriority7SigPktsRcvdRate            CounterBasedGauge64,
    globalStatPriority7SigPktsAccptd              CounterBasedGauge64,
    globalStatPriority7SigPktsAccptdRate          CounterBasedGauge64,
    globalStatPriority7SigPktsDropped             CounterBasedGauge64,
    globalStatPriority7SigPktsDroppedRate         CounterBasedGauge64,
    globalStatPriority7SigBytesRcvd               CounterBasedGauge64,
    globalStatPriority7SigBytesRcvdRate           CounterBasedGauge64,
    globalStatPriority7SigBytesAccptd             CounterBasedGauge64,
    globalStatPriority7SigBytesAccptdRate         CounterBasedGauge64,
    globalStatPriority7SigBytesDropped            CounterBasedGauge64,
    globalStatPriority7SigBytesDroppedRate        CounterBasedGauge64,
    globalStatPriority8SigPktsRcvd                CounterBasedGauge64,
    globalStatPriority8SigPktsRcvdRate            CounterBasedGauge64,
    globalStatPriority8SigPktsAccptd              CounterBasedGauge64,
    globalStatPriority8SigPktsAccptdRate          CounterBasedGauge64,
    globalStatPriority8SigPktsDropped             CounterBasedGauge64,
    globalStatPriority8SigPktsDroppedRate         CounterBasedGauge64,
    globalStatPriority8SigBytesRcvd               CounterBasedGauge64,
    globalStatPriority8SigBytesRcvdRate           CounterBasedGauge64,
    globalStatPriority8SigBytesAccptd             CounterBasedGauge64,
    globalStatPriority8SigBytesAccptdRate         CounterBasedGauge64,
    globalStatPriority8SigBytesDropped            CounterBasedGauge64,
    globalStatPriority8SigBytesDroppedRate        CounterBasedGauge64,
    globalStatDropClosingUdp                      CounterBasedGauge64,
    globalStatDropClosingTcp                      CounterBasedGauge64,
    globalStatDropClosingUdpRate                  CounterBasedGauge64,
    globalStatDropClosingTcpRate                  CounterBasedGauge64,
    globalStatCodecActiveTranscSILK16             CounterBasedGauge64,
    globalStatActiveTransrTotal                   CounterBasedGauge64,
    globalStatEmergencyRedirects                  CounterBasedGauge64,
    globalStatCodecSILKBoards                     CounterBasedGauge64,
    globalStatCodecActiveTranscILBC               CounterBasedGauge64,
    globalStataSRVCCTransfersOK                   CounterBasedGauge64,
    globalStataSRVCCTransfersFailed               CounterBasedGauge64,
    globalStatpreaSRVCCTransfersOK                CounterBasedGauge64,
    globalStatpreaSRVCCTransfersFailed            CounterBasedGauge64,
    globalStatActiveRecordedCalls                 CounterBasedGauge64,
    globalStatFailedRecordingCallsPercent         CounterBasedGauge64,
    globalStatFailedSRSRecordingCalls             CounterBasedGauge64,
    globalStatFailedFeatureRecordingCalls         CounterBasedGauge64,
    globalStatFailedResourceRecordingCalls        CounterBasedGauge64,
    globalStatFailedLicenseRecordingCalls         CounterBasedGauge64,
    globalStatCodecActiveTranscOPUS               CounterBasedGauge64,
    globalStatTotalRecordedCalls                  CounterBasedGauge64,
    globalStatTotalAttemptedRecordedCalls         CounterBasedGauge64,
    globalStatActivePrecIWCalls                   CounterBasedGauge64,
    alarmStatTotalAlarms                          CounterBasedGauge64,
    alarmStatCriticalAlarms                       CounterBasedGauge64,
    alarmStatMajorAlarms                          CounterBasedGauge64,
    alarmStatMinorAlarms                          CounterBasedGauge64,
    alarmStatInfoAlarms                           CounterBasedGauge64,
    globalStatActivePNSubscribers                 CounterBasedGauge64,
    globalStatISUPInterworkingCalls               CounterBasedGauge64,
    globalStatPushNtfnReqSentCount                CounterBasedGauge64,
    globalStatPushNtfnReqSentRate                 CounterBasedGauge64,
    globalStatPushNtfnOKRspRcvdCount              CounterBasedGauge64,
    globalStatPushNtfnOKRspRcvdRate               CounterBasedGauge64,
    globalStatPushNtfnFailedRspRcvdCount          CounterBasedGauge64,
    globalStatPushNtfnFailedRspRcvdRate           CounterBasedGauge64,
    globalStatPushNtfnTimeoutCount                CounterBasedGauge64,
    globalStatPushNtfnTimeoutRate                 CounterBasedGauge64,
    globalStatPushNtfnConnectionErrorCount        CounterBasedGauge64,
    globalStatPushNtfnConnectionErrorRate         CounterBasedGauge64,
    globalStatPushNtfnNumConns                    CounterBasedGauge64,
    globalStatPushNtfnNumTrans                    CounterBasedGauge64,
    globalStatPushNtfnAverageRTT                  CounterBasedGauge64,
    globalStatPriorityCallAttemptFailureRate      CounterBasedGauge64,
    globalStatSIPCongestionQPri00PktsAccepted     CounterBasedGauge64,
    globalStatSIPCongestionQPri00PktsDropped      CounterBasedGauge64,
    globalStatSIPCongestionQPri01PktsAccepted     CounterBasedGauge64,
    globalStatSIPCongestionQPri01PktsDropped      CounterBasedGauge64,
    globalStatSIPCongestionQPri02PktsAccepted     CounterBasedGauge64,
    globalStatSIPCongestionQPri02PktsDropped      CounterBasedGauge64,
    globalStatSIPCongestionQPri03PktsAccepted     CounterBasedGauge64,
    globalStatSIPCongestionQPri03PktsDropped      CounterBasedGauge64,
    globalStatSIPCongestionQPri04PktsAccepted     CounterBasedGauge64,
    globalStatSIPCongestionQPri04PktsDropped      CounterBasedGauge64,
    globalStatSIPCongestionQPri05PktsAccepted     CounterBasedGauge64,
    globalStatSIPCongestionQPri05PktsDropped      CounterBasedGauge64,
    globalStatSIPCongestionQPri06PktsAccepted     CounterBasedGauge64,
    globalStatSIPCongestionQPri06PktsDropped      CounterBasedGauge64,
    globalStatSIPCongestionQPri07PktsAccepted     CounterBasedGauge64,
    globalStatSIPCongestionQPri07PktsDropped      CounterBasedGauge64,
    globalStatSIPCongestionQPri08PktsAccepted     CounterBasedGauge64,
    globalStatSIPCongestionQPri08PktsDropped      CounterBasedGauge64,
    globalStatSIPCongestionQPri09PktsAccepted     CounterBasedGauge64,
    globalStatSIPCongestionQPri09PktsDropped      CounterBasedGauge64,
    globalStatSIPCongestionQPri10PktsAccepted     CounterBasedGauge64,
    globalStatSIPCongestionQPri10PktsDropped      CounterBasedGauge64,
    globalStatSIPCongestionQPri11PktsAccepted     CounterBasedGauge64,
    globalStatSIPCongestionQPri11PktsDropped      CounterBasedGauge64,
    globalStatSIPCongestionQPri12PktsAccepted     CounterBasedGauge64,
    globalStatSIPCongestionQPri12PktsDropped      CounterBasedGauge64,
    globalStatSIPCongestionQPri13PktsAccepted     CounterBasedGauge64,
    globalStatSIPCongestionQPri13PktsDropped      CounterBasedGauge64,
    globalStatSIPCongestionQPri14PktsAccepted     CounterBasedGauge64,
    globalStatSIPCongestionQPri14PktsDropped      CounterBasedGauge64,
    globalStatSIPCongestionQPri15PktsAccepted     CounterBasedGauge64,
    globalStatSIPCongestionQPri15PktsDropped      CounterBasedGauge64,
    globalStatSigningSucceededCount               CounterBasedGauge64,
    globalStatSigningSucceededRate                CounterBasedGauge64,
    globalStatSigningRejectedCount                CounterBasedGauge64,
    globalStatSigningRejectedRate                 CounterBasedGauge64,
    globalStatSigningTimeoutCount                 CounterBasedGauge64,
    globalStatSigningTimeoutRate                  CounterBasedGauge64,
    globalStatSigningUnavailableCount             CounterBasedGauge64,
    globalStatSigningUnavailableRate              CounterBasedGauge64,
    globalStatFailedRecordedCallsSetup            CounterBasedGauge64,
    globalStatFailedRecordedCallsDrop             CounterBasedGauge64,
    globalStatFailedRecordedCallsSetupPercent     CounterBasedGauge64,
    globalStatFailedRecordedCallsDropPercent      CounterBasedGauge64,
    globalStatNoPermitCount                       CounterBasedGauge64,
    globalStatNoPermitRate                        CounterBasedGauge64
  }

  globalStatsSummaryPeriod OBJECT-TYPE
    SYNTAX       INTEGER {
                   summaryPeriod1CurrentClctnIntv(1)
                 }
    MAX-ACCESS   not-accessible
    STATUS       current
    DESCRIPTION  "The period over which the statistics were collected.
                  This is an index field."
    ::= { perimetaGlobalStatsEntry 2 }

  globalStatsCollectionTime OBJECT-TYPE
    SYNTAX       Unsigned32
    MAX-ACCESS   read-only
    STATUS       current
    DESCRIPTION  "The last collection time of the statistics in
                  seconds since 1970."
    ::= { perimetaGlobalStatsEntry 3 }

  globalStatSIPMessagesRcvd OBJECT-TYPE
    SYNTAX       CounterBasedGauge64
    MAX-ACCESS   read-only
    STATUS       current
    DESCRIPTION  "Total SIP messages received (last
                  period)"
    ::= { perimetaGlobalStatsEntry 10 }

  globalStatSIPMessagesSent OBJECT-TYPE
    SYNTAX       CounterBasedGauge64
    MAX-ACCESS   read-only
    STATUS       current
    DESCRIPTION  "Total SIP messages sent (last period)"
    ::= { perimetaGlobalStatsEntry 11 }

  globalStatSIPInvitesRcvd OBJECT-TYPE
    SYNTAX       CounterBasedGauge64
    MAX-ACCESS   read-only
    STATUS       current
    DESCRIPTION  "Total INVITEs received (last period)"
    ::= { perimetaGlobalStatsEntry 12 }

  globalStatSIPInvitesSent OBJECT-TYPE
    SYNTAX       CounterBasedGauge64
    MAX-ACCESS   read-only
    STATUS       current
    DESCRIPTION  "Total INVITEs sent (last period)"
    ::= { perimetaGlobalStatsEntry 13 }

  globalStatSIPByesRcvd OBJECT-TYPE
    SYNTAX       CounterBasedGauge64
    MAX-ACCESS   read-only
    STATUS       current
    DESCRIPTION  "Total BYEs received (last period)"
    ::= { perimetaGlobalStatsEntry 14 }

  globalStatSIPByesSent OBJECT-TYPE
    SYNTAX       CounterBasedGauge64
    MAX-ACCESS   read-only
    STATUS       current
    DESCRIPTION  "Total BYEs sent (last period)"
    ::= { perimetaGlobalStatsEntry 15 }

  globalStatSIPCancelsRcvd OBJECT-TYPE
    SYNTAX       CounterBasedGauge64
    MAX-ACCESS   read-only
    STATUS       current
    DESCRIPTION  "Total CANCELs received (last period)"
    ::= { perimetaGlobalStatsEntry 16 }

  globalStatSIPCancelsSent OBJECT-TYPE
    SYNTAX       CounterBasedGauge64
    MAX-ACCESS   read-only
    STATUS       current
    DESCRIPTION  "Total CANCELs sent (last period)"
    ::= { perimetaGlobalStatsEntry 17 }

  globalStatSIPRegistersRcvd OBJECT-TYPE
    SYNTAX       CounterBasedGauge64
    MAX-ACCESS   read-only
    STATUS       current
    DESCRIPTION  "Total REGISTERs received (last period)"
    ::= { perimetaGlobalStatsEntry 18 }

  globalStatSIPRegistersSent OBJECT-TYPE
    SYNTAX       CounterBasedGauge64
    MAX-ACCESS   read-only
    STATUS       current
    DESCRIPTION  "Total REGISTERs sent (last period)"
    ::= { perimetaGlobalStatsEntry 19 }

  globalStatSIPSubscribesRcvd OBJECT-TYPE
    SYNTAX       CounterBasedGauge64
    MAX-ACCESS   read-only
    STATUS       current
    DESCRIPTION  "Total SUBSCRIBEs received (last period)"
    ::= { perimetaGlobalStatsEntry 20 }

  globalStatSIPSubscribesSent OBJECT-TYPE
    SYNTAX       CounterBasedGauge64
    MAX-ACCESS   read-only
    STATUS       current
    DESCRIPTION  "Total SUBSCRIBEs sent (last period)"
    ::= { perimetaGlobalStatsEntry 21 }

  globalStatSIPCongestionQOldestPkt OBJECT-TYPE
    SYNTAX       CounterBasedGauge64
    MAX-ACCESS   read-only
    STATUS       current
    DESCRIPTION  "Current oldest packet on queue (in
                  milliseconds)"
    ::= { perimetaGlobalStatsEntry 22 }

  globalStatSIPCongestionQLevel OBJECT-TYPE
    SYNTAX       CounterBasedGauge64
    MAX-ACCESS   read-only
    STATUS       current
    DESCRIPTION  "Congestion level"
    ::= { perimetaGlobalStatsEntry 23 }

  globalStatSIPCongestionQMaxPktDelay OBJECT-TYPE
    SYNTAX       CounterBasedGauge64
    MAX-ACCESS   read-only
    STATUS       current
    DESCRIPTION  "Highest single packet delay
                  (milliseconds)"
    ::= { perimetaGlobalStatsEntry 24 }

  globalStatSIPCongestionQPktsDropped OBJECT-TYPE
    SYNTAX       CounterBasedGauge64
    MAX-ACCESS   read-only
    STATUS       current
    DESCRIPTION  "Total SIP packets rejected by the
                  congestion queues (last period)"
    ::= { perimetaGlobalStatsEntry 25 }

  globalStatSIPCongestionQPktsAccepted OBJECT-TYPE
    SYNTAX       CounterBasedGauge64
    MAX-ACCESS   read-only
    STATUS       current
    DESCRIPTION  "Total SIP packets accepted by the
                  congestion queues (last period)"
    ::= { perimetaGlobalStatsEntry 26 }

  globalStatSIP1XXResponsesSent OBJECT-TYPE
    SYNTAX       CounterBasedGauge64
    MAX-ACCESS   read-only
    STATUS       current
    DESCRIPTION  "Total 1xx responses sent (last period)"
    ::= { perimetaGlobalStatsEntry 27 }

  globalStatSIP1XXResponsesRcvd OBJECT-TYPE
    SYNTAX       CounterBasedGauge64
    MAX-ACCESS   read-only
    STATUS       current
    DESCRIPTION  "Total 1xx responses received (last
                  period)"
    ::= { perimetaGlobalStatsEntry 28 }

  globalStatSIP2XXResponsesSent OBJECT-TYPE
    SYNTAX       CounterBasedGauge64
    MAX-ACCESS   read-only
    STATUS       current
    DESCRIPTION  "Total 2xx responses sent (last period)"
    ::= { perimetaGlobalStatsEntry 29 }

  globalStatSIP2XXResponsesRcvd OBJECT-TYPE
    SYNTAX       CounterBasedGauge64
    MAX-ACCESS   read-only
    STATUS       current
    DESCRIPTION  "Total 2xx responses received (last
                  period)"
    ::= { perimetaGlobalStatsEntry 30 }

  globalStatSIP3XXResponsesSent OBJECT-TYPE
    SYNTAX       CounterBasedGauge64
    MAX-ACCESS   read-only
    STATUS       current
    DESCRIPTION  "Total 3xx responses sent (last period)"
    ::= { perimetaGlobalStatsEntry 31 }

  globalStatSIP3XXResponsesRcvd OBJECT-TYPE
    SYNTAX       CounterBasedGauge64
    MAX-ACCESS   read-only
    STATUS       current
    DESCRIPTION  "Total 3xx responses received (last
                  period)"
    ::= { perimetaGlobalStatsEntry 32 }

  globalStatSIP4XXResponsesSent OBJECT-TYPE
    SYNTAX       CounterBasedGauge64
    MAX-ACCESS   read-only
    STATUS       current
    DESCRIPTION  "Total 4xx responses sent (last period)"
    ::= { perimetaGlobalStatsEntry 33 }

  globalStatSIP4XXResponsesRcvd OBJECT-TYPE
    SYNTAX       CounterBasedGauge64
    MAX-ACCESS   read-only
    STATUS       current
    DESCRIPTION  "Total 4xx responses received (last
                  period)"
    ::= { perimetaGlobalStatsEntry 34 }

  globalStatSIP5XXResponsesSent OBJECT-TYPE
    SYNTAX       CounterBasedGauge64
    MAX-ACCESS   read-only
    STATUS       current
    DESCRIPTION  "Total 5xx responses sent (last period)"
    ::= { perimetaGlobalStatsEntry 35 }

  globalStatSIP5XXResponsesRcvd OBJECT-TYPE
    SYNTAX       CounterBasedGauge64
    MAX-ACCESS   read-only
    STATUS       current
    DESCRIPTION  "Total 5xx responses received (last
                  period)"
    ::= { perimetaGlobalStatsEntry 36 }

  globalStatSIP6XXResponsesSent OBJECT-TYPE
    SYNTAX       CounterBasedGauge64
    MAX-ACCESS   read-only
    STATUS       current
    DESCRIPTION  "Total 6xx responses sent (last period)"
    ::= { perimetaGlobalStatsEntry 37 }

  globalStatSIP6XXResponsesRcvd OBJECT-TYPE
    SYNTAX       CounterBasedGauge64
    MAX-ACCESS   read-only
    STATUS       current
    DESCRIPTION  "Total 6xx responses received (last
                  period)"
    ::= { perimetaGlobalStatsEntry 38 }

  globalStatRTPOctetsSentRate OBJECT-TYPE
    SYNTAX       CounterBasedGauge64
    MAX-ACCESS   read-only
    STATUS       current
    DESCRIPTION  "RTP bytes sent per second"
    ::= { perimetaGlobalStatsEntry 39 }

  globalStatRTPOctetsRcvdRate OBJECT-TYPE
    SYNTAX       CounterBasedGauge64
    MAX-ACCESS   read-only
    STATUS       current
    DESCRIPTION  "RTP bytes received per second"
    ::= { perimetaGlobalStatsEntry 40 }

  globalStatRTPOctetsDiscardedPercent OBJECT-TYPE
    SYNTAX       CounterBasedGauge64
    UNITS        "/ 10000 %"
    MAX-ACCESS   read-only
    STATUS       current
    DESCRIPTION  "RTP bytes discarded (percentage of bytes
                  received)"
    ::= { perimetaGlobalStatsEntry 41 }

  globalStatRTPPktsSentRate OBJECT-TYPE
    SYNTAX       CounterBasedGauge64
    MAX-ACCESS   read-only
    STATUS       current
    DESCRIPTION  "RTP packets sent per second"
    ::= { perimetaGlobalStatsEntry 42 }

  globalStatRTPPktsReceivedRate OBJECT-TYPE
    SYNTAX       CounterBasedGauge64
    MAX-ACCESS   read-only
    STATUS       current
    DESCRIPTION  "RTP packets received per second"
    ::= { perimetaGlobalStatsEntry 43 }

  globalStatRTPPktsDiscardedPercent OBJECT-TYPE
    SYNTAX       CounterBasedGauge64
    UNITS        "/ 10000 %"
    MAX-ACCESS   read-only
    STATUS       current
    DESCRIPTION  "RTP packets discarded (percent of
                  packets received)"
    ::= { perimetaGlobalStatsEntry 44 }

  globalStatActiveSessions OBJECT-TYPE
    SYNTAX       CounterBasedGauge64
    MAX-ACCESS   read-only
    STATUS       current
    DESCRIPTION  "Active media sessions"
    ::= { perimetaGlobalStatsEntry 45 }

  globalStatPktsRcvd OBJECT-TYPE
    SYNTAX       CounterBasedGauge64
    MAX-ACCESS   read-only
    STATUS       current
    DESCRIPTION  "Total packets received (in the last
                  period)"
    ::= { perimetaGlobalStatsEntry 46 }

  globalStatPktsRcvdRate OBJECT-TYPE
    SYNTAX       CounterBasedGauge64
    MAX-ACCESS   read-only
    STATUS       current
    DESCRIPTION  "Packets received per second"
    ::= { perimetaGlobalStatsEntry 47 }

  globalStatSignalingPktsRcvd OBJECT-TYPE
    SYNTAX       CounterBasedGauge64
    MAX-ACCESS   read-only
    STATUS       current
    DESCRIPTION  "Total signaling packets received (last
                  period)"
    ::= { perimetaGlobalStatsEntry 48 }

  globalStatSignalingPktsRcvdRate OBJECT-TYPE
    SYNTAX       CounterBasedGauge64
    MAX-ACCESS   read-only
    STATUS       current
    DESCRIPTION  "Signaling packets received per second"
    ::= { perimetaGlobalStatsEntry 49 }

  globalStatMediaPktsRcvd OBJECT-TYPE
    SYNTAX       CounterBasedGauge64
    MAX-ACCESS   read-only
    STATUS       current
    DESCRIPTION  "Total media packets received (last
                  period)"
    ::= { perimetaGlobalStatsEntry 50 }

  globalStatMediaPktsRcvdRate OBJECT-TYPE
    SYNTAX       CounterBasedGauge64
    MAX-ACCESS   read-only
    STATUS       current
    DESCRIPTION  "Media packets received per second"
    ::= { perimetaGlobalStatsEntry 51 }

  globalStatOtherPktsRcvd OBJECT-TYPE
    SYNTAX       CounterBasedGauge64
    MAX-ACCESS   read-only
    STATUS       current
    DESCRIPTION  "Total other packets received (last
                  period)"
    ::= { perimetaGlobalStatsEntry 52 }

  globalStatOtherPktsRcvdRate OBJECT-TYPE
    SYNTAX       CounterBasedGauge64
    MAX-ACCESS   read-only
    STATUS       current
    DESCRIPTION  "Other packets received per second"
    ::= { perimetaGlobalStatsEntry 53 }

  globalStatSignalingPktsSent OBJECT-TYPE
    SYNTAX       CounterBasedGauge64
    MAX-ACCESS   read-only
    STATUS       current
    DESCRIPTION  "Total signaling packets sent (last
                  period)"
    ::= { perimetaGlobalStatsEntry 54 }

  globalStatSignalingPktsSentRate OBJECT-TYPE
    SYNTAX       CounterBasedGauge64
    MAX-ACCESS   read-only
    STATUS       current
    DESCRIPTION  "Signaling packets sent per second"
    ::= { perimetaGlobalStatsEntry 55 }

  globalStatSignalingPktsAccptd OBJECT-TYPE
    SYNTAX       CounterBasedGauge64
    MAX-ACCESS   read-only
    STATUS       current
    DESCRIPTION  "Total signaling packets accepted (last
                  period)"
    ::= { perimetaGlobalStatsEntry 56 }

  globalStatSignalingPktsAccptdRate OBJECT-TYPE
    SYNTAX       CounterBasedGauge64
    MAX-ACCESS   read-only
    STATUS       current
    DESCRIPTION  "Signaling packets accepted per second"
    ::= { perimetaGlobalStatsEntry 57 }

  globalStatSignalingPktsDropped OBJECT-TYPE
    SYNTAX       CounterBasedGauge64
    MAX-ACCESS   read-only
    STATUS       current
    DESCRIPTION  "Total signaling packets dropped (last
                  period)"
    ::= { perimetaGlobalStatsEntry 58 }

  globalStatSignalingPktsDroppedRate OBJECT-TYPE
    SYNTAX       CounterBasedGauge64
    MAX-ACCESS   read-only
    STATUS       current
    DESCRIPTION  "Signaling packets dropped per second"
    ::= { perimetaGlobalStatsEntry 59 }

  globalStatPriority1SigPktsRcvd OBJECT-TYPE
    SYNTAX       CounterBasedGauge64
    MAX-ACCESS   read-only
    STATUS       current
    DESCRIPTION  "Total priority 1 signaling packets
                  received (last period)"
    ::= { perimetaGlobalStatsEntry 60 }

  globalStatPriority1SigPktsRcvdRate OBJECT-TYPE
    SYNTAX       CounterBasedGauge64
    MAX-ACCESS   read-only
    STATUS       current
    DESCRIPTION  "Priority 1 signaling packets received
                  per second"
    ::= { perimetaGlobalStatsEntry 61 }

  globalStatPriority1SigPktsAccptd OBJECT-TYPE
    SYNTAX       CounterBasedGauge64
    MAX-ACCESS   read-only
    STATUS       current
    DESCRIPTION  "Total priority 1 signaling packets
                  accepted (last period)"
    ::= { perimetaGlobalStatsEntry 62 }

  globalStatPriority1SigPktsAccptdRate OBJECT-TYPE
    SYNTAX       CounterBasedGauge64
    MAX-ACCESS   read-only
    STATUS       current
    DESCRIPTION  "Priority 1 signaling packets accepted
                  per second"
    ::= { perimetaGlobalStatsEntry 63 }

  globalStatPriority1SigPktsDropped OBJECT-TYPE
    SYNTAX       CounterBasedGauge64
    MAX-ACCESS   read-only
    STATUS       current
    DESCRIPTION  "Total priority 1 signaling packets
                  dropped (last period)"
    ::= { perimetaGlobalStatsEntry 64 }

  globalStatPriority1SigPktsDroppedRate OBJECT-TYPE
    SYNTAX       CounterBasedGauge64
    MAX-ACCESS   read-only
    STATUS       current
    DESCRIPTION  "Priority 1 signaling packets dropped per
                  second"
    ::= { perimetaGlobalStatsEntry 65 }

  globalStatPriority2SigPktsRcvd OBJECT-TYPE
    SYNTAX       CounterBasedGauge64
    MAX-ACCESS   read-only
    STATUS       current
    DESCRIPTION  "Total priority 2 signaling packets
                  received (last period)"
    ::= { perimetaGlobalStatsEntry 66 }

  globalStatPriority2SigPktsRcvdRate OBJECT-TYPE
    SYNTAX       CounterBasedGauge64
    MAX-ACCESS   read-only
    STATUS       current
    DESCRIPTION  "Priority 2 signaling packets received
                  per second"
    ::= { perimetaGlobalStatsEntry 67 }

  globalStatPriority2SigPktsAccptd OBJECT-TYPE
    SYNTAX       CounterBasedGauge64
    MAX-ACCESS   read-only
    STATUS       current
    DESCRIPTION  "Total priority 2 signaling packets
                  accepted (last period)"
    ::= { perimetaGlobalStatsEntry 68 }

  globalStatPriority2SigPktsAccptdRate OBJECT-TYPE
    SYNTAX       CounterBasedGauge64
    MAX-ACCESS   read-only
    STATUS       current
    DESCRIPTION  "Priority 2 signaling packets accepted
                  per second"
    ::= { perimetaGlobalStatsEntry 69 }

  globalStatPriority2SigPktsDropped OBJECT-TYPE
    SYNTAX       CounterBasedGauge64
    MAX-ACCESS   read-only
    STATUS       current
    DESCRIPTION  "Total priority 2 signaling packets
                  dropped (last period)"
    ::= { perimetaGlobalStatsEntry 70 }

  globalStatPriority2SigPktsDroppedRate OBJECT-TYPE
    SYNTAX       CounterBasedGauge64
    MAX-ACCESS   read-only
    STATUS       current
    DESCRIPTION  "Priority 2 signaling packets dropped per
                  second"
    ::= { perimetaGlobalStatsEntry 71 }

  globalStatPriority3SigPktsRcvd OBJECT-TYPE
    SYNTAX       CounterBasedGauge64
    MAX-ACCESS   read-only
    STATUS       current
    DESCRIPTION  "Total priority 3 signaling packets
                  received (last period)"
    ::= { perimetaGlobalStatsEntry 72 }

  globalStatPriority3SigPktsRcvdRate OBJECT-TYPE
    SYNTAX       CounterBasedGauge64
    MAX-ACCESS   read-only
    STATUS       current
    DESCRIPTION  "Priority 3 signaling packets received
                  per second"
    ::= { perimetaGlobalStatsEntry 73 }

  globalStatPriority3SigPktsAccptd OBJECT-TYPE
    SYNTAX       CounterBasedGauge64
    MAX-ACCESS   read-only
    STATUS       current
    DESCRIPTION  "Total priority 3 signaling packets
                  accepted (last period)"
    ::= { perimetaGlobalStatsEntry 74 }

  globalStatPriority3SigPktsAccptdRate OBJECT-TYPE
    SYNTAX       CounterBasedGauge64
    MAX-ACCESS   read-only
    STATUS       current
    DESCRIPTION  "Priority 3 signaling packets accepted
                  per second"
    ::= { perimetaGlobalStatsEntry 75 }

  globalStatPriority3SigPktsDropped OBJECT-TYPE
    SYNTAX       CounterBasedGauge64
    MAX-ACCESS   read-only
    STATUS       current
    DESCRIPTION  "Total priority 3 signaling packets
                  dropped (last period)"
    ::= { perimetaGlobalStatsEntry 76 }

  globalStatPriority3SigPktsDroppedRate OBJECT-TYPE
    SYNTAX       CounterBasedGauge64
    MAX-ACCESS   read-only
    STATUS       current
    DESCRIPTION  "Priority 3 signaling packets dropped per
                  second"
    ::= { perimetaGlobalStatsEntry 77 }

  globalStatUnknownIPVersionSigPktsDropped OBJECT-TYPE
    SYNTAX       CounterBasedGauge64
    MAX-ACCESS   read-only
    STATUS       current
    DESCRIPTION  "Total signaling packets dropped due to
                  unknown IP version (last period)"
    ::= { perimetaGlobalStatsEntry 78 }

  globalStatUnknownIPVersionSigPktsDroppedRate OBJECT-TYPE
    SYNTAX       CounterBasedGauge64
    MAX-ACCESS   read-only
    STATUS       current
    DESCRIPTION  "Signaling packets dropped due to unknown
                  IP version per second"
    ::= { perimetaGlobalStatsEntry 79 }

  globalStatBlacklistedSigPktsDropped OBJECT-TYPE
    SYNTAX       CounterBasedGauge64
    MAX-ACCESS   read-only
    STATUS       current
    DESCRIPTION  "Total signaling packets dropped due to
                  blacklisting (last period)"
    ::= { perimetaGlobalStatsEntry 80 }

  globalStatBlacklistedSigPktsDroppedRate OBJECT-TYPE
    SYNTAX       CounterBasedGauge64
    MAX-ACCESS   read-only
    STATUS       current
    DESCRIPTION  "Signaling packets dropped due to
                  blacklisting per second"
    ::= { perimetaGlobalStatsEntry 81 }

  globalStatNoServicePortSigPktsDropped OBJECT-TYPE
    SYNTAX       CounterBasedGauge64
    MAX-ACCESS   read-only
    STATUS       current
    DESCRIPTION  "Total signaling packets dropped due to
                  no service port (last period)"
    ::= { perimetaGlobalStatsEntry 82 }

  globalStatNoServicePortSigPktsDroppedRate OBJECT-TYPE
    SYNTAX       CounterBasedGauge64
    MAX-ACCESS   read-only
    STATUS       current
    DESCRIPTION  "Signaling packets dropped due to no
                  service port per second"
    ::= { perimetaGlobalStatsEntry 83 }

  globalStatFixedRateLimitSigPktsDropped OBJECT-TYPE
    SYNTAX       CounterBasedGauge64
    MAX-ACCESS   read-only
    STATUS       current
    DESCRIPTION  "Total signaling packets dropped due to
                  fixed-rate limit (last period)"
    ::= { perimetaGlobalStatsEntry 84 }

  globalStatFixedRateLimitSigPktsDroppedRate OBJECT-TYPE
    SYNTAX       CounterBasedGauge64
    MAX-ACCESS   read-only
    STATUS       current
    DESCRIPTION  "Signaling packets dropped due to
                  fixed-rate limit per second"
    ::= { perimetaGlobalStatsEntry 85 }

  globalStatAdaptiveRateLimitSigPktsDropped OBJECT-TYPE
    SYNTAX       CounterBasedGauge64
    MAX-ACCESS   read-only
    STATUS       current
    DESCRIPTION  "Total signaling packets dropped due to
                  adaptive-rate limit (last period)"
    ::= { perimetaGlobalStatsEntry 86 }

  globalStatAdaptiveRateLimitSigPktsDroppedRate OBJECT-TYPE
    SYNTAX       CounterBasedGauge64
    MAX-ACCESS   read-only
    STATUS       current
    DESCRIPTION  "Signaling packets dropped due to
                  adaptive-rate limit per second"
    ::= { perimetaGlobalStatsEntry 87 }

  globalStatCongestedSigPktsDropped OBJECT-TYPE
    SYNTAX       CounterBasedGauge64
    MAX-ACCESS   read-only
    STATUS       current
    DESCRIPTION  "Total signaling packets dropped due to
                  congestion (last period)"
    ::= { perimetaGlobalStatsEntry 88 }

  globalStatCongestedSigPktsDroppedRate OBJECT-TYPE
    SYNTAX       CounterBasedGauge64
    MAX-ACCESS   read-only
    STATUS       current
    DESCRIPTION  "Signaling packets dropped due to
                  congestion per second"
    ::= { perimetaGlobalStatsEntry 89 }

  globalStatBadICMPSigPktsDropped OBJECT-TYPE
    SYNTAX       CounterBasedGauge64
    MAX-ACCESS   read-only
    STATUS       current
    DESCRIPTION  "Total signaling packets dropped due to
                  ICMP errors (last period)"
    ::= { perimetaGlobalStatsEntry 90 }

  globalStatBadICMPSigPktsDroppedRate OBJECT-TYPE
    SYNTAX       CounterBasedGauge64
    MAX-ACCESS   read-only
    STATUS       current
    DESCRIPTION  "Signaling packets dropped due to ICMP
                  errors per second"
    ::= { perimetaGlobalStatsEntry 91 }

  globalStatTCPSYNSigPktsDropped OBJECT-TYPE
    SYNTAX       CounterBasedGauge64
    MAX-ACCESS   read-only
    STATUS       current
    DESCRIPTION  "Total signaling packets dropped due to
                  SYN failure (last period)"
    ::= { perimetaGlobalStatsEntry 92 }

  globalStatTCPSYNSigPktsDroppedRate OBJECT-TYPE
    SYNTAX       CounterBasedGauge64
    MAX-ACCESS   read-only
    STATUS       current
    DESCRIPTION  "Signaling packets dropped due to SYN
                  failure per second"
    ::= { perimetaGlobalStatsEntry 93 }

  globalStatCallSetupFailurePercent OBJECT-TYPE
    SYNTAX       CounterBasedGauge64
    UNITS        "/ 10000 %"
    MAX-ACCESS   read-only
    STATUS       current
    DESCRIPTION  "Total percentage of call setup attempts
                  failing"
    ::= { perimetaGlobalStatsEntry 94 }

  globalStatNumberAnalysisCallSetupFailPercent OBJECT-TYPE
    SYNTAX       CounterBasedGauge64
    UNITS        "/ 10000 %"
    MAX-ACCESS   read-only
    STATUS       current
    DESCRIPTION  "Percentage of call setup attempts
                  failing due to number analysis"
    ::= { perimetaGlobalStatsEntry 95 }

  globalStatRoutingCallSetupFailurePercent OBJECT-TYPE
    SYNTAX       CounterBasedGauge64
    UNITS        "/ 10000 %"
    MAX-ACCESS   read-only
    STATUS       current
    DESCRIPTION  "Percentage of call setup attempts
                  failing due to routing policy"
    ::= { perimetaGlobalStatsEntry 96 }

  globalStatCapacityControlCallStpFailrePrcnt OBJECT-TYPE
    SYNTAX       CounterBasedGauge64
    UNITS        "/ 10000 %"
    MAX-ACCESS   read-only
    STATUS       current
    DESCRIPTION  "Percentage of call setup attempts
                  failing due to capacity control"
    ::= { perimetaGlobalStatsEntry 97 }

  globalStatActiveCalls OBJECT-TYPE
    SYNTAX       CounterBasedGauge64
    MAX-ACCESS   read-only
    STATUS       current
    DESCRIPTION  "Currently active calls"
    ::= { perimetaGlobalStatsEntry 98 }

  globalStatActivatingCalls OBJECT-TYPE
    SYNTAX       CounterBasedGauge64
    MAX-ACCESS   read-only
    STATUS       current
    DESCRIPTION  "Currently activating calls"
    ::= { perimetaGlobalStatsEntry 99 }

  globalStatDeactivatingCalls OBJECT-TYPE
    SYNTAX       CounterBasedGauge64
    MAX-ACCESS   read-only
    STATUS       current
    DESCRIPTION  "Currently deactivating calls"
    ::= { perimetaGlobalStatsEntry 100 }

  globalStatCallAttemptRate OBJECT-TYPE
    SYNTAX       CounterBasedGauge64
    MAX-ACCESS   read-only
    STATUS       current
    DESCRIPTION  "Call setup attempts per second"
    ::= { perimetaGlobalStatsEntry 101 }

  globalStatCallAttemptFailureRate OBJECT-TYPE
    SYNTAX       CounterBasedGauge64
    MAX-ACCESS   read-only
    STATUS       current
    DESCRIPTION  "Failed call setup attempts per second"
    ::= { perimetaGlobalStatsEntry 102 }

  globalStatActiveCallFailuresPercent OBJECT-TYPE
    SYNTAX       CounterBasedGauge64
    UNITS        "/ 10000 %"
    MAX-ACCESS   read-only
    STATUS       current
    DESCRIPTION  "Active call failures (percentage of all
                  active calls)"
    ::= { perimetaGlobalStatsEntry 103 }

  globalStatActiveEmergencyCalls OBJECT-TYPE
    SYNTAX       CounterBasedGauge64
    MAX-ACCESS   read-only
    STATUS       current
    DESCRIPTION  "Currently active priority calls"
    ::= { perimetaGlobalStatsEntry 104 }

  globalStatActiveIPSecCalls OBJECT-TYPE
    SYNTAX       CounterBasedGauge64
    MAX-ACCESS   read-only
    STATUS       current
    DESCRIPTION  "Number of IPSec IMS-AKA calls"
    ::= { perimetaGlobalStatsEntry 105 }

  globalStatActiveSubscribers OBJECT-TYPE
    SYNTAX       CounterBasedGauge64
    MAX-ACCESS   read-only
    STATUS       current
    DESCRIPTION  "Number of registered subscribers"
    ::= { perimetaGlobalStatsEntry 106 }

  globalStatRXCallSetupFailureRate OBJECT-TYPE
    SYNTAX       CounterBasedGauge64
    MAX-ACCESS   read-only
    STATUS       current
    DESCRIPTION  "Rx call setup failures (failures/s)"
    ::= { perimetaGlobalStatsEntry 107 }

  globalStatRXRenegotiationAttemptRate OBJECT-TYPE
    SYNTAX       CounterBasedGauge64
    MAX-ACCESS   read-only
    STATUS       current
    DESCRIPTION  "Rx call renegotiation attempts
                  (attempts/s)"
    ::= { perimetaGlobalStatsEntry 108 }

  globalStatRXRenegotiationFailureRate OBJECT-TYPE
    SYNTAX       CounterBasedGauge64
    MAX-ACCESS   read-only
    STATUS       current
    DESCRIPTION  "Rx call renegotiation failures
                  (failures/s)"
    ::= { perimetaGlobalStatsEntry 109 }

  globalStatMalformedDiameterPktsRcvdRate OBJECT-TYPE
    SYNTAX       CounterBasedGauge64
    MAX-ACCESS   read-only
    STATUS       current
    DESCRIPTION  "Malformed Diameter packets rcvd
                  (packets/s)"
    ::= { perimetaGlobalStatsEntry 110 }

  globalStatDiameterPktsRcvdRate OBJECT-TYPE
    SYNTAX       CounterBasedGauge64
    MAX-ACCESS   read-only
    STATUS       current
    DESCRIPTION  "Total Diameter packets rcvd (packets/s)"
    ::= { perimetaGlobalStatsEntry 111 }

  globalStatMalformedDiameterPktsRcvdPercent OBJECT-TYPE
    SYNTAX       CounterBasedGauge64
    MAX-ACCESS   read-only
    STATUS       current
    DESCRIPTION  "Malformed Diameter packets rcvd (% vs
                  packets rcvd)"
    ::= { perimetaGlobalStatsEntry 112 }

  globalStatDiamAnswrMsgsUnknwnHopByHopIDRcvdRate OBJECT-TYPE
    SYNTAX       CounterBasedGauge64
    MAX-ACCESS   read-only
    STATUS       current
    DESCRIPTION  "Diameter answer msgs rcvd with unknown
                  Hop-By-Hop id (msgs/s)"
    ::= { perimetaGlobalStatsEntry 113 }

  globalStatDiamPktsUnknwnCommandCodeRcvdRate OBJECT-TYPE
    SYNTAX       CounterBasedGauge64
    MAX-ACCESS   read-only
    STATUS       current
    DESCRIPTION  "Diameter packets rcvd with unknown
                  command code (packets/s)"
    ::= { perimetaGlobalStatsEntry 114 }

  globalStatDiamAnswrMsgsWthPrtclErrRcvdRate OBJECT-TYPE
    SYNTAX       CounterBasedGauge64
    MAX-ACCESS   read-only
    STATUS       current
    DESCRIPTION  "Diameter answer msgs rcvd with protocol
                  error (msgs/s)"
    ::= { perimetaGlobalStatsEntry 115 }

  globalStatDiamTrnsprtReqsWthTransntFailrsRate OBJECT-TYPE
    SYNTAX       CounterBasedGauge64
    MAX-ACCESS   read-only
    STATUS       current
    DESCRIPTION  "Diameter transport reqs not satisfied
                  due to transient failure (req/s)"
    ::= { perimetaGlobalStatsEntry 116 }

  globalStatDiamTrnsprtReqsWthPermFailrsRate OBJECT-TYPE
    SYNTAX       CounterBasedGauge64
    MAX-ACCESS   read-only
    STATUS       current
    DESCRIPTION  "Diameter transport reqs not satisfied
                  due to permanent failure (req/s)"
    ::= { perimetaGlobalStatsEntry 117 }

  globalStatDiamTrnsprtReqsWthUnexpctdFailrRate OBJECT-TYPE
    SYNTAX       CounterBasedGauge64
    MAX-ACCESS   read-only
    STATUS       current
    DESCRIPTION  "Diameter transport reqs not satisfied
                  due to unexpected failure (req/s)"
    ::= { perimetaGlobalStatsEntry 118 }

  globalStatSIPSignalingRate OBJECT-TYPE
    SYNTAX       CounterBasedGauge64
    MAX-ACCESS   read-only
    STATUS       current
    DESCRIPTION  "SIP Signaling Rate"
    ::= { perimetaGlobalStatsEntry 119 }

  globalStatUsedSessionPerc OBJECT-TYPE
    SYNTAX       CounterBasedGauge64
    UNITS        "/ 10000 %"
    MAX-ACCESS   read-only
    STATUS       current
    DESCRIPTION  "Percentage of used media sessions"
    ::= { perimetaGlobalStatsEntry 120 }

  globalStatPriority4SigPktsRcvd OBJECT-TYPE
    SYNTAX       CounterBasedGauge64
    MAX-ACCESS   read-only
    STATUS       current
    DESCRIPTION  "Total priority 4 signaling packets
                  received (last period)"
    ::= { perimetaGlobalStatsEntry 121 }

  globalStatPriority4SigPktsRcvdRate OBJECT-TYPE
    SYNTAX       CounterBasedGauge64
    MAX-ACCESS   read-only
    STATUS       current
    DESCRIPTION  "Priority 4 signaling packets received
                  per second"
    ::= { perimetaGlobalStatsEntry 122 }

  globalStatPriority4SigPktsAccptd OBJECT-TYPE
    SYNTAX       CounterBasedGauge64
    MAX-ACCESS   read-only
    STATUS       current
    DESCRIPTION  "Total priority 4 signaling packets
                  accepted (last period)"
    ::= { perimetaGlobalStatsEntry 123 }

  globalStatPriority4SigPktsAccptdRate OBJECT-TYPE
    SYNTAX       CounterBasedGauge64
    MAX-ACCESS   read-only
    STATUS       current
    DESCRIPTION  "Priority 4 signaling packets accepted
                  per second"
    ::= { perimetaGlobalStatsEntry 124 }

  globalStatPriority4SigPktsDropped OBJECT-TYPE
    SYNTAX       CounterBasedGauge64
    MAX-ACCESS   read-only
    STATUS       current
    DESCRIPTION  "Total priority 4 signaling packets
                  dropped (last period)"
    ::= { perimetaGlobalStatsEntry 125 }

  globalStatPriority4SigPktsDroppedRate OBJECT-TYPE
    SYNTAX       CounterBasedGauge64
    MAX-ACCESS   read-only
    STATUS       current
    DESCRIPTION  "Priority 4 signaling packets dropped per
                  second"
    ::= { perimetaGlobalStatsEntry 126 }

  globalStatPriority5SigPktsRcvd OBJECT-TYPE
    SYNTAX       CounterBasedGauge64
    MAX-ACCESS   read-only
    STATUS       current
    DESCRIPTION  "Total priority 5 signaling packets
                  received (last period)"
    ::= { perimetaGlobalStatsEntry 127 }

  globalStatPriority5SigPktsRcvdRate OBJECT-TYPE
    SYNTAX       CounterBasedGauge64
    MAX-ACCESS   read-only
    STATUS       current
    DESCRIPTION  "Priority 5 signaling packets received
                  per second"
    ::= { perimetaGlobalStatsEntry 128 }

  globalStatPriority5SigPktsAccptd OBJECT-TYPE
    SYNTAX       CounterBasedGauge64
    MAX-ACCESS   read-only
    STATUS       current
    DESCRIPTION  "Total priority 5 signaling packets
                  accepted (last period)"
    ::= { perimetaGlobalStatsEntry 129 }

  globalStatPriority5SigPktsAccptdRate OBJECT-TYPE
    SYNTAX       CounterBasedGauge64
    MAX-ACCESS   read-only
    STATUS       current
    DESCRIPTION  "Priority 5 signaling packets accepted
                  per second"
    ::= { perimetaGlobalStatsEntry 130 }

  globalStatPriority5SigPktsDropped OBJECT-TYPE
    SYNTAX       CounterBasedGauge64
    MAX-ACCESS   read-only
    STATUS       current
    DESCRIPTION  "Total priority 5 signaling packets
                  dropped (last period)"
    ::= { perimetaGlobalStatsEntry 131 }

  globalStatPriority5SigPktsDroppedRate OBJECT-TYPE
    SYNTAX       CounterBasedGauge64
    MAX-ACCESS   read-only
    STATUS       current
    DESCRIPTION  "Priority 5 signaling packets dropped per
                  second"
    ::= { perimetaGlobalStatsEntry 132 }

  globalStatPriority6SigPktsRcvd OBJECT-TYPE
    SYNTAX       CounterBasedGauge64
    MAX-ACCESS   read-only
    STATUS       current
    DESCRIPTION  "Total priority 6 signaling packets
                  received (last period)"
    ::= { perimetaGlobalStatsEntry 133 }

  globalStatPriority6SigPktsRcvdRate OBJECT-TYPE
    SYNTAX       CounterBasedGauge64
    MAX-ACCESS   read-only
    STATUS       current
    DESCRIPTION  "Priority 6 signaling packets received
                  per second"
    ::= { perimetaGlobalStatsEntry 134 }

  globalStatPriority6SigPktsAccptd OBJECT-TYPE
    SYNTAX       CounterBasedGauge64
    MAX-ACCESS   read-only
    STATUS       current
    DESCRIPTION  "Total priority 6 signaling packets
                  accepted (last period)"
    ::= { perimetaGlobalStatsEntry 135 }

  globalStatPriority6SigPktsAccptdRate OBJECT-TYPE
    SYNTAX       CounterBasedGauge64
    MAX-ACCESS   read-only
    STATUS       current
    DESCRIPTION  "Priority 6 signaling packets accepted
                  per second"
    ::= { perimetaGlobalStatsEntry 136 }

  globalStatPriority6SigPktsDropped OBJECT-TYPE
    SYNTAX       CounterBasedGauge64
    MAX-ACCESS   read-only
    STATUS       current
    DESCRIPTION  "Total priority 6 signaling packets
                  dropped (last period)"
    ::= { perimetaGlobalStatsEntry 137 }

  globalStatPriority6SigPktsDroppedRate OBJECT-TYPE
    SYNTAX       CounterBasedGauge64
    MAX-ACCESS   read-only
    STATUS       current
    DESCRIPTION  "Priority 6 signaling packets dropped per
                  second"
    ::= { perimetaGlobalStatsEntry 138 }

  globalStatPriority1SigBytesRcvd OBJECT-TYPE
    SYNTAX       CounterBasedGauge64
    MAX-ACCESS   read-only
    STATUS       current
    DESCRIPTION  "Total priority 1 signaling bytes
                  received (last period)"
    ::= { perimetaGlobalStatsEntry 139 }

  globalStatPriority1SigBytesRcvdRate OBJECT-TYPE
    SYNTAX       CounterBasedGauge64
    MAX-ACCESS   read-only
    STATUS       current
    DESCRIPTION  "Priority 1 signaling bytes received per
                  second"
    ::= { perimetaGlobalStatsEntry 140 }

  globalStatPriority1SigBytesAccptd OBJECT-TYPE
    SYNTAX       CounterBasedGauge64
    MAX-ACCESS   read-only
    STATUS       current
    DESCRIPTION  "Total priority 1 signaling bytes
                  accepted (last period)"
    ::= { perimetaGlobalStatsEntry 141 }

  globalStatPriority1SigBytesAccptdRate OBJECT-TYPE
    SYNTAX       CounterBasedGauge64
    MAX-ACCESS   read-only
    STATUS       current
    DESCRIPTION  "Priority 1 signaling bytes accepted per
                  second"
    ::= { perimetaGlobalStatsEntry 142 }

  globalStatPriority1SigBytesDropped OBJECT-TYPE
    SYNTAX       CounterBasedGauge64
    MAX-ACCESS   read-only
    STATUS       current
    DESCRIPTION  "Total priority 1 signaling bytes dropped
                  (last period)"
    ::= { perimetaGlobalStatsEntry 143 }

  globalStatPriority1SigBytesDroppedRate OBJECT-TYPE
    SYNTAX       CounterBasedGauge64
    MAX-ACCESS   read-only
    STATUS       current
    DESCRIPTION  "Priority 1 signaling bytes dropped per
                  second"
    ::= { perimetaGlobalStatsEntry 144 }

  globalStatPriority2SigBytesRcvd OBJECT-TYPE
    SYNTAX       CounterBasedGauge64
    MAX-ACCESS   read-only
    STATUS       current
    DESCRIPTION  "Total priority 2 signaling bytes
                  received (last period)"
    ::= { perimetaGlobalStatsEntry 145 }

  globalStatPriority2SigBytesRcvdRate OBJECT-TYPE
    SYNTAX       CounterBasedGauge64
    MAX-ACCESS   read-only
    STATUS       current
    DESCRIPTION  "Priority 2 signaling bytes received per
                  second"
    ::= { perimetaGlobalStatsEntry 146 }

  globalStatPriority2SigBytesAccptd OBJECT-TYPE
    SYNTAX       CounterBasedGauge64
    MAX-ACCESS   read-only
    STATUS       current
    DESCRIPTION  "Total priority 2 signaling bytes
                  accepted (last period)"
    ::= { perimetaGlobalStatsEntry 147 }

  globalStatPriority2SigBytesAccptdRate OBJECT-TYPE
    SYNTAX       CounterBasedGauge64
    MAX-ACCESS   read-only
    STATUS       current
    DESCRIPTION  "Priority 2 signaling bytes accepted per
                  second"
    ::= { perimetaGlobalStatsEntry 148 }

  globalStatPriority2SigBytesDropped OBJECT-TYPE
    SYNTAX       CounterBasedGauge64
    MAX-ACCESS   read-only
    STATUS       current
    DESCRIPTION  "Total priority 2 signaling bytes dropped
                  (last period)"
    ::= { perimetaGlobalStatsEntry 149 }

  globalStatPriority2SigBytesDroppedRate OBJECT-TYPE
    SYNTAX       CounterBasedGauge64
    MAX-ACCESS   read-only
    STATUS       current
    DESCRIPTION  "Priority 2 signaling bytes dropped per
                  second"
    ::= { perimetaGlobalStatsEntry 150 }

  globalStatPriority3SigBytesRcvd OBJECT-TYPE
    SYNTAX       CounterBasedGauge64
    MAX-ACCESS   read-only
    STATUS       current
    DESCRIPTION  "Total priority 3 signaling bytes
                  received (last period)"
    ::= { perimetaGlobalStatsEntry 151 }

  globalStatPriority3SigBytesRcvdRate OBJECT-TYPE
    SYNTAX       CounterBasedGauge64
    MAX-ACCESS   read-only
    STATUS       current
    DESCRIPTION  "Priority 3 signaling bytes received per
                  second"
    ::= { perimetaGlobalStatsEntry 152 }

  globalStatPriority3SigBytesAccptd OBJECT-TYPE
    SYNTAX       CounterBasedGauge64
    MAX-ACCESS   read-only
    STATUS       current
    DESCRIPTION  "Total priority 3 signaling bytes
                  accepted (last period)"
    ::= { perimetaGlobalStatsEntry 153 }

  globalStatPriority3SigBytesAccptdRate OBJECT-TYPE
    SYNTAX       CounterBasedGauge64
    MAX-ACCESS   read-only
    STATUS       current
    DESCRIPTION  "Priority 3 signaling bytes accepted per
                  second"
    ::= { perimetaGlobalStatsEntry 154 }

  globalStatPriority3SigBytesDropped OBJECT-TYPE
    SYNTAX       CounterBasedGauge64
    MAX-ACCESS   read-only
    STATUS       current
    DESCRIPTION  "Total priority 3 signaling bytes dropped
                  (last period)"
    ::= { perimetaGlobalStatsEntry 155 }

  globalStatPriority3SigBytesDroppedRate OBJECT-TYPE
    SYNTAX       CounterBasedGauge64
    MAX-ACCESS   read-only
    STATUS       current
    DESCRIPTION  "Priority 3 signaling bytes dropped per
                  second"
    ::= { perimetaGlobalStatsEntry 156 }

  globalStatPriority4SigBytesRcvd OBJECT-TYPE
    SYNTAX       CounterBasedGauge64
    MAX-ACCESS   read-only
    STATUS       current
    DESCRIPTION  "Total priority 4 signaling bytes
                  received (last period)"
    ::= { perimetaGlobalStatsEntry 157 }

  globalStatPriority4SigBytesRcvdRate OBJECT-TYPE
    SYNTAX       CounterBasedGauge64
    MAX-ACCESS   read-only
    STATUS       current
    DESCRIPTION  "Priority 4 signaling bytes received per
                  second"
    ::= { perimetaGlobalStatsEntry 158 }

  globalStatPriority4SigBytesAccptd OBJECT-TYPE
    SYNTAX       CounterBasedGauge64
    MAX-ACCESS   read-only
    STATUS       current
    DESCRIPTION  "Total priority 4 signaling bytes
                  accepted (last period)"
    ::= { perimetaGlobalStatsEntry 159 }

  globalStatPriority4SigBytesAccptdRate OBJECT-TYPE
    SYNTAX       CounterBasedGauge64
    MAX-ACCESS   read-only
    STATUS       current
    DESCRIPTION  "Priority 4 signaling bytes accepted per
                  second"
    ::= { perimetaGlobalStatsEntry 160 }

  globalStatPriority4SigBytesDropped OBJECT-TYPE
    SYNTAX       CounterBasedGauge64
    MAX-ACCESS   read-only
    STATUS       current
    DESCRIPTION  "Total priority 4 signaling bytes dropped
                  (last period)"
    ::= { perimetaGlobalStatsEntry 161 }

  globalStatPriority4SigBytesDroppedRate OBJECT-TYPE
    SYNTAX       CounterBasedGauge64
    MAX-ACCESS   read-only
    STATUS       current
    DESCRIPTION  "Priority 4 signaling bytes dropped per
                  second"
    ::= { perimetaGlobalStatsEntry 162 }

  globalStatPriority5SigBytesRcvd OBJECT-TYPE
    SYNTAX       CounterBasedGauge64
    MAX-ACCESS   read-only
    STATUS       current
    DESCRIPTION  "Total priority 5 signaling bytes
                  received (last period)"
    ::= { perimetaGlobalStatsEntry 163 }

  globalStatPriority5SigBytesRcvdRate OBJECT-TYPE
    SYNTAX       CounterBasedGauge64
    MAX-ACCESS   read-only
    STATUS       current
    DESCRIPTION  "Priority 5 signaling bytes received per
                  second"
    ::= { perimetaGlobalStatsEntry 164 }

  globalStatPriority5SigBytesAccptd OBJECT-TYPE
    SYNTAX       CounterBasedGauge64
    MAX-ACCESS   read-only
    STATUS       current
    DESCRIPTION  "Total priority 5 signaling bytes
                  accepted (last period)"
    ::= { perimetaGlobalStatsEntry 165 }

  globalStatPriority5SigBytesAccptdRate OBJECT-TYPE
    SYNTAX       CounterBasedGauge64
    MAX-ACCESS   read-only
    STATUS       current
    DESCRIPTION  "Priority 5 signaling bytes accepted per
                  second"
    ::= { perimetaGlobalStatsEntry 166 }

  globalStatPriority5SigBytesDropped OBJECT-TYPE
    SYNTAX       CounterBasedGauge64
    MAX-ACCESS   read-only
    STATUS       current
    DESCRIPTION  "Total priority 5 signaling bytes dropped
                  (last period)"
    ::= { perimetaGlobalStatsEntry 167 }

  globalStatPriority5SigBytesDroppedRate OBJECT-TYPE
    SYNTAX       CounterBasedGauge64
    MAX-ACCESS   read-only
    STATUS       current
    DESCRIPTION  "Priority 5 signaling bytes dropped per
                  second"
    ::= { perimetaGlobalStatsEntry 168 }

  globalStatPriority6SigBytesRcvd OBJECT-TYPE
    SYNTAX       CounterBasedGauge64
    MAX-ACCESS   read-only
    STATUS       current
    DESCRIPTION  "Total priority 6 signaling bytes
                  received (last period)"
    ::= { perimetaGlobalStatsEntry 169 }

  globalStatPriority6SigBytesRcvdRate OBJECT-TYPE
    SYNTAX       CounterBasedGauge64
    MAX-ACCESS   read-only
    STATUS       current
    DESCRIPTION  "Priority 6 signaling bytes received per
                  second"
    ::= { perimetaGlobalStatsEntry 170 }

  globalStatPriority6SigBytesAccptd OBJECT-TYPE
    SYNTAX       CounterBasedGauge64
    MAX-ACCESS   read-only
    STATUS       current
    DESCRIPTION  "Total priority 6 signaling bytes
                  accepted (last period)"
    ::= { perimetaGlobalStatsEntry 171 }

  globalStatPriority6SigBytesAccptdRate OBJECT-TYPE
    SYNTAX       CounterBasedGauge64
    MAX-ACCESS   read-only
    STATUS       current
    DESCRIPTION  "Priority 6 signaling bytes accepted per
                  second"
    ::= { perimetaGlobalStatsEntry 172 }

  globalStatPriority6SigBytesDropped OBJECT-TYPE
    SYNTAX       CounterBasedGauge64
    MAX-ACCESS   read-only
    STATUS       current
    DESCRIPTION  "Total priority 6 signaling bytes dropped
                  (last period)"
    ::= { perimetaGlobalStatsEntry 173 }

  globalStatPriority6SigBytesDroppedRate OBJECT-TYPE
    SYNTAX       CounterBasedGauge64
    MAX-ACCESS   read-only
    STATUS       current
    DESCRIPTION  "Priority 6 signaling bytes dropped per
                  second"
    ::= { perimetaGlobalStatsEntry 174 }

  globalStatActiveSrtpIwCalls OBJECT-TYPE
    SYNTAX       CounterBasedGauge64
    MAX-ACCESS   read-only
    STATUS       current
    DESCRIPTION  "Number of SRTP interworked calls"
    ::= { perimetaGlobalStatsEntry 175 }

  globalStatActiveEmergencySessions OBJECT-TYPE
    SYNTAX       CounterBasedGauge64
    MAX-ACCESS   read-only
    STATUS       current
    DESCRIPTION  "Active priority media sessions"
    ::= { perimetaGlobalStatsEntry 176 }

  globalStatUnclassPktRate OBJECT-TYPE
    SYNTAX       CounterBasedGauge64
    MAX-ACCESS   read-only
    STATUS       current
    DESCRIPTION  "Unclassified media packets dropped per
                  second"
    ::= { perimetaGlobalStatsEntry 177 }

  globalStatCPUMaxSig OBJECT-TYPE
    SYNTAX       CounterBasedGauge64
    UNITS        "/ 10000 %"
    MAX-ACCESS   read-only
    STATUS       current
    DESCRIPTION  "Signaling CPU"
    ::= { perimetaGlobalStatsEntry 178 }

  globalStatCPUMaxSipMsg OBJECT-TYPE
    SYNTAX       CounterBasedGauge64
    UNITS        "/ 10000 %"
    MAX-ACCESS   read-only
    STATUS       current
    DESCRIPTION  "SIP Message Processing CPU"
    ::= { perimetaGlobalStatsEntry 179 }

  globalStatCPUMaxCore OBJECT-TYPE
    SYNTAX       CounterBasedGauge64
    UNITS        "/ 10000 %"
    MAX-ACCESS   read-only
    STATUS       current
    DESCRIPTION  "Total CPU usage"
    ::= { perimetaGlobalStatsEntry 180 }

  globalStatFreeMem OBJECT-TYPE
    SYNTAX       CounterBasedGauge64
    MAX-ACCESS   read-only
    STATUS       current
    DESCRIPTION  "Free memory (MB)"
    ::= { perimetaGlobalStatsEntry 181 }

  globalStatMediaPktSentRate OBJECT-TYPE
    SYNTAX       CounterBasedGauge64
    MAX-ACCESS   read-only
    STATUS       current
    DESCRIPTION  "Media packets sent per second"
    ::= { perimetaGlobalStatsEntry 182 }

  globalStatIncomingQueueErr OBJECT-TYPE
    SYNTAX       CounterBasedGauge64
    MAX-ACCESS   read-only
    STATUS       current
    DESCRIPTION  "Total incoming queue errors"
    ::= { perimetaGlobalStatsEntry 183 }

  globalStatPktSentRate OBJECT-TYPE
    SYNTAX       CounterBasedGauge64
    MAX-ACCESS   read-only
    STATUS       current
    DESCRIPTION  "Packets sent per second"
    ::= { perimetaGlobalStatsEntry 184 }

  globalStatUsedCapacityPerc OBJECT-TYPE
    SYNTAX       CounterBasedGauge64
    UNITS        "/ 10000 %"
    MAX-ACCESS   read-only
    STATUS       current
    DESCRIPTION  "Percentage of used media capacity units"
    ::= { perimetaGlobalStatsEntry 185 }

  globalStatsOverallCapacityPerc OBJECT-TYPE
    SYNTAX       CounterBasedGauge64
    UNITS        "/ 10000 %"
    MAX-ACCESS   read-only
    STATUS       current
    DESCRIPTION  "Overall media capacity percent usage"
    ::= { perimetaGlobalStatsEntry 186 }

  globalStatTotalIPsecCallsMade OBJECT-TYPE
    SYNTAX       CounterBasedGauge64
    MAX-ACCESS   read-only
    STATUS       current
    DESCRIPTION  "Total calls using IPsec IMS-AKA
                  signaling (last period)"
    ::= { perimetaGlobalStatsEntry 187 }

  globalStatSRTPIWSessions OBJECT-TYPE
    SYNTAX       CounterBasedGauge64
    MAX-ACCESS   read-only
    STATUS       current
    DESCRIPTION  "Sessions with SRTP interworking"
    ::= { perimetaGlobalStatsEntry 188 }

  globalStatActiveCallsTranscTrig OBJECT-TYPE
    SYNTAX       CounterBasedGauge64
    MAX-ACCESS   read-only
    STATUS       current
    DESCRIPTION  "Calls with transcoding triggered"
    ::= { perimetaGlobalStatsEntry 189 }

  globalStatActiveCallsTranscUsed OBJECT-TYPE
    SYNTAX       CounterBasedGauge64
    MAX-ACCESS   read-only
    STATUS       current
    DESCRIPTION  "Calls using transcoding"
    ::= { perimetaGlobalStatsEntry 190 }

  globalStatCallsTriggeredTransc OBJECT-TYPE
    SYNTAX       CounterBasedGauge64
    MAX-ACCESS   read-only
    STATUS       current
    DESCRIPTION  "Calls that triggered transcoding (last
                  period)"
    ::= { perimetaGlobalStatsEntry 191 }

  globalStatCallsUsedTransc OBJECT-TYPE
    SYNTAX       CounterBasedGauge64
    MAX-ACCESS   read-only
    STATUS       current
    DESCRIPTION  "Calls that used transcoding (last
                  period)"
    ::= { perimetaGlobalStatsEntry 192 }

  globalStatActiveH323Calls OBJECT-TYPE
    SYNTAX       CounterBasedGauge64
    MAX-ACCESS   read-only
    STATUS       current
    DESCRIPTION  "Number of H.323 calls currently active
                  or being set up"
    ::= { perimetaGlobalStatsEntry 193 }

  globalStatTCPMediaPktsRcvdCount OBJECT-TYPE
    SYNTAX       CounterBasedGauge64
    MAX-ACCESS   read-only
    STATUS       current
    DESCRIPTION  "Total TCP media packets received (last
                  period)"
    ::= { perimetaGlobalStatsEntry 194 }

  globalStatTCPMediaPktsRcvdRate OBJECT-TYPE
    SYNTAX       CounterBasedGauge64
    MAX-ACCESS   read-only
    STATUS       current
    DESCRIPTION  "TCP media packets received per second"
    ::= { perimetaGlobalStatsEntry 195 }

  globalStatTCPMediaBytesRcvdCount OBJECT-TYPE
    SYNTAX       CounterBasedGauge64
    MAX-ACCESS   read-only
    STATUS       current
    DESCRIPTION  "Total TCP media bytes received (last
                  period)"
    ::= { perimetaGlobalStatsEntry 196 }

  globalStatTCPMediaRcvBandWidth OBJECT-TYPE
    SYNTAX       CounterBasedGauge64
    MAX-ACCESS   read-only
    STATUS       current
    DESCRIPTION  "TCP media received bandwidth
                  (bytes/second)"
    ::= { perimetaGlobalStatsEntry 197 }

  globalStatTCPMediaPktsFwdCount OBJECT-TYPE
    SYNTAX       CounterBasedGauge64
    MAX-ACCESS   read-only
    STATUS       current
    DESCRIPTION  "Total TCP media packets forwarded (last
                  period)"
    ::= { perimetaGlobalStatsEntry 198 }

  globalStatTCPMediaPktsFwdRate OBJECT-TYPE
    SYNTAX       CounterBasedGauge64
    MAX-ACCESS   read-only
    STATUS       current
    DESCRIPTION  "TCP media packets forwarded per second"
    ::= { perimetaGlobalStatsEntry 199 }

  globalStatTCPMediaBytesFwdCount OBJECT-TYPE
    SYNTAX       CounterBasedGauge64
    MAX-ACCESS   read-only
    STATUS       current
    DESCRIPTION  "Total TCP media bytes forwarded (last
                  period)"
    ::= { perimetaGlobalStatsEntry 200 }

  globalStatTCPMediaFwdBandWidth OBJECT-TYPE
    SYNTAX       CounterBasedGauge64
    MAX-ACCESS   read-only
    STATUS       current
    DESCRIPTION  "TCP media forwarded bandwidth
                  (bytes/second)"
    ::= { perimetaGlobalStatsEntry 201 }

  globalStatTCPMedPktsDropCount OBJECT-TYPE
    SYNTAX       CounterBasedGauge64
    MAX-ACCESS   read-only
    STATUS       current
    DESCRIPTION  "Total TCP media packets dropped (last
                  period)"
    ::= { perimetaGlobalStatsEntry 202 }

  globalStatTCPMediaDropRate OBJECT-TYPE
    SYNTAX       CounterBasedGauge64
    MAX-ACCESS   read-only
    STATUS       current
    DESCRIPTION  "TCP media packets dropped per second"
    ::= { perimetaGlobalStatsEntry 203 }

  globalStatActiveSubscriptions OBJECT-TYPE
    SYNTAX       CounterBasedGauge64
    MAX-ACCESS   read-only
    STATUS       current
    DESCRIPTION  "Currently Active/Activating
                  Subscriptions"
    ::= { perimetaGlobalStatsEntry 204 }

  globalStatMSRPSessions OBJECT-TYPE
    SYNTAX       CounterBasedGauge64
    MAX-ACCESS   read-only
    STATUS       current
    DESCRIPTION  "Currently active MSRP media sessions"
    ::= { perimetaGlobalStatsEntry 205 }

  globalStatTCPSessions OBJECT-TYPE
    SYNTAX       CounterBasedGauge64
    MAX-ACCESS   read-only
    STATUS       current
    DESCRIPTION  "Currently active TCP media sessions"
    ::= { perimetaGlobalStatsEntry 206 }

  globalStatInbandDtmfCalls OBJECT-TYPE
    SYNTAX       CounterBasedGauge64
    MAX-ACCESS   read-only
    STATUS       current
    DESCRIPTION  "Number of calls using inband DTMF
                  detection"
    ::= { perimetaGlobalStatsEntry 207 }

  globalStatUsedAdvancedCapacityPerc OBJECT-TYPE
    SYNTAX       CounterBasedGauge64
    UNITS        "/ 10000 %"
    MAX-ACCESS   read-only
    STATUS       current
    DESCRIPTION  "Percentage of advanced media capacity
                  units in use"
    ::= { perimetaGlobalStatsEntry 208 }

  globalStatDspPktsRcvd OBJECT-TYPE
    SYNTAX       CounterBasedGauge64
    MAX-ACCESS   read-only
    STATUS       current
    DESCRIPTION  "Total packets received by DSPs (in the
                  last period)"
    ::= { perimetaGlobalStatsEntry 209 }

  globalStatDspPktsRcvdRate OBJECT-TYPE
    SYNTAX       CounterBasedGauge64
    MAX-ACCESS   read-only
    STATUS       current
    DESCRIPTION  "Packets received per second by DSPs"
    ::= { perimetaGlobalStatsEntry 210 }

  globalStatDspOctetsRcvd OBJECT-TYPE
    SYNTAX       CounterBasedGauge64
    MAX-ACCESS   read-only
    STATUS       current
    DESCRIPTION  "Total octets received by DSPs (in the
                  last period)"
    ::= { perimetaGlobalStatsEntry 211 }

  globalStatDspOctetsRcvdRate OBJECT-TYPE
    SYNTAX       CounterBasedGauge64
    MAX-ACCESS   read-only
    STATUS       current
    DESCRIPTION  "Octets received per second by DSPs"
    ::= { perimetaGlobalStatsEntry 212 }

  globalStatDspPcmForwarded OBJECT-TYPE
    SYNTAX       CounterBasedGauge64
    MAX-ACCESS   read-only
    STATUS       current
    DESCRIPTION  "Linear PCM packets forwarded to a DSP
                  encoder (in the last period)"
    ::= { perimetaGlobalStatsEntry 213 }

  globalStatDspPcmForwardRate OBJECT-TYPE
    SYNTAX       CounterBasedGauge64
    MAX-ACCESS   read-only
    STATUS       current
    DESCRIPTION  "Linear PCM packets forwarded to a DSP
                  encoder per second"
    ::= { perimetaGlobalStatsEntry 214 }

  globalStatDspPcmRcvd OBJECT-TYPE
    SYNTAX       CounterBasedGauge64
    MAX-ACCESS   read-only
    STATUS       current
    DESCRIPTION  "Linear PCM packets received by a DSP
                  encoder (in the last period)"
    ::= { perimetaGlobalStatsEntry 215 }

  globalStatDspPcmRcvdRate OBJECT-TYPE
    SYNTAX       CounterBasedGauge64
    MAX-ACCESS   read-only
    STATUS       current
    DESCRIPTION  "Linear PCM packets received by a DSP
                  encoder per second"
    ::= { perimetaGlobalStatsEntry 216 }

  globalStatDspPktsSent OBJECT-TYPE
    SYNTAX       CounterBasedGauge64
    MAX-ACCESS   read-only
    STATUS       current
    DESCRIPTION  "Total packets sent by DSPs (in the last
                  period)"
    ::= { perimetaGlobalStatsEntry 217 }

  globalStatDspPktsSentRate OBJECT-TYPE
    SYNTAX       CounterBasedGauge64
    MAX-ACCESS   read-only
    STATUS       current
    DESCRIPTION  "Packets sent per second by DSPs"
    ::= { perimetaGlobalStatsEntry 218 }

  globalStatDspOctetsSent OBJECT-TYPE
    SYNTAX       CounterBasedGauge64
    MAX-ACCESS   read-only
    STATUS       current
    DESCRIPTION  "Total octets sent by DSPs (in the last
                  period)"
    ::= { perimetaGlobalStatsEntry 219 }

  globalStatDspOctetsSentRate OBJECT-TYPE
    SYNTAX       CounterBasedGauge64
    MAX-ACCESS   read-only
    STATUS       current
    DESCRIPTION  "Octets sent per second by DSPs"
    ::= { perimetaGlobalStatsEntry 220 }

  globalStatDspRxUnexpCodec OBJECT-TYPE
    SYNTAX       CounterBasedGauge64
    MAX-ACCESS   read-only
    STATUS       current
    DESCRIPTION  "Number of packets received by DSPs
                  referring to an unexpected codec"
    ::= { perimetaGlobalStatsEntry 221 }

  globalStatDspRxUnexpPtype OBJECT-TYPE
    SYNTAX       CounterBasedGauge64
    MAX-ACCESS   read-only
    STATUS       current
    DESCRIPTION  "Number of packets received by DSPs with
                  an unexpected payload type"
    ::= { perimetaGlobalStatsEntry 222 }

  globalStatDspRxIntFails OBJECT-TYPE
    SYNTAX       CounterBasedGauge64
    MAX-ACCESS   read-only
    STATUS       current
    DESCRIPTION  "Number of packets dropped by DSPs due to
                  internal processing failures"
    ::= { perimetaGlobalStatsEntry 223 }

  globalStatDspRxInvalLen OBJECT-TYPE
    SYNTAX       CounterBasedGauge64
    MAX-ACCESS   read-only
    STATUS       current
    DESCRIPTION  "Number of packets dropped by DSPs due to
                  an invalid length"
    ::= { perimetaGlobalStatsEntry 224 }

  globalStatDspRxMisordered OBJECT-TYPE
    SYNTAX       CounterBasedGauge64
    MAX-ACCESS   read-only
    STATUS       current
    DESCRIPTION  "Number of packets received out of order
                  by DSPs"
    ::= { perimetaGlobalStatsEntry 225 }

  globalStatDspRxSeqLost OBJECT-TYPE
    SYNTAX       CounterBasedGauge64
    MAX-ACCESS   read-only
    STATUS       current
    DESCRIPTION  "Number of packets seen with loss in RTP
                  sequence num by DSPs"
    ::= { perimetaGlobalStatsEntry 226 }

  globalStatDspUnderruns OBJECT-TYPE
    SYNTAX       CounterBasedGauge64
    MAX-ACCESS   read-only
    STATUS       current
    DESCRIPTION  "Number of underruns detected in a stream
                  by DSP jitter buffer"
    ::= { perimetaGlobalStatsEntry 227 }

  globalStatDspOverruns OBJECT-TYPE
    SYNTAX       CounterBasedGauge64
    MAX-ACCESS   read-only
    STATUS       current
    DESCRIPTION  "Number of overruns detected in a stream
                  by DSP jitter buffer"
    ::= { perimetaGlobalStatsEntry 228 }

  globalStatDspRxIntBuffErrs OBJECT-TYPE
    SYNTAX       CounterBasedGauge64
    MAX-ACCESS   read-only
    STATUS       current
    DESCRIPTION  "Number of DSP internal buffer errors"
    ::= { perimetaGlobalStatsEntry 229 }

  globalStatDspTxInvalid OBJECT-TYPE
    SYNTAX       CounterBasedGauge64
    MAX-ACCESS   read-only
    STATUS       current
    DESCRIPTION  "Number of Tx packets dropped by DSPs due
                  to invalid content"
    ::= { perimetaGlobalStatsEntry 230 }

  globalStatDspTxGaps OBJECT-TYPE
    SYNTAX       CounterBasedGauge64
    MAX-ACCESS   read-only
    STATUS       current
    DESCRIPTION  "Number of times a gap was detected and
                  filled with silence by DSPs"
    ::= { perimetaGlobalStatsEntry 231 }

  globalStatDspTxNoRtp OBJECT-TYPE
    SYNTAX       CounterBasedGauge64
    MAX-ACCESS   read-only
    STATUS       current
    DESCRIPTION  "Number of Tx packets dropped by DSPs due
                  to no matching flow"
    ::= { perimetaGlobalStatsEntry 232 }

  globalStatDspChecksumFails OBJECT-TYPE
    SYNTAX       CounterBasedGauge64
    MAX-ACCESS   read-only
    STATUS       current
    DESCRIPTION  "Number of Tx packets dropped due to DSP
                  checksum verification failures"
    ::= { perimetaGlobalStatsEntry 233 }

  globalStatDspRxMipsDrops OBJECT-TYPE
    SYNTAX       CounterBasedGauge64
    MAX-ACCESS   read-only
    STATUS       current
    DESCRIPTION  "Estimated number of Rx packets dropped
                  due to DSP MIPs protection"
    ::= { perimetaGlobalStatsEntry 234 }

  globalStatDspTxMipsDrops OBJECT-TYPE
    SYNTAX       CounterBasedGauge64
    MAX-ACCESS   read-only
    STATUS       current
    DESCRIPTION  "Estimated number of Tx packets dropped
                  due to DSP MIPs protection"
    ::= { perimetaGlobalStatsEntry 235 }

  globalStatDspInbandTones OBJECT-TYPE
    SYNTAX       CounterBasedGauge64
    MAX-ACCESS   read-only
    STATUS       current
    DESCRIPTION  "Number of inband tones detected by DSPs"
    ::= { perimetaGlobalStatsEntry 236 }

  globalStatDspRxTones OBJECT-TYPE
    SYNTAX       CounterBasedGauge64
    MAX-ACCESS   read-only
    STATUS       current
    DESCRIPTION  "Number of RFC2833 tones detected by DSPs"
    ::= { perimetaGlobalStatsEntry 237 }

  globalStatDspRxUnsupTones OBJECT-TYPE
    SYNTAX       CounterBasedGauge64
    MAX-ACCESS   read-only
    STATUS       current
    DESCRIPTION  "Number of unsupported tones detected by
                  DSPs"
    ::= { perimetaGlobalStatsEntry 238 }

  globalStatDspTxTones OBJECT-TYPE
    SYNTAX       CounterBasedGauge64
    MAX-ACCESS   read-only
    STATUS       current
    DESCRIPTION  "Number of RFC2833 tones injected by DSPs"
    ::= { perimetaGlobalStatsEntry 239 }

  globalStatDspMaxPdv OBJECT-TYPE
    SYNTAX       CounterBasedGauge64
    MAX-ACCESS   read-only
    STATUS       current
    DESCRIPTION  "Maximum packet delay variation detected
                  by DSP jitter buffer"
    ::= { perimetaGlobalStatsEntry 240 }

  globalStatDspBoardTemp OBJECT-TYPE
    SYNTAX       CounterBasedGauge64
    MAX-ACCESS   read-only
    STATUS       current
    DESCRIPTION  "Current maximum temperature across all
                  DSP boards"
    ::= { perimetaGlobalStatsEntry 241 }

  globalStatDspCpuUsage OBJECT-TYPE
    SYNTAX       CounterBasedGauge64
    MAX-ACCESS   read-only
    STATUS       current
    DESCRIPTION  "Current maximum CPU usage across all
                  DSPs"
    ::= { perimetaGlobalStatsEntry 242 }

  globalStatDspNumFlowpairs OBJECT-TYPE
    SYNTAX       CounterBasedGauge64
    MAX-ACCESS   read-only
    STATUS       current
    DESCRIPTION  "Total DSP flowpairs"
    ::= { perimetaGlobalStatsEntry 243 }

  globalStatDspNumInbandFlowpairs OBJECT-TYPE
    SYNTAX       CounterBasedGauge64
    MAX-ACCESS   read-only
    STATUS       current
    DESCRIPTION  "Total Inband DTMF DSP flowpairs"
    ::= { perimetaGlobalStatsEntry 244 }

  globalStatDspRtpPktsDropped OBJECT-TYPE
    SYNTAX       CounterBasedGauge64
    MAX-ACCESS   read-only
    STATUS       current
    DESCRIPTION  "Total packets dropped by DSPs"
    ::= { perimetaGlobalStatsEntry 245 }

  globalStatDspMaxAllocLatency OBJECT-TYPE
    SYNTAX       CounterBasedGauge64
    MAX-ACCESS   read-only
    STATUS       current
    DESCRIPTION  "Maximum latency on DSP flowpair
                  allocation"
    ::= { perimetaGlobalStatsEntry 246 }

  globalStatDspMaxModifyLatency OBJECT-TYPE
    SYNTAX       CounterBasedGauge64
    MAX-ACCESS   read-only
    STATUS       current
    DESCRIPTION  "Maximum latency on DSP flowpair
                  modification"
    ::= { perimetaGlobalStatsEntry 247 }

  globalStatDspMaxDeleteLatency OBJECT-TYPE
    SYNTAX       CounterBasedGauge64
    MAX-ACCESS   read-only
    STATUS       current
    DESCRIPTION  "Maximum latency on DSP flowpair deletion"
    ::= { perimetaGlobalStatsEntry 248 }

  globalStatDspMaxStatsLatency OBJECT-TYPE
    SYNTAX       CounterBasedGauge64
    MAX-ACCESS   read-only
    STATUS       current
    DESCRIPTION  "Maximum latency on DSP flowpair stats
                  requests"
    ::= { perimetaGlobalStatsEntry 249 }

  globalStatDspAvgAllocLatency OBJECT-TYPE
    SYNTAX       CounterBasedGauge64
    MAX-ACCESS   read-only
    STATUS       current
    DESCRIPTION  "Average latency on DSP flowpair
                  allocation"
    ::= { perimetaGlobalStatsEntry 250 }

  globalStatDspAvgModifyLatency OBJECT-TYPE
    SYNTAX       CounterBasedGauge64
    MAX-ACCESS   read-only
    STATUS       current
    DESCRIPTION  "Average latency on DSP flowpair
                  modification"
    ::= { perimetaGlobalStatsEntry 251 }

  globalStatDspAvgDeleteLatency OBJECT-TYPE
    SYNTAX       CounterBasedGauge64
    MAX-ACCESS   read-only
    STATUS       current
    DESCRIPTION  "Average latency on DSP flowpair deletion"
    ::= { perimetaGlobalStatsEntry 252 }

  globalStatDspAvgStatsLatency OBJECT-TYPE
    SYNTAX       CounterBasedGauge64
    MAX-ACCESS   read-only
    STATUS       current
    DESCRIPTION  "Average latency on DSP flowpair stats
                  requests"
    ::= { perimetaGlobalStatsEntry 253 }

  globalStatCodecActiveTranscPCMU OBJECT-TYPE
    SYNTAX       CounterBasedGauge64
    MAX-ACCESS   read-only
    STATUS       current
    DESCRIPTION  "Active calls transcoding with PCMU"
    ::= { perimetaGlobalStatsEntry 254 }

  globalStatCodecActiveTranscPCMA OBJECT-TYPE
    SYNTAX       CounterBasedGauge64
    MAX-ACCESS   read-only
    STATUS       current
    DESCRIPTION  "Active calls transcoding with PCMA"
    ::= { perimetaGlobalStatsEntry 255 }

  globalStatCodecActiveTranscG729 OBJECT-TYPE
    SYNTAX       CounterBasedGauge64
    MAX-ACCESS   read-only
    STATUS       current
    DESCRIPTION  "Active calls transcoding with G729"
    ::= { perimetaGlobalStatsEntry 256 }

  globalStatCodecActiveTranscG722 OBJECT-TYPE
    SYNTAX       CounterBasedGauge64
    MAX-ACCESS   read-only
    STATUS       current
    DESCRIPTION  "Active calls transcoding with G722"
    ::= { perimetaGlobalStatsEntry 257 }

  globalStatCodecActiveTranscSILK8 OBJECT-TYPE
    SYNTAX       CounterBasedGauge64
    MAX-ACCESS   read-only
    STATUS       current
    DESCRIPTION  "Active calls transcoding with SILK/8000"
    ::= { perimetaGlobalStatsEntry 258 }

  globalStatCodecActiveTranscAMR OBJECT-TYPE
    SYNTAX       CounterBasedGauge64
    MAX-ACCESS   read-only
    STATUS       current
    DESCRIPTION  "Active calls transcoding with AMR"
    ::= { perimetaGlobalStatsEntry 259 }

  globalStatCodecActiveTranscAMRWB OBJECT-TYPE
    SYNTAX       CounterBasedGauge64
    MAX-ACCESS   read-only
    STATUS       current
    DESCRIPTION  "Active calls transcoding with AMR-WB"
    ::= { perimetaGlobalStatsEntry 260 }

  globalStatActiveT38FaxTranscSessions OBJECT-TYPE
    SYNTAX       CounterBasedGauge64
    MAX-ACCESS   read-only
    STATUS       current
    DESCRIPTION  "Active calls transcoding with T.38"
    ::= { perimetaGlobalStatsEntry 261 }

  globalStatDspNumFaxFlowpairs OBJECT-TYPE
    SYNTAX       CounterBasedGauge64
    MAX-ACCESS   read-only
    STATUS       current
    DESCRIPTION  "Total DSP fax flowpairs"
    ::= { perimetaGlobalStatsEntry 262 }

  globalStatActiveCallsFaxTranscUsed OBJECT-TYPE
    SYNTAX       CounterBasedGauge64
    MAX-ACCESS   read-only
    STATUS       current
    DESCRIPTION  "Calls using fax transcoding"
    ::= { perimetaGlobalStatsEntry 263 }

  globalStatTotalFaxToneFlowpairs OBJECT-TYPE
    SYNTAX       CounterBasedGauge64
    MAX-ACCESS   read-only
    STATUS       current
    DESCRIPTION  "Media sessions using fax tone detection"
    ::= { perimetaGlobalStatsEntry 264 }

  globalStatSIPCongestionInvDropCnt OBJECT-TYPE
    SYNTAX       CounterBasedGauge64
    MAX-ACCESS   read-only
    STATUS       current
    DESCRIPTION  "Total INVITEs dropped due to SIP
                  congestion"
    ::= { perimetaGlobalStatsEntry 265 }

  globalStatSIPCongestionSubDropCnt OBJECT-TYPE
    SYNTAX       CounterBasedGauge64
    MAX-ACCESS   read-only
    STATUS       current
    DESCRIPTION  "Total SUBSCRIBEs dropped due to SIP
                  congestion"
    ::= { perimetaGlobalStatsEntry 266 }

  globalStatSIPCongestionInvDropRate OBJECT-TYPE
    SYNTAX       CounterBasedGauge64
    MAX-ACCESS   read-only
    STATUS       current
    DESCRIPTION  "INVITEs dropped due to SIP congestion
                  per second"
    ::= { perimetaGlobalStatsEntry 267 }

  globalStatSIPCongestionSubDropRate OBJECT-TYPE
    SYNTAX       CounterBasedGauge64
    MAX-ACCESS   read-only
    STATUS       current
    DESCRIPTION  "SUBSCRIBEs dropped due to SIP congestion
                  per second"
    ::= { perimetaGlobalStatsEntry 268 }

  globalStatUndersizedDropped OBJECT-TYPE
    SYNTAX       CounterBasedGauge64
    MAX-ACCESS   read-only
    STATUS       current
    DESCRIPTION  "Total signaling packets dropped due to
                  being undersized (last period)"
    ::= { perimetaGlobalStatsEntry 269 }

  globalStatSigDisUndersizeRate OBJECT-TYPE
    SYNTAX       CounterBasedGauge64
    MAX-ACCESS   read-only
    STATUS       current
    DESCRIPTION  "Signaling packets dropped due to being
                  undersized per second"
    ::= { perimetaGlobalStatsEntry 270 }

  globalStatESRVCCAnchoredCalls OBJECT-TYPE
    SYNTAX       CounterBasedGauge64
    MAX-ACCESS   read-only
    STATUS       current
    DESCRIPTION  "Current SRVCC anchored calls"
    ::= { perimetaGlobalStatsEntry 271 }

  globalStatESRVCCTransfersOK OBJECT-TYPE
    SYNTAX       CounterBasedGauge64
    MAX-ACCESS   read-only
    STATUS       current
    DESCRIPTION  "Number of successful eSRVCC call
                  transfers"
    ::= { perimetaGlobalStatsEntry 272 }

  globalStatESRVCCTransfersFailed OBJECT-TYPE
    SYNTAX       CounterBasedGauge64
    MAX-ACCESS   read-only
    STATUS       current
    DESCRIPTION  "Number of failed eSRVCC call transfers"
    ::= { perimetaGlobalStatsEntry 273 }

  globalStatESRVCCCurSubscribers OBJECT-TYPE
    SYNTAX       CounterBasedGauge64
    MAX-ACCESS   read-only
    STATUS       current
    DESCRIPTION  "Current number of eSRVCC-capable
                  subscribers"
    ::= { perimetaGlobalStatsEntry 274 }

  globalStatESRVCCNumRejects OBJECT-TYPE
    SYNTAX       CounterBasedGauge64
    MAX-ACCESS   read-only
    STATUS       current
    DESCRIPTION  "Number of rejected SIP MESSAGEs
                  containing eSRVCC data"
    ::= { perimetaGlobalStatsEntry 275 }

  globalStatCodecActiveTranscG723 OBJECT-TYPE
    SYNTAX       CounterBasedGauge64
    MAX-ACCESS   read-only
    STATUS       current
    DESCRIPTION  "Active calls transcoding with G723"
    ::= { perimetaGlobalStatsEntry 276 }

  globalStatInbandInjectCount OBJECT-TYPE
    SYNTAX       CounterBasedGauge64
    MAX-ACCESS   read-only
    STATUS       current
    DESCRIPTION  "Number of inband tones generated by DSPs"
    ::= { perimetaGlobalStatsEntry 277 }

  globalStatActiveMSRPCalls OBJECT-TYPE
    SYNTAX       CounterBasedGauge64
    MAX-ACCESS   read-only
    STATUS       current
    DESCRIPTION  "Number of MSRP calls"
    ::= { perimetaGlobalStatsEntry 278 }

  globalStatActiveMSRPSIWCalls OBJECT-TYPE
    SYNTAX       CounterBasedGauge64
    MAX-ACCESS   read-only
    STATUS       current
    DESCRIPTION  "Active MSRPS interworking calls"
    ::= { perimetaGlobalStatsEntry 279 }

  globalStatActiveMSRPSPtCalls OBJECT-TYPE
    SYNTAX       CounterBasedGauge64
    MAX-ACCESS   read-only
    STATUS       current
    DESCRIPTION  "Active MSRPS passthrough calls"
    ::= { perimetaGlobalStatsEntry 280 }

  globalStatMSRPSIWSessRate OBJECT-TYPE
    SYNTAX       CounterBasedGauge64
    MAX-ACCESS   read-only
    STATUS       current
    DESCRIPTION  "MSRPS interworking session creation rate
                  (sessions/sec)"
    ::= { perimetaGlobalStatsEntry 281 }

  globalStatMSRPSPtSessRate OBJECT-TYPE
    SYNTAX       CounterBasedGauge64
    MAX-ACCESS   read-only
    STATUS       current
    DESCRIPTION  "MSRPS passthrough session creation rate
                  (sessions/sec)"
    ::= { perimetaGlobalStatsEntry 282 }

  globalStatCodecActiveTranscG72616 OBJECT-TYPE
    SYNTAX       CounterBasedGauge64
    MAX-ACCESS   read-only
    STATUS       current
    DESCRIPTION  "Active calls transcoding with G726-16"
    ::= { perimetaGlobalStatsEntry 283 }

  globalStatCodecActiveTranscG72624 OBJECT-TYPE
    SYNTAX       CounterBasedGauge64
    MAX-ACCESS   read-only
    STATUS       current
    DESCRIPTION  "Active calls transcoding with G726-24"
    ::= { perimetaGlobalStatsEntry 284 }

  globalStatCodecActiveTranscG72632 OBJECT-TYPE
    SYNTAX       CounterBasedGauge64
    MAX-ACCESS   read-only
    STATUS       current
    DESCRIPTION  "Active calls transcoding with G726-32"
    ::= { perimetaGlobalStatsEntry 285 }

  globalStatCodecActiveTranscG72640 OBJECT-TYPE
    SYNTAX       CounterBasedGauge64
    MAX-ACCESS   read-only
    STATUS       current
    DESCRIPTION  "Active calls transcoding with G726-40"
    ::= { perimetaGlobalStatsEntry 286 }

  globalStatCodecActiveTranscG729AB OBJECT-TYPE
    SYNTAX       CounterBasedGauge64
    MAX-ACCESS   read-only
    STATUS       current
    DESCRIPTION  "Active calls transcoding with G729AB"
    ::= { perimetaGlobalStatsEntry 287 }

  globalStatAllocatedMediaSessions OBJECT-TYPE
    SYNTAX       CounterBasedGauge64
    MAX-ACCESS   read-only
    STATUS       current
    DESCRIPTION  "Allocated media sessions"
    ::= { perimetaGlobalStatsEntry 288 }

  globalStatCoupledMediaSessions OBJECT-TYPE
    SYNTAX       CounterBasedGauge64
    MAX-ACCESS   read-only
    STATUS       current
    DESCRIPTION  "Allocated linked media sessions"
    ::= { perimetaGlobalStatsEntry 289 }

  globalStatTotalInbandDtmfFlowpairs OBJECT-TYPE
    SYNTAX       CounterBasedGauge64
    MAX-ACCESS   read-only
    STATUS       current
    DESCRIPTION  "Number of media sessions using inband
                  DTMF detection"
    ::= { perimetaGlobalStatsEntry 290 }

  globalStatTotalAdvancedMRUUsage OBJECT-TYPE
    SYNTAX       CounterBasedGauge64
    MAX-ACCESS   read-only
    STATUS       current
    DESCRIPTION  "Number of advanced capacity units
                  currently in use"
    ::= { perimetaGlobalStatsEntry 291 }

  globalStatDSPPCIE8120Utilization OBJECT-TYPE
    SYNTAX       CounterBasedGauge64
    UNITS        "/ 10000 %"
    MAX-ACCESS   read-only
    STATUS       current
    DESCRIPTION  "Percentage utilization of PCIE 8120 DSPs"
    ::= { perimetaGlobalStatsEntry 292 }

  globalStatTcCodecFailures OBJECT-TYPE
    SYNTAX       CounterBasedGauge64
    MAX-ACCESS   read-only
    STATUS       current
    DESCRIPTION  "Total calls that failed due to
                  transcoding codecs"
    ::= { perimetaGlobalStatsEntry 293 }

  globalStatTotalH323Calls OBJECT-TYPE
    SYNTAX       CounterBasedGauge64
    MAX-ACCESS   read-only
    STATUS       current
    DESCRIPTION  "Total number of calls that used H.323"
    ::= { perimetaGlobalStatsEntry 294 }

  globalStatTotalAudioTranscCalls OBJECT-TYPE
    SYNTAX       CounterBasedGauge64
    MAX-ACCESS   read-only
    STATUS       current
    DESCRIPTION  "Calls using audio transcoding"
    ::= { perimetaGlobalStatsEntry 295 }

  globalStatRPG1B1RcvdCompression OBJECT-TYPE
    SYNTAX       CounterBasedGauge64
    MAX-ACCESS   read-only
    STATUS       current
    DESCRIPTION  "RPG1 blade 1 rcvd compression"
    ::= { perimetaGlobalStatsEntry 296 }

  globalStatRPG1B1TransCompression OBJECT-TYPE
    SYNTAX       CounterBasedGauge64
    MAX-ACCESS   read-only
    STATUS       current
    DESCRIPTION  "RPG1 blade 1 transmission compression"
    ::= { perimetaGlobalStatsEntry 297 }

  globalStatRPG2B1RcvdCompression OBJECT-TYPE
    SYNTAX       CounterBasedGauge64
    MAX-ACCESS   read-only
    STATUS       current
    DESCRIPTION  "RPG2 blade 1 rcvd compression"
    ::= { perimetaGlobalStatsEntry 298 }

  globalStatRPG2B1TransCompression OBJECT-TYPE
    SYNTAX       CounterBasedGauge64
    MAX-ACCESS   read-only
    STATUS       current
    DESCRIPTION  "RPG2 blade 1 transmission compression"
    ::= { perimetaGlobalStatsEntry 299 }

  globalStatRPG3B1RcvdCompression OBJECT-TYPE
    SYNTAX       CounterBasedGauge64
    MAX-ACCESS   read-only
    STATUS       current
    DESCRIPTION  "RPG3 blade 1 rcvd compression"
    ::= { perimetaGlobalStatsEntry 300 }

  globalStatRPG3B1TransCompression OBJECT-TYPE
    SYNTAX       CounterBasedGauge64
    MAX-ACCESS   read-only
    STATUS       current
    DESCRIPTION  "RPG3 blade 1 transmission compression"
    ::= { perimetaGlobalStatsEntry 301 }

  globalStatRPG4B1RcvdCompression OBJECT-TYPE
    SYNTAX       CounterBasedGauge64
    MAX-ACCESS   read-only
    STATUS       current
    DESCRIPTION  "RPG4 blade 1 rcvd compression"
    ::= { perimetaGlobalStatsEntry 302 }

  globalStatRPG4B1TransCompression OBJECT-TYPE
    SYNTAX       CounterBasedGauge64
    MAX-ACCESS   read-only
    STATUS       current
    DESCRIPTION  "RPG4 blade 1 transmission compression"
    ::= { perimetaGlobalStatsEntry 303 }

  globalStatRPG5B1RcvdCompression OBJECT-TYPE
    SYNTAX       CounterBasedGauge64
    MAX-ACCESS   read-only
    STATUS       current
    DESCRIPTION  "RPG5 blade 1 rcvd compression"
    ::= { perimetaGlobalStatsEntry 304 }

  globalStatRPG5B1TransCompression OBJECT-TYPE
    SYNTAX       CounterBasedGauge64
    MAX-ACCESS   read-only
    STATUS       current
    DESCRIPTION  "RPG5 blade 1 transmission compression"
    ::= { perimetaGlobalStatsEntry 305 }

  globalStatRPG6B1RcvdCompression OBJECT-TYPE
    SYNTAX       CounterBasedGauge64
    MAX-ACCESS   read-only
    STATUS       current
    DESCRIPTION  "RPG6 blade 1 rcvd compression"
    ::= { perimetaGlobalStatsEntry 306 }

  globalStatRPG6B1TransCompression OBJECT-TYPE
    SYNTAX       CounterBasedGauge64
    MAX-ACCESS   read-only
    STATUS       current
    DESCRIPTION  "RPG6 blade 1 transmission compression"
    ::= { perimetaGlobalStatsEntry 307 }

  globalStatRPG7B1RcvdCompression OBJECT-TYPE
    SYNTAX       CounterBasedGauge64
    MAX-ACCESS   read-only
    STATUS       current
    DESCRIPTION  "RPG7 blade 1 rcvd compression"
    ::= { perimetaGlobalStatsEntry 308 }

  globalStatRPG7B1TransCompression OBJECT-TYPE
    SYNTAX       CounterBasedGauge64
    MAX-ACCESS   read-only
    STATUS       current
    DESCRIPTION  "RPG7 blade 1 transmission compression"
    ::= { perimetaGlobalStatsEntry 309 }

  globalStatRPG8B1RcvdCompression OBJECT-TYPE
    SYNTAX       CounterBasedGauge64
    MAX-ACCESS   read-only
    STATUS       current
    DESCRIPTION  "RPG8 blade 1 rcvd compression"
    ::= { perimetaGlobalStatsEntry 310 }

  globalStatRPG8B1TransCompression OBJECT-TYPE
    SYNTAX       CounterBasedGauge64
    MAX-ACCESS   read-only
    STATUS       current
    DESCRIPTION  "RPG8 blade 1 transmission compression"
    ::= { perimetaGlobalStatsEntry 311 }

  globalStatIBG1MB1RcvdCompression OBJECT-TYPE
    SYNTAX       CounterBasedGauge64
    MAX-ACCESS   read-only
    STATUS       current
    DESCRIPTION  "IBG1_M blade 1 rcvd compression"
    ::= { perimetaGlobalStatsEntry 312 }

  globalStatIBG1MB1TransCompression OBJECT-TYPE
    SYNTAX       CounterBasedGauge64
    MAX-ACCESS   read-only
    STATUS       current
    DESCRIPTION  "IBG1_M blade 1 transmission compression"
    ::= { perimetaGlobalStatsEntry 313 }

  globalStatIBG2MB1RcvdCompression OBJECT-TYPE
    SYNTAX       CounterBasedGauge64
    MAX-ACCESS   read-only
    STATUS       current
    DESCRIPTION  "IBG2_M blade 1 rcvd compression"
    ::= { perimetaGlobalStatsEntry 314 }

  globalStatIBG2MB1TransCompression OBJECT-TYPE
    SYNTAX       CounterBasedGauge64
    MAX-ACCESS   read-only
    STATUS       current
    DESCRIPTION  "IBG2_M blade 1 transmission compression"
    ::= { perimetaGlobalStatsEntry 315 }

  globalStatIBG1B1RcvdCompression OBJECT-TYPE
    SYNTAX       CounterBasedGauge64
    MAX-ACCESS   read-only
    STATUS       current
    DESCRIPTION  "IBG1 blade 1 rcvd compression"
    ::= { perimetaGlobalStatsEntry 316 }

  globalStatIBG1B1TransCompression OBJECT-TYPE
    SYNTAX       CounterBasedGauge64
    MAX-ACCESS   read-only
    STATUS       current
    DESCRIPTION  "IBG1 blade 1 transmission compression"
    ::= { perimetaGlobalStatsEntry 317 }

  globalStatIBG2B1RcvdCompression OBJECT-TYPE
    SYNTAX       CounterBasedGauge64
    MAX-ACCESS   read-only
    STATUS       current
    DESCRIPTION  "IBG2 blade 1 rcvd compression"
    ::= { perimetaGlobalStatsEntry 318 }

  globalStatIBG2B1TransCompression OBJECT-TYPE
    SYNTAX       CounterBasedGauge64
    MAX-ACCESS   read-only
    STATUS       current
    DESCRIPTION  "IBG2 blade 1 transmission compression"
    ::= { perimetaGlobalStatsEntry 319 }

  globalStatIPG1B1RcvdCompression OBJECT-TYPE
    SYNTAX       CounterBasedGauge64
    MAX-ACCESS   read-only
    STATUS       current
    DESCRIPTION  "IPG1 blade 1 rcvd compression"
    ::= { perimetaGlobalStatsEntry 320 }

  globalStatIPG1B1TransCompression OBJECT-TYPE
    SYNTAX       CounterBasedGauge64
    MAX-ACCESS   read-only
    STATUS       current
    DESCRIPTION  "IPG1 blade 1 transmission compression"
    ::= { perimetaGlobalStatsEntry 321 }

  globalStatIFXG1B1RcvdCompression OBJECT-TYPE
    SYNTAX       CounterBasedGauge64
    MAX-ACCESS   read-only
    STATUS       current
    DESCRIPTION  "IFXG1 blade 1 rcvd compression"
    ::= { perimetaGlobalStatsEntry 322 }

  globalStatIFXG1B1TransCompression OBJECT-TYPE
    SYNTAX       CounterBasedGauge64
    MAX-ACCESS   read-only
    STATUS       current
    DESCRIPTION  "IFXG1 blade 1 transmission compression"
    ::= { perimetaGlobalStatsEntry 323 }

  globalStatIFXG2B1RcvdCompression OBJECT-TYPE
    SYNTAX       CounterBasedGauge64
    MAX-ACCESS   read-only
    STATUS       current
    DESCRIPTION  "IFXG2 blade 1 rcvd compression"
    ::= { perimetaGlobalStatsEntry 324 }

  globalStatIFXG2B1TransCompression OBJECT-TYPE
    SYNTAX       CounterBasedGauge64
    MAX-ACCESS   read-only
    STATUS       current
    DESCRIPTION  "IFXG2 blade 1 transmission compression"
    ::= { perimetaGlobalStatsEntry 325 }

  globalStatRPXG1B1RcvdCompression OBJECT-TYPE
    SYNTAX       CounterBasedGauge64
    MAX-ACCESS   read-only
    STATUS       current
    DESCRIPTION  "RPXG1 blade 1 rcvd compression"
    ::= { perimetaGlobalStatsEntry 326 }

  globalStatRPXG1B1TransCompression OBJECT-TYPE
    SYNTAX       CounterBasedGauge64
    MAX-ACCESS   read-only
    STATUS       current
    DESCRIPTION  "RPXG1 blade 1 transmission compression"
    ::= { perimetaGlobalStatsEntry 327 }

  globalStatRPXG2B1RcvdCompression OBJECT-TYPE
    SYNTAX       CounterBasedGauge64
    MAX-ACCESS   read-only
    STATUS       current
    DESCRIPTION  "RPXG2 blade 1 rcvd compression"
    ::= { perimetaGlobalStatsEntry 328 }

  globalStatRPXG2B1TransCompression OBJECT-TYPE
    SYNTAX       CounterBasedGauge64
    MAX-ACCESS   read-only
    STATUS       current
    DESCRIPTION  "RPXG2 blade 1 transmission compression"
    ::= { perimetaGlobalStatsEntry 329 }

  globalStatRPXG3B1RcvdCompression OBJECT-TYPE
    SYNTAX       CounterBasedGauge64
    MAX-ACCESS   read-only
    STATUS       current
    DESCRIPTION  "RPXG3 blade 1 rcvd compression"
    ::= { perimetaGlobalStatsEntry 330 }

  globalStatRPXG3B1TransCompression OBJECT-TYPE
    SYNTAX       CounterBasedGauge64
    MAX-ACCESS   read-only
    STATUS       current
    DESCRIPTION  "RPXG3 blade 1 transmission compression"
    ::= { perimetaGlobalStatsEntry 331 }

  globalStatRPXG4B1RcvdCompression OBJECT-TYPE
    SYNTAX       CounterBasedGauge64
    MAX-ACCESS   read-only
    STATUS       current
    DESCRIPTION  "RPXG4 blade 1 rcvd compression"
    ::= { perimetaGlobalStatsEntry 332 }

  globalStatRPXG4B1TransCompression OBJECT-TYPE
    SYNTAX       CounterBasedGauge64
    MAX-ACCESS   read-only
    STATUS       current
    DESCRIPTION  "RPXG4 blade 1 transmission compression"
    ::= { perimetaGlobalStatsEntry 333 }

  globalStatRPG1B2RcvdCompression OBJECT-TYPE
    SYNTAX       CounterBasedGauge64
    MAX-ACCESS   read-only
    STATUS       current
    DESCRIPTION  "RPG1 blade 2 rcvd compression"
    ::= { perimetaGlobalStatsEntry 334 }

  globalStatRPG1B2TransCompression OBJECT-TYPE
    SYNTAX       CounterBasedGauge64
    MAX-ACCESS   read-only
    STATUS       current
    DESCRIPTION  "RPG1 blade 2 transmission compression"
    ::= { perimetaGlobalStatsEntry 335 }

  globalStatRPG2B2RcvdCompression OBJECT-TYPE
    SYNTAX       CounterBasedGauge64
    MAX-ACCESS   read-only
    STATUS       current
    DESCRIPTION  "RPG2 blade 2 rcvd compression"
    ::= { perimetaGlobalStatsEntry 336 }

  globalStatRPG2B2TransCompression OBJECT-TYPE
    SYNTAX       CounterBasedGauge64
    MAX-ACCESS   read-only
    STATUS       current
    DESCRIPTION  "RPG2 blade 2 transmission compression"
    ::= { perimetaGlobalStatsEntry 337 }

  globalStatRPG3B2RcvdCompression OBJECT-TYPE
    SYNTAX       CounterBasedGauge64
    MAX-ACCESS   read-only
    STATUS       current
    DESCRIPTION  "RPG3 blade 2 rcvd compression"
    ::= { perimetaGlobalStatsEntry 338 }

  globalStatRPG3B2TransCompression OBJECT-TYPE
    SYNTAX       CounterBasedGauge64
    MAX-ACCESS   read-only
    STATUS       current
    DESCRIPTION  "RPG3 blade 2 transmission compression"
    ::= { perimetaGlobalStatsEntry 339 }

  globalStatRPG4B2RcvdCompression OBJECT-TYPE
    SYNTAX       CounterBasedGauge64
    MAX-ACCESS   read-only
    STATUS       current
    DESCRIPTION  "RPG4 blade 2 rcvd compression"
    ::= { perimetaGlobalStatsEntry 340 }

  globalStatRPG4B2TransCompression OBJECT-TYPE
    SYNTAX       CounterBasedGauge64
    MAX-ACCESS   read-only
    STATUS       current
    DESCRIPTION  "RPG4 blade 2 transmission compression"
    ::= { perimetaGlobalStatsEntry 341 }

  globalStatRPG5B2RcvdCompression OBJECT-TYPE
    SYNTAX       CounterBasedGauge64
    MAX-ACCESS   read-only
    STATUS       current
    DESCRIPTION  "RPG5 blade 2 rcvd compression"
    ::= { perimetaGlobalStatsEntry 342 }

  globalStatRPG5B2TransCompression OBJECT-TYPE
    SYNTAX       CounterBasedGauge64
    MAX-ACCESS   read-only
    STATUS       current
    DESCRIPTION  "RPG5 blade 2 transmission compression"
    ::= { perimetaGlobalStatsEntry 343 }

  globalStatRPG6B2RcvdCompression OBJECT-TYPE
    SYNTAX       CounterBasedGauge64
    MAX-ACCESS   read-only
    STATUS       current
    DESCRIPTION  "RPG6 blade 2 rcvd compression"
    ::= { perimetaGlobalStatsEntry 344 }

  globalStatRPG6B2TransCompression OBJECT-TYPE
    SYNTAX       CounterBasedGauge64
    MAX-ACCESS   read-only
    STATUS       current
    DESCRIPTION  "RPG6 blade 2 transmission compression"
    ::= { perimetaGlobalStatsEntry 345 }

  globalStatRPG7B2RcvdCompression OBJECT-TYPE
    SYNTAX       CounterBasedGauge64
    MAX-ACCESS   read-only
    STATUS       current
    DESCRIPTION  "RPG7 blade 2 rcvd compression"
    ::= { perimetaGlobalStatsEntry 346 }

  globalStatRPG7B2TransCompression OBJECT-TYPE
    SYNTAX       CounterBasedGauge64
    MAX-ACCESS   read-only
    STATUS       current
    DESCRIPTION  "RPG7 blade 2 transmission compression"
    ::= { perimetaGlobalStatsEntry 347 }

  globalStatRPG8B2RcvdCompression OBJECT-TYPE
    SYNTAX       CounterBasedGauge64
    MAX-ACCESS   read-only
    STATUS       current
    DESCRIPTION  "RPG8 blade 2 rcvd compression"
    ::= { perimetaGlobalStatsEntry 348 }

  globalStatRPG8B2TransCompression OBJECT-TYPE
    SYNTAX       CounterBasedGauge64
    MAX-ACCESS   read-only
    STATUS       current
    DESCRIPTION  "RPG8 blade 2 transmission compression"
    ::= { perimetaGlobalStatsEntry 349 }

  globalStatIBG1MB2RcvdCompression OBJECT-TYPE
    SYNTAX       CounterBasedGauge64
    MAX-ACCESS   read-only
    STATUS       current
    DESCRIPTION  "IBG1_M blade 2 rcvd compression"
    ::= { perimetaGlobalStatsEntry 350 }

  globalStatIBG1MB2TransCompression OBJECT-TYPE
    SYNTAX       CounterBasedGauge64
    MAX-ACCESS   read-only
    STATUS       current
    DESCRIPTION  "IBG1_M blade 2 transmission compression"
    ::= { perimetaGlobalStatsEntry 351 }

  globalStatIBG2MB2RcvdCompression OBJECT-TYPE
    SYNTAX       CounterBasedGauge64
    MAX-ACCESS   read-only
    STATUS       current
    DESCRIPTION  "IBG2_M blade 2 rcvd compression"
    ::= { perimetaGlobalStatsEntry 352 }

  globalStatIBG2MB2TransCompression OBJECT-TYPE
    SYNTAX       CounterBasedGauge64
    MAX-ACCESS   read-only
    STATUS       current
    DESCRIPTION  "IBG2_M blade 2 transmission compression"
    ::= { perimetaGlobalStatsEntry 353 }

  globalStatIBG1B2RcvdCompression OBJECT-TYPE
    SYNTAX       CounterBasedGauge64
    MAX-ACCESS   read-only
    STATUS       current
    DESCRIPTION  "IBG1 blade 2 rcvd compression"
    ::= { perimetaGlobalStatsEntry 354 }

  globalStatIBG1B2TransCompression OBJECT-TYPE
    SYNTAX       CounterBasedGauge64
    MAX-ACCESS   read-only
    STATUS       current
    DESCRIPTION  "IBG1 blade 2 transmission compression"
    ::= { perimetaGlobalStatsEntry 355 }

  globalStatIBG2B2RcvdCompression OBJECT-TYPE
    SYNTAX       CounterBasedGauge64
    MAX-ACCESS   read-only
    STATUS       current
    DESCRIPTION  "IBG2 blade 2 rcvd compression"
    ::= { perimetaGlobalStatsEntry 356 }

  globalStatIBG2B2TransCompression OBJECT-TYPE
    SYNTAX       CounterBasedGauge64
    MAX-ACCESS   read-only
    STATUS       current
    DESCRIPTION  "IBG2 blade 2 transmission compression"
    ::= { perimetaGlobalStatsEntry 357 }

  globalStatIPG1B2RcvdCompression OBJECT-TYPE
    SYNTAX       CounterBasedGauge64
    MAX-ACCESS   read-only
    STATUS       current
    DESCRIPTION  "IPG1 blade 2 rcvd compression"
    ::= { perimetaGlobalStatsEntry 358 }

  globalStatIPG1B2TransCompression OBJECT-TYPE
    SYNTAX       CounterBasedGauge64
    MAX-ACCESS   read-only
    STATUS       current
    DESCRIPTION  "IPG1 blade 2 transmission compression"
    ::= { perimetaGlobalStatsEntry 359 }

  globalStatIFXG1B2RcvdCompression OBJECT-TYPE
    SYNTAX       CounterBasedGauge64
    MAX-ACCESS   read-only
    STATUS       current
    DESCRIPTION  "IFXG1 blade 2 rcvd compression"
    ::= { perimetaGlobalStatsEntry 360 }

  globalStatIFXG1B2TransCompression OBJECT-TYPE
    SYNTAX       CounterBasedGauge64
    MAX-ACCESS   read-only
    STATUS       current
    DESCRIPTION  "IFXG1 blade 2 transmission compression"
    ::= { perimetaGlobalStatsEntry 361 }

  globalStatIFXG2B2RcvdCompression OBJECT-TYPE
    SYNTAX       CounterBasedGauge64
    MAX-ACCESS   read-only
    STATUS       current
    DESCRIPTION  "IFXG2 blade 2 rcvd compression"
    ::= { perimetaGlobalStatsEntry 362 }

  globalStatIFXG2B2TransCompression OBJECT-TYPE
    SYNTAX       CounterBasedGauge64
    MAX-ACCESS   read-only
    STATUS       current
    DESCRIPTION  "IFXG2 blade 2 transmission compression"
    ::= { perimetaGlobalStatsEntry 363 }

  globalStatRPXG1B2RcvdCompression OBJECT-TYPE
    SYNTAX       CounterBasedGauge64
    MAX-ACCESS   read-only
    STATUS       current
    DESCRIPTION  "RPXG1 blade 2 rcvd compression"
    ::= { perimetaGlobalStatsEntry 364 }

  globalStatRPXG1B2TransCompression OBJECT-TYPE
    SYNTAX       CounterBasedGauge64
    MAX-ACCESS   read-only
    STATUS       current
    DESCRIPTION  "RPXG1 blade 2 transmission compression"
    ::= { perimetaGlobalStatsEntry 365 }

  globalStatRPXG2B2RcvdCompression OBJECT-TYPE
    SYNTAX       CounterBasedGauge64
    MAX-ACCESS   read-only
    STATUS       current
    DESCRIPTION  "RPXG2 blade 2 rcvd compression"
    ::= { perimetaGlobalStatsEntry 366 }

  globalStatRPXG2B2TransCompression OBJECT-TYPE
    SYNTAX       CounterBasedGauge64
    MAX-ACCESS   read-only
    STATUS       current
    DESCRIPTION  "RPXG2 blade 2 transmission compression"
    ::= { perimetaGlobalStatsEntry 367 }

  globalStatRPXG3B2RcvdCompression OBJECT-TYPE
    SYNTAX       CounterBasedGauge64
    MAX-ACCESS   read-only
    STATUS       current
    DESCRIPTION  "RPXG3 blade 2 rcvd compression"
    ::= { perimetaGlobalStatsEntry 368 }

  globalStatRPXG3B2TransCompression OBJECT-TYPE
    SYNTAX       CounterBasedGauge64
    MAX-ACCESS   read-only
    STATUS       current
    DESCRIPTION  "RPXG3 blade 2 transmission compression"
    ::= { perimetaGlobalStatsEntry 369 }

  globalStatRPXG4B2RcvdCompression OBJECT-TYPE
    SYNTAX       CounterBasedGauge64
    MAX-ACCESS   read-only
    STATUS       current
    DESCRIPTION  "RPXG4 blade 2 rcvd compression"
    ::= { perimetaGlobalStatsEntry 370 }

  globalStatRPXG4B2TransCompression OBJECT-TYPE
    SYNTAX       CounterBasedGauge64
    MAX-ACCESS   read-only
    STATUS       current
    DESCRIPTION  "RPXG4 blade 2 transmission compression"
    ::= { perimetaGlobalStatsEntry 371 }

  globalStatSigH248RequestsSent OBJECT-TYPE
    SYNTAX       CounterBasedGauge64
    MAX-ACCESS   read-only
    STATUS       current
    DESCRIPTION  "H248 requests sent"
    ::= { perimetaGlobalStatsEntry 372 }

  globalStatSigH248RequestsRcvd OBJECT-TYPE
    SYNTAX       CounterBasedGauge64
    MAX-ACCESS   read-only
    STATUS       current
    DESCRIPTION  "H248 requests rcvd"
    ::= { perimetaGlobalStatsEntry 373 }

  globalStatSigH248RepliesSent OBJECT-TYPE
    SYNTAX       CounterBasedGauge64
    MAX-ACCESS   read-only
    STATUS       current
    DESCRIPTION  "H248 replies sent"
    ::= { perimetaGlobalStatsEntry 374 }

  globalStatSigH248RepliesRcvd OBJECT-TYPE
    SYNTAX       CounterBasedGauge64
    MAX-ACCESS   read-only
    STATUS       current
    DESCRIPTION  "H248 replies rcvd"
    ::= { perimetaGlobalStatsEntry 375 }

  globalStatSigH248RequestsFailed OBJECT-TYPE
    SYNTAX       CounterBasedGauge64
    MAX-ACCESS   read-only
    STATUS       current
    DESCRIPTION  "H248 requests failed"
    ::= { perimetaGlobalStatsEntry 376 }

  globalStatSigH248RequestsRetried OBJECT-TYPE
    SYNTAX       CounterBasedGauge64
    MAX-ACCESS   read-only
    STATUS       current
    DESCRIPTION  "H248 requests retried"
    ::= { perimetaGlobalStatsEntry 377 }

  globalStatSigH248RepliesRetried OBJECT-TYPE
    SYNTAX       CounterBasedGauge64
    MAX-ACCESS   read-only
    STATUS       current
    DESCRIPTION  "H248 replies retried"
    ::= { perimetaGlobalStatsEntry 378 }

  globalStatMedH248RequestsSent OBJECT-TYPE
    SYNTAX       CounterBasedGauge64
    MAX-ACCESS   read-only
    STATUS       current
    DESCRIPTION  "H248 requests sent"
    ::= { perimetaGlobalStatsEntry 379 }

  globalStatMedH248RequestsRcvd OBJECT-TYPE
    SYNTAX       CounterBasedGauge64
    MAX-ACCESS   read-only
    STATUS       current
    DESCRIPTION  "H248 requests rcvd"
    ::= { perimetaGlobalStatsEntry 380 }

  globalStatMedH248RepliesSent OBJECT-TYPE
    SYNTAX       CounterBasedGauge64
    MAX-ACCESS   read-only
    STATUS       current
    DESCRIPTION  "H248 replies sent"
    ::= { perimetaGlobalStatsEntry 381 }

  globalStatMedH248RepliesRcvd OBJECT-TYPE
    SYNTAX       CounterBasedGauge64
    MAX-ACCESS   read-only
    STATUS       current
    DESCRIPTION  "H248 replies rcvd"
    ::= { perimetaGlobalStatsEntry 382 }

  globalStatMedH248RequestsFailed OBJECT-TYPE
    SYNTAX       CounterBasedGauge64
    MAX-ACCESS   read-only
    STATUS       current
    DESCRIPTION  "H248 requests failed"
    ::= { perimetaGlobalStatsEntry 383 }

  globalStatMedH248RequestsRetried OBJECT-TYPE
    SYNTAX       CounterBasedGauge64
    MAX-ACCESS   read-only
    STATUS       current
    DESCRIPTION  "H248 requests retried"
    ::= { perimetaGlobalStatsEntry 384 }

  globalStatMedH248RepliesRetried OBJECT-TYPE
    SYNTAX       CounterBasedGauge64
    MAX-ACCESS   read-only
    STATUS       current
    DESCRIPTION  "H248 replies retried"
    ::= { perimetaGlobalStatsEntry 385 }

  globalStatExcessTcpConns OBJECT-TYPE
    SYNTAX       CounterBasedGauge64
    MAX-ACCESS   read-only
    STATUS       current
    DESCRIPTION  "TCP connection limit exceeded"
    ::= { perimetaGlobalStatsEntry 386 }

  globalStatTlsHShakeQueued OBJECT-TYPE
    SYNTAX       CounterBasedGauge64
    MAX-ACCESS   read-only
    STATUS       current
    DESCRIPTION  "TLS handshakes queued"
    ::= { perimetaGlobalStatsEntry 387 }

  globalStatTlsHShakeInit OBJECT-TYPE
    SYNTAX       CounterBasedGauge64
    MAX-ACCESS   read-only
    STATUS       current
    DESCRIPTION  "TLS handshakes initiated"
    ::= { perimetaGlobalStatsEntry 388 }

  globalStatTlsHShakeComp OBJECT-TYPE
    SYNTAX       CounterBasedGauge64
    MAX-ACCESS   read-only
    STATUS       current
    DESCRIPTION  "TLS handshakes completed"
    ::= { perimetaGlobalStatsEntry 389 }

  globalStatTlsHShakeRej OBJECT-TYPE
    SYNTAX       CounterBasedGauge64
    MAX-ACCESS   read-only
    STATUS       current
    DESCRIPTION  "TLS handshakes rejected"
    ::= { perimetaGlobalStatsEntry 390 }

  globalStatTlsHShakeFail OBJECT-TYPE
    SYNTAX       CounterBasedGauge64
    MAX-ACCESS   read-only
    STATUS       current
    DESCRIPTION  "TLS handshakes failed"
    ::= { perimetaGlobalStatsEntry 391 }

  globalStatTlsProtErrs OBJECT-TYPE
    SYNTAX       CounterBasedGauge64
    MAX-ACCESS   read-only
    STATUS       current
    DESCRIPTION  "TLS protocol errors"
    ::= { perimetaGlobalStatsEntry 392 }

  globalStatTlsRenegs OBJECT-TYPE
    SYNTAX       CounterBasedGauge64
    MAX-ACCESS   read-only
    STATUS       current
    DESCRIPTION  "TLS protocol renegotiations"
    ::= { perimetaGlobalStatsEntry 393 }

  globalStatTlsSegDecoded OBJECT-TYPE
    SYNTAX       CounterBasedGauge64
    MAX-ACCESS   read-only
    STATUS       current
    DESCRIPTION  "TLS segments decoded"
    ::= { perimetaGlobalStatsEntry 394 }

  globalStatTlsBytesDecoded OBJECT-TYPE
    SYNTAX       CounterBasedGauge64
    MAX-ACCESS   read-only
    STATUS       current
    DESCRIPTION  "TLS bytes decoded"
    ::= { perimetaGlobalStatsEntry 395 }

  globalStatTlsSegEncoded OBJECT-TYPE
    SYNTAX       CounterBasedGauge64
    MAX-ACCESS   read-only
    STATUS       current
    DESCRIPTION  "TLS segments encoded"
    ::= { perimetaGlobalStatsEntry 396 }

  globalStatTlsBytesEncoded OBJECT-TYPE
    SYNTAX       CounterBasedGauge64
    MAX-ACCESS   read-only
    STATUS       current
    DESCRIPTION  "TLS bytes encoded"
    ::= { perimetaGlobalStatsEntry 397 }

  globalStatActiveTcpConns OBJECT-TYPE
    SYNTAX       CounterBasedGauge64
    MAX-ACCESS   read-only
    STATUS       current
    DESCRIPTION  "Active TCP connections"
    ::= { perimetaGlobalStatsEntry 398 }

  globalStatActiveTlsConns OBJECT-TYPE
    SYNTAX       CounterBasedGauge64
    MAX-ACCESS   read-only
    STATUS       current
    DESCRIPTION  "Active TLS connections"
    ::= { perimetaGlobalStatsEntry 399 }

  globalStatHShakeTlsConns OBJECT-TYPE
    SYNTAX       CounterBasedGauge64
    MAX-ACCESS   read-only
    STATUS       current
    DESCRIPTION  "Handshaking TLS connections"
    ::= { perimetaGlobalStatsEntry 400 }

  globalStatTcpTermNoData OBJECT-TYPE
    SYNTAX       CounterBasedGauge64
    MAX-ACCESS   read-only
    STATUS       current
    DESCRIPTION  "TCP connection terminated - no data
                  received"
    ::= { perimetaGlobalStatsEntry 401 }

  globalStatTcpTermNotAuth OBJECT-TYPE
    SYNTAX       CounterBasedGauge64
    MAX-ACCESS   read-only
    STATUS       current
    DESCRIPTION  "TCP connection terminated -
                  Authorization timeout"
    ::= { perimetaGlobalStatsEntry 402 }

  globalStatTcpTermUnauth OBJECT-TYPE
    SYNTAX       CounterBasedGauge64
    MAX-ACCESS   read-only
    STATUS       current
    DESCRIPTION  "TCP connection terminated when
                  unauthorized"
    ::= { perimetaGlobalStatsEntry 403 }

  globalStatMediaCapacityAlloc OBJECT-TYPE
    SYNTAX       CounterBasedGauge64
    MAX-ACCESS   read-only
    STATUS       current
    DESCRIPTION  "Media capacity unit allocation"
    ::= { perimetaGlobalStatsEntry 404 }

  globalStatCallAttempts OBJECT-TYPE
    SYNTAX       CounterBasedGauge64
    MAX-ACCESS   read-only
    STATUS       current
    DESCRIPTION  "Call attempts (last period)"
    ::= { perimetaGlobalStatsEntry 405 }

  globalStatCallAttemptSignalFailurePercent OBJECT-TYPE
    SYNTAX       CounterBasedGauge64
    UNITS        "/ 10000 %"
    MAX-ACCESS   read-only
    STATUS       current
    DESCRIPTION  "Percentage of call setup attempts
                  failing due to signaling failure"
    ::= { perimetaGlobalStatsEntry 406 }

  globalStatRPG1B1RcvdPacketRate OBJECT-TYPE
    SYNTAX       CounterBasedGauge64
    MAX-ACCESS   read-only
    STATUS       current
    DESCRIPTION  "RPG1 blade 1 pkts rcvd (pkts/s)"
    ::= { perimetaGlobalStatsEntry 407 }

  globalStatRPG1B1TransPacketRate OBJECT-TYPE
    SYNTAX       CounterBasedGauge64
    MAX-ACCESS   read-only
    STATUS       current
    DESCRIPTION  "RPG1 blade 1 pkts sent (pkts/s)"
    ::= { perimetaGlobalStatsEntry 408 }

  globalStatRPG1B1RcvdByteRate OBJECT-TYPE
    SYNTAX       CounterBasedGauge64
    MAX-ACCESS   read-only
    STATUS       current
    DESCRIPTION  "RPG1 blade 1 bytes rcvd (bytes/s)"
    ::= { perimetaGlobalStatsEntry 409 }

  globalStatRPG1B1TransByteRate OBJECT-TYPE
    SYNTAX       CounterBasedGauge64
    MAX-ACCESS   read-only
    STATUS       current
    DESCRIPTION  "RPG1 blade 1 bytes sent (bytes/s)"
    ::= { perimetaGlobalStatsEntry 410 }

  globalStatRPG1B1RcvdErrorRate OBJECT-TYPE
    SYNTAX       CounterBasedGauge64
    MAX-ACCESS   read-only
    STATUS       current
    DESCRIPTION  "RPG1 blade 1 receive errors (errors/s)"
    ::= { perimetaGlobalStatsEntry 411 }

  globalStatRPG1B1TransErrorRate OBJECT-TYPE
    SYNTAX       CounterBasedGauge64
    MAX-ACCESS   read-only
    STATUS       current
    DESCRIPTION  "RPG1 blade 1 transmission errors
                  (errors/s)"
    ::= { perimetaGlobalStatsEntry 412 }

  globalStatRPG1B1RcvdDropPacketRate OBJECT-TYPE
    SYNTAX       CounterBasedGauge64
    MAX-ACCESS   read-only
    STATUS       current
    DESCRIPTION  "RPG1 blade 1 rcvd pkts dropped (pkts/s)"
    ::= { perimetaGlobalStatsEntry 413 }

  globalStatRPG1B1TransDropPacketRate OBJECT-TYPE
    SYNTAX       CounterBasedGauge64
    MAX-ACCESS   read-only
    STATUS       current
    DESCRIPTION  "RPG1 blade 1 transmission pkts dropped
                  (pkts/s)"
    ::= { perimetaGlobalStatsEntry 414 }

  globalStatRPG1B1RcvdMulticastRate OBJECT-TYPE
    SYNTAX       CounterBasedGauge64
    MAX-ACCESS   read-only
    STATUS       current
    DESCRIPTION  "RPG1 blade 1 multicast pkts rcvd
                  (pkts/s)"
    ::= { perimetaGlobalStatsEntry 415 }

  globalStatRPG1B1TransCollisionRate OBJECT-TYPE
    SYNTAX       CounterBasedGauge64
    MAX-ACCESS   read-only
    STATUS       current
    DESCRIPTION  "RPG1 blade 1 transmission collisions per
                  second"
    ::= { perimetaGlobalStatsEntry 416 }

  globalStatRPG1B1RcvdLengthErrRate OBJECT-TYPE
    SYNTAX       CounterBasedGauge64
    MAX-ACCESS   read-only
    STATUS       current
    DESCRIPTION  "RPG1 blade 1 rcvd length errors
                  (errors/s)"
    ::= { perimetaGlobalStatsEntry 417 }

  globalStatRPG1B1RcvdOverrunErrRate OBJECT-TYPE
    SYNTAX       CounterBasedGauge64
    MAX-ACCESS   read-only
    STATUS       current
    DESCRIPTION  "RPG1 blade 1 rcvd overrun errors
                  (errors/s)"
    ::= { perimetaGlobalStatsEntry 418 }

  globalStatRPG1B1RcvdCRCErrRate OBJECT-TYPE
    SYNTAX       CounterBasedGauge64
    MAX-ACCESS   read-only
    STATUS       current
    DESCRIPTION  "RPG1 blade 1 rcvd CRC errors (errors/s)"
    ::= { perimetaGlobalStatsEntry 419 }

  globalStatRPG1B1RcvdFrameErrRate OBJECT-TYPE
    SYNTAX       CounterBasedGauge64
    MAX-ACCESS   read-only
    STATUS       current
    DESCRIPTION  "RPG1 blade 1 rcvd frame errors
                  (errors/s)"
    ::= { perimetaGlobalStatsEntry 420 }

  globalStatRPG1B1RcvdFifoFrameErrRate OBJECT-TYPE
    SYNTAX       CounterBasedGauge64
    MAX-ACCESS   read-only
    STATUS       current
    DESCRIPTION  "RPG1 blade 1 rcvd Fifo frame errors
                  (errors/s)"
    ::= { perimetaGlobalStatsEntry 421 }

  globalStatRPG1B1RcvdMissedFrameErrRate OBJECT-TYPE
    SYNTAX       CounterBasedGauge64
    MAX-ACCESS   read-only
    STATUS       current
    DESCRIPTION  "RPG1 blade 1 rcvd missed frame errors
                  (errors/s)"
    ::= { perimetaGlobalStatsEntry 422 }

  globalStatRPG1B1TransAbortErrRate OBJECT-TYPE
    SYNTAX       CounterBasedGauge64
    MAX-ACCESS   read-only
    STATUS       current
    DESCRIPTION  "RPG1 blade 1 transmission aborted errors
                  (errors/s)"
    ::= { perimetaGlobalStatsEntry 423 }

  globalStatRPG1B1TransCarrierErrRate OBJECT-TYPE
    SYNTAX       CounterBasedGauge64
    MAX-ACCESS   read-only
    STATUS       current
    DESCRIPTION  "RPG1 blade 1 transmission carrier errors
                  (errors/s)"
    ::= { perimetaGlobalStatsEntry 424 }

  globalStatRPG1B1TransFifoErrRate OBJECT-TYPE
    SYNTAX       CounterBasedGauge64
    MAX-ACCESS   read-only
    STATUS       current
    DESCRIPTION  "RPG1 blade 1 transmission Fifo errors
                  (errors/s)"
    ::= { perimetaGlobalStatsEntry 425 }

  globalStatRPG1B1TransHtbtErrRate OBJECT-TYPE
    SYNTAX       CounterBasedGauge64
    MAX-ACCESS   read-only
    STATUS       current
    DESCRIPTION  "RPG1 blade 1 transmission heartbeat
                  errors (errors/s)"
    ::= { perimetaGlobalStatsEntry 426 }

  globalStatRPG1B1TransWindowErrRate OBJECT-TYPE
    SYNTAX       CounterBasedGauge64
    MAX-ACCESS   read-only
    STATUS       current
    DESCRIPTION  "RPG1 blade 1 transmission window errors
                  (errors/s)"
    ::= { perimetaGlobalStatsEntry 427 }

  globalStatRPG2B1RcvdPacketRate OBJECT-TYPE
    SYNTAX       CounterBasedGauge64
    MAX-ACCESS   read-only
    STATUS       current
    DESCRIPTION  "RPG2 blade 1 pkts rcvd (pkts/s)"
    ::= { perimetaGlobalStatsEntry 428 }

  globalStatRPG2B1TransPacketRate OBJECT-TYPE
    SYNTAX       CounterBasedGauge64
    MAX-ACCESS   read-only
    STATUS       current
    DESCRIPTION  "RPG2 blade 1 pkts sent (pkts/s)"
    ::= { perimetaGlobalStatsEntry 429 }

  globalStatRPG2B1RcvdByteRate OBJECT-TYPE
    SYNTAX       CounterBasedGauge64
    MAX-ACCESS   read-only
    STATUS       current
    DESCRIPTION  "RPG2 blade 1 bytes rcvd (bytes/s)"
    ::= { perimetaGlobalStatsEntry 430 }

  globalStatRPG2B1TransByteRate OBJECT-TYPE
    SYNTAX       CounterBasedGauge64
    MAX-ACCESS   read-only
    STATUS       current
    DESCRIPTION  "RPG2 blade 1 bytes sent (bytes/s)"
    ::= { perimetaGlobalStatsEntry 431 }

  globalStatRPG2B1RcvdErrorRate OBJECT-TYPE
    SYNTAX       CounterBasedGauge64
    MAX-ACCESS   read-only
    STATUS       current
    DESCRIPTION  "RPG2 blade 1 receive errors (errors/s)"
    ::= { perimetaGlobalStatsEntry 432 }

  globalStatRPG2B1TransErrorRate OBJECT-TYPE
    SYNTAX       CounterBasedGauge64
    MAX-ACCESS   read-only
    STATUS       current
    DESCRIPTION  "RPG2 blade 1 transmission errors
                  (errors/s)"
    ::= { perimetaGlobalStatsEntry 433 }

  globalStatRPG2B1RcvdDropPacketRate OBJECT-TYPE
    SYNTAX       CounterBasedGauge64
    MAX-ACCESS   read-only
    STATUS       current
    DESCRIPTION  "RPG2 blade 1 rcvd pkts dropped (pkts/s)"
    ::= { perimetaGlobalStatsEntry 434 }

  globalStatRPG2B1TransDropPacketRate OBJECT-TYPE
    SYNTAX       CounterBasedGauge64
    MAX-ACCESS   read-only
    STATUS       current
    DESCRIPTION  "RPG2 blade 1 transmission pkts dropped
                  (pkts/s)"
    ::= { perimetaGlobalStatsEntry 435 }

  globalStatRPG2B1RcvdMulticastRate OBJECT-TYPE
    SYNTAX       CounterBasedGauge64
    MAX-ACCESS   read-only
    STATUS       current
    DESCRIPTION  "RPG2 blade 1 multicast pkts rcvd
                  (pkts/s)"
    ::= { perimetaGlobalStatsEntry 436 }

  globalStatRPG2B1TransCollisionRate OBJECT-TYPE
    SYNTAX       CounterBasedGauge64
    MAX-ACCESS   read-only
    STATUS       current
    DESCRIPTION  "RPG2 blade 1 transmission collisions per
                  second"
    ::= { perimetaGlobalStatsEntry 437 }

  globalStatRPG2B1RcvdLengthErrRate OBJECT-TYPE
    SYNTAX       CounterBasedGauge64
    MAX-ACCESS   read-only
    STATUS       current
    DESCRIPTION  "RPG2 blade 1 rcvd length errors
                  (errors/s)"
    ::= { perimetaGlobalStatsEntry 438 }

  globalStatRPG2B1RcvdOverrunErrRate OBJECT-TYPE
    SYNTAX       CounterBasedGauge64
    MAX-ACCESS   read-only
    STATUS       current
    DESCRIPTION  "RPG2 blade 1 rcvd overrun errors
                  (errors/s)"
    ::= { perimetaGlobalStatsEntry 439 }

  globalStatRPG2B1RcvdCRCErrRate OBJECT-TYPE
    SYNTAX       CounterBasedGauge64
    MAX-ACCESS   read-only
    STATUS       current
    DESCRIPTION  "RPG2 blade 1 rcvd CRC errors (errors/s)"
    ::= { perimetaGlobalStatsEntry 440 }

  globalStatRPG2B1RcvdFrameErrRate OBJECT-TYPE
    SYNTAX       CounterBasedGauge64
    MAX-ACCESS   read-only
    STATUS       current
    DESCRIPTION  "RPG2 blade 1 rcvd frame errors
                  (errors/s)"
    ::= { perimetaGlobalStatsEntry 441 }

  globalStatRPG2B1RcvdFifoFrameErrRate OBJECT-TYPE
    SYNTAX       CounterBasedGauge64
    MAX-ACCESS   read-only
    STATUS       current
    DESCRIPTION  "RPG2 blade 1 rcvd Fifo frame errors
                  (errors/s)"
    ::= { perimetaGlobalStatsEntry 442 }

  globalStatRPG2B1RcvdMissedFrameErrRate OBJECT-TYPE
    SYNTAX       CounterBasedGauge64
    MAX-ACCESS   read-only
    STATUS       current
    DESCRIPTION  "RPG2 blade 1 rcvd missed frame errors
                  (errors/s)"
    ::= { perimetaGlobalStatsEntry 443 }

  globalStatRPG2B1TransAbortErrRate OBJECT-TYPE
    SYNTAX       CounterBasedGauge64
    MAX-ACCESS   read-only
    STATUS       current
    DESCRIPTION  "RPG2 blade 1 transmission aborted errors
                  (errors/s)"
    ::= { perimetaGlobalStatsEntry 444 }

  globalStatRPG2B1TransCarrierErrRate OBJECT-TYPE
    SYNTAX       CounterBasedGauge64
    MAX-ACCESS   read-only
    STATUS       current
    DESCRIPTION  "RPG2 blade 1 transmission carrier errors
                  (errors/s)"
    ::= { perimetaGlobalStatsEntry 445 }

  globalStatRPG2B1TransFifoErrRate OBJECT-TYPE
    SYNTAX       CounterBasedGauge64
    MAX-ACCESS   read-only
    STATUS       current
    DESCRIPTION  "RPG2 blade 1 transmission Fifo errors
                  (errors/s)"
    ::= { perimetaGlobalStatsEntry 446 }

  globalStatRPG2B1TransHtbtErrRate OBJECT-TYPE
    SYNTAX       CounterBasedGauge64
    MAX-ACCESS   read-only
    STATUS       current
    DESCRIPTION  "RPG2 blade 1 transmission heartbeat
                  errors (errors/s)"
    ::= { perimetaGlobalStatsEntry 447 }

  globalStatRPG2B1TransWindowErrRate OBJECT-TYPE
    SYNTAX       CounterBasedGauge64
    MAX-ACCESS   read-only
    STATUS       current
    DESCRIPTION  "RPG2 blade 1 transmission window errors
                  (errors/s)"
    ::= { perimetaGlobalStatsEntry 448 }

  globalStatRPG3B1RcvdPacketRate OBJECT-TYPE
    SYNTAX       CounterBasedGauge64
    MAX-ACCESS   read-only
    STATUS       current
    DESCRIPTION  "RPG3 blade 1 pkts rcvd (pkts/s)"
    ::= { perimetaGlobalStatsEntry 449 }

  globalStatRPG3B1TransPacketRate OBJECT-TYPE
    SYNTAX       CounterBasedGauge64
    MAX-ACCESS   read-only
    STATUS       current
    DESCRIPTION  "RPG3 blade 1 pkts sent (pkts/s)"
    ::= { perimetaGlobalStatsEntry 450 }

  globalStatRPG3B1RcvdByteRate OBJECT-TYPE
    SYNTAX       CounterBasedGauge64
    MAX-ACCESS   read-only
    STATUS       current
    DESCRIPTION  "RPG3 blade 1 bytes rcvd (bytes/s)"
    ::= { perimetaGlobalStatsEntry 451 }

  globalStatRPG3B1TransByteRate OBJECT-TYPE
    SYNTAX       CounterBasedGauge64
    MAX-ACCESS   read-only
    STATUS       current
    DESCRIPTION  "RPG3 blade 1 bytes sent (bytes/s)"
    ::= { perimetaGlobalStatsEntry 452 }

  globalStatRPG3B1RcvdErrorRate OBJECT-TYPE
    SYNTAX       CounterBasedGauge64
    MAX-ACCESS   read-only
    STATUS       current
    DESCRIPTION  "RPG3 blade 1 receive errors (errors/s)"
    ::= { perimetaGlobalStatsEntry 453 }

  globalStatRPG3B1TransErrorRate OBJECT-TYPE
    SYNTAX       CounterBasedGauge64
    MAX-ACCESS   read-only
    STATUS       current
    DESCRIPTION  "RPG3 blade 1 transmission errors
                  (errors/s)"
    ::= { perimetaGlobalStatsEntry 454 }

  globalStatRPG3B1RcvdDropPacketRate OBJECT-TYPE
    SYNTAX       CounterBasedGauge64
    MAX-ACCESS   read-only
    STATUS       current
    DESCRIPTION  "RPG3 blade 1 rcvd pkts dropped (pkts/s)"
    ::= { perimetaGlobalStatsEntry 455 }

  globalStatRPG3B1TransDropPacketRate OBJECT-TYPE
    SYNTAX       CounterBasedGauge64
    MAX-ACCESS   read-only
    STATUS       current
    DESCRIPTION  "RPG3 blade 1 transmission pkts dropped
                  (pkts/s)"
    ::= { perimetaGlobalStatsEntry 456 }

  globalStatRPG3B1RcvdMulticastRate OBJECT-TYPE
    SYNTAX       CounterBasedGauge64
    MAX-ACCESS   read-only
    STATUS       current
    DESCRIPTION  "RPG3 blade 1 multicast pkts rcvd
                  (pkts/s)"
    ::= { perimetaGlobalStatsEntry 457 }

  globalStatRPG3B1TransCollisionRate OBJECT-TYPE
    SYNTAX       CounterBasedGauge64
    MAX-ACCESS   read-only
    STATUS       current
    DESCRIPTION  "RPG3 blade 1 transmission collisions per
                  second"
    ::= { perimetaGlobalStatsEntry 458 }

  globalStatRPG3B1RcvdLengthErrRate OBJECT-TYPE
    SYNTAX       CounterBasedGauge64
    MAX-ACCESS   read-only
    STATUS       current
    DESCRIPTION  "RPG3 blade 1 rcvd length errors
                  (errors/s)"
    ::= { perimetaGlobalStatsEntry 459 }

  globalStatRPG3B1RcvdOverrunErrRate OBJECT-TYPE
    SYNTAX       CounterBasedGauge64
    MAX-ACCESS   read-only
    STATUS       current
    DESCRIPTION  "RPG3 blade 1 rcvd overrun errors
                  (errors/s)"
    ::= { perimetaGlobalStatsEntry 460 }

  globalStatRPG3B1RcvdCRCErrRate OBJECT-TYPE
    SYNTAX       CounterBasedGauge64
    MAX-ACCESS   read-only
    STATUS       current
    DESCRIPTION  "RPG3 blade 1 rcvd CRC errors (errors/s)"
    ::= { perimetaGlobalStatsEntry 461 }

  globalStatRPG3B1RcvdFrameErrRate OBJECT-TYPE
    SYNTAX       CounterBasedGauge64
    MAX-ACCESS   read-only
    STATUS       current
    DESCRIPTION  "RPG3 blade 1 rcvd frame errors
                  (errors/s)"
    ::= { perimetaGlobalStatsEntry 462 }

  globalStatRPG3B1RcvdFifoFrameErrRate OBJECT-TYPE
    SYNTAX       CounterBasedGauge64
    MAX-ACCESS   read-only
    STATUS       current
    DESCRIPTION  "RPG3 blade 1 rcvd Fifo frame errors
                  (errors/s)"
    ::= { perimetaGlobalStatsEntry 463 }

  globalStatRPG3B1RcvdMissedFrameErrRate OBJECT-TYPE
    SYNTAX       CounterBasedGauge64
    MAX-ACCESS   read-only
    STATUS       current
    DESCRIPTION  "RPG3 blade 1 rcvd missed frame errors
                  (errors/s)"
    ::= { perimetaGlobalStatsEntry 464 }

  globalStatRPG3B1TransAbortErrRate OBJECT-TYPE
    SYNTAX       CounterBasedGauge64
    MAX-ACCESS   read-only
    STATUS       current
    DESCRIPTION  "RPG3 blade 1 transmission aborted errors
                  (errors/s)"
    ::= { perimetaGlobalStatsEntry 465 }

  globalStatRPG3B1TransCarrierErrRate OBJECT-TYPE
    SYNTAX       CounterBasedGauge64
    MAX-ACCESS   read-only
    STATUS       current
    DESCRIPTION  "RPG3 blade 1 transmission carrier errors
                  (errors/s)"
    ::= { perimetaGlobalStatsEntry 466 }

  globalStatRPG3B1TransFifoErrRate OBJECT-TYPE
    SYNTAX       CounterBasedGauge64
    MAX-ACCESS   read-only
    STATUS       current
    DESCRIPTION  "RPG3 blade 1 transmission Fifo errors
                  (errors/s)"
    ::= { perimetaGlobalStatsEntry 467 }

  globalStatRPG3B1TransHtbtErrRate OBJECT-TYPE
    SYNTAX       CounterBasedGauge64
    MAX-ACCESS   read-only
    STATUS       current
    DESCRIPTION  "RPG3 blade 1 transmission heartbeat
                  errors (errors/s)"
    ::= { perimetaGlobalStatsEntry 468 }

  globalStatRPG3B1TransWindowErrRate OBJECT-TYPE
    SYNTAX       CounterBasedGauge64
    MAX-ACCESS   read-only
    STATUS       current
    DESCRIPTION  "RPG3 blade 1 transmission window errors
                  (errors/s)"
    ::= { perimetaGlobalStatsEntry 469 }

  globalStatRPG4B1RcvdPacketRate OBJECT-TYPE
    SYNTAX       CounterBasedGauge64
    MAX-ACCESS   read-only
    STATUS       current
    DESCRIPTION  "RPG4 blade 1 pkts rcvd (pkts/s)"
    ::= { perimetaGlobalStatsEntry 470 }

  globalStatRPG4B1TransPacketRate OBJECT-TYPE
    SYNTAX       CounterBasedGauge64
    MAX-ACCESS   read-only
    STATUS       current
    DESCRIPTION  "RPG4 blade 1 pkts sent (pkts/s)"
    ::= { perimetaGlobalStatsEntry 471 }

  globalStatRPG4B1RcvdByteRate OBJECT-TYPE
    SYNTAX       CounterBasedGauge64
    MAX-ACCESS   read-only
    STATUS       current
    DESCRIPTION  "RPG4 blade 1 bytes rcvd (bytes/s)"
    ::= { perimetaGlobalStatsEntry 472 }

  globalStatRPG4B1TransByteRate OBJECT-TYPE
    SYNTAX       CounterBasedGauge64
    MAX-ACCESS   read-only
    STATUS       current
    DESCRIPTION  "RPG4 blade 1 bytes sent (bytes/s)"
    ::= { perimetaGlobalStatsEntry 473 }

  globalStatRPG4B1RcvdErrorRate OBJECT-TYPE
    SYNTAX       CounterBasedGauge64
    MAX-ACCESS   read-only
    STATUS       current
    DESCRIPTION  "RPG4 blade 1 receive errors (errors/s)"
    ::= { perimetaGlobalStatsEntry 474 }

  globalStatRPG4B1TransErrorRate OBJECT-TYPE
    SYNTAX       CounterBasedGauge64
    MAX-ACCESS   read-only
    STATUS       current
    DESCRIPTION  "RPG4 blade 1 transmission errors
                  (errors/s)"
    ::= { perimetaGlobalStatsEntry 475 }

  globalStatRPG4B1RcvdDropPacketRate OBJECT-TYPE
    SYNTAX       CounterBasedGauge64
    MAX-ACCESS   read-only
    STATUS       current
    DESCRIPTION  "RPG4 blade 1 rcvd pkts dropped (pkts/s)"
    ::= { perimetaGlobalStatsEntry 476 }

  globalStatRPG4B1TransDropPacketRate OBJECT-TYPE
    SYNTAX       CounterBasedGauge64
    MAX-ACCESS   read-only
    STATUS       current
    DESCRIPTION  "RPG4 blade 1 transmission pkts dropped
                  (pkts/s)"
    ::= { perimetaGlobalStatsEntry 477 }

  globalStatRPG4B1RcvdMulticastRate OBJECT-TYPE
    SYNTAX       CounterBasedGauge64
    MAX-ACCESS   read-only
    STATUS       current
    DESCRIPTION  "RPG4 blade 1 multicast pkts rcvd
                  (pkts/s)"
    ::= { perimetaGlobalStatsEntry 478 }

  globalStatRPG4B1TransCollisionRate OBJECT-TYPE
    SYNTAX       CounterBasedGauge64
    MAX-ACCESS   read-only
    STATUS       current
    DESCRIPTION  "RPG4 blade 1 transmission collisions per
                  second"
    ::= { perimetaGlobalStatsEntry 479 }

  globalStatRPG4B1RcvdLengthErrRate OBJECT-TYPE
    SYNTAX       CounterBasedGauge64
    MAX-ACCESS   read-only
    STATUS       current
    DESCRIPTION  "RPG4 blade 1 rcvd length errors
                  (errors/s)"
    ::= { perimetaGlobalStatsEntry 480 }

  globalStatRPG4B1RcvdOverrunErrRate OBJECT-TYPE
    SYNTAX       CounterBasedGauge64
    MAX-ACCESS   read-only
    STATUS       current
    DESCRIPTION  "RPG4 blade 1 rcvd overrun errors
                  (errors/s)"
    ::= { perimetaGlobalStatsEntry 481 }

  globalStatRPG4B1RcvdCRCErrRate OBJECT-TYPE
    SYNTAX       CounterBasedGauge64
    MAX-ACCESS   read-only
    STATUS       current
    DESCRIPTION  "RPG4 blade 1 rcvd CRC errors (errors/s)"
    ::= { perimetaGlobalStatsEntry 482 }

  globalStatRPG4B1RcvdFrameErrRate OBJECT-TYPE
    SYNTAX       CounterBasedGauge64
    MAX-ACCESS   read-only
    STATUS       current
    DESCRIPTION  "RPG4 blade 1 rcvd frame errors
                  (errors/s)"
    ::= { perimetaGlobalStatsEntry 483 }

  globalStatRPG4B1RcvdFifoFrameErrRate OBJECT-TYPE
    SYNTAX       CounterBasedGauge64
    MAX-ACCESS   read-only
    STATUS       current
    DESCRIPTION  "RPG4 blade 1 rcvd Fifo frame errors
                  (errors/s)"
    ::= { perimetaGlobalStatsEntry 484 }

  globalStatRPG4B1RcvdMissedFrameErrRate OBJECT-TYPE
    SYNTAX       CounterBasedGauge64
    MAX-ACCESS   read-only
    STATUS       current
    DESCRIPTION  "RPG4 blade 1 rcvd missed frame errors
                  (errors/s)"
    ::= { perimetaGlobalStatsEntry 485 }

  globalStatRPG4B1TransAbortErrRate OBJECT-TYPE
    SYNTAX       CounterBasedGauge64
    MAX-ACCESS   read-only
    STATUS       current
    DESCRIPTION  "RPG4 blade 1 transmission aborted errors
                  (errors/s)"
    ::= { perimetaGlobalStatsEntry 486 }

  globalStatRPG4B1TransCarrierErrRate OBJECT-TYPE
    SYNTAX       CounterBasedGauge64
    MAX-ACCESS   read-only
    STATUS       current
    DESCRIPTION  "RPG4 blade 1 transmission carrier errors
                  (errors/s)"
    ::= { perimetaGlobalStatsEntry 487 }

  globalStatRPG4B1TransFifoErrRate OBJECT-TYPE
    SYNTAX       CounterBasedGauge64
    MAX-ACCESS   read-only
    STATUS       current
    DESCRIPTION  "RPG4 blade 1 transmission Fifo errors
                  (errors/s)"
    ::= { perimetaGlobalStatsEntry 488 }

  globalStatRPG4B1TransHtbtErrRate OBJECT-TYPE
    SYNTAX       CounterBasedGauge64
    MAX-ACCESS   read-only
    STATUS       current
    DESCRIPTION  "RPG4 blade 1 transmission heartbeat
                  errors (errors/s)"
    ::= { perimetaGlobalStatsEntry 489 }

  globalStatRPG4B1TransWindowErrRate OBJECT-TYPE
    SYNTAX       CounterBasedGauge64
    MAX-ACCESS   read-only
    STATUS       current
    DESCRIPTION  "RPG4 blade 1 transmission window errors
                  (errors/s)"
    ::= { perimetaGlobalStatsEntry 490 }

  globalStatRPG5B1RcvdPacketRate OBJECT-TYPE
    SYNTAX       CounterBasedGauge64
    MAX-ACCESS   read-only
    STATUS       current
    DESCRIPTION  "RPG5 blade 1 pkts rcvd (pkts/s)"
    ::= { perimetaGlobalStatsEntry 491 }

  globalStatRPG5B1TransPacketRate OBJECT-TYPE
    SYNTAX       CounterBasedGauge64
    MAX-ACCESS   read-only
    STATUS       current
    DESCRIPTION  "RPG5 blade 1 pkts sent (pkts/s)"
    ::= { perimetaGlobalStatsEntry 492 }

  globalStatRPG5B1RcvdByteRate OBJECT-TYPE
    SYNTAX       CounterBasedGauge64
    MAX-ACCESS   read-only
    STATUS       current
    DESCRIPTION  "RPG5 blade 1 bytes rcvd (bytes/s)"
    ::= { perimetaGlobalStatsEntry 493 }

  globalStatRPG5B1TransByteRate OBJECT-TYPE
    SYNTAX       CounterBasedGauge64
    MAX-ACCESS   read-only
    STATUS       current
    DESCRIPTION  "RPG5 blade 1 bytes sent (bytes/s)"
    ::= { perimetaGlobalStatsEntry 494 }

  globalStatRPG5B1RcvdErrorRate OBJECT-TYPE
    SYNTAX       CounterBasedGauge64
    MAX-ACCESS   read-only
    STATUS       current
    DESCRIPTION  "RPG5 blade 1 receive errors (errors/s)"
    ::= { perimetaGlobalStatsEntry 495 }

  globalStatRPG5B1TransErrorRate OBJECT-TYPE
    SYNTAX       CounterBasedGauge64
    MAX-ACCESS   read-only
    STATUS       current
    DESCRIPTION  "RPG5 blade 1 transmission errors
                  (errors/s)"
    ::= { perimetaGlobalStatsEntry 496 }

  globalStatRPG5B1RcvdDropPacketRate OBJECT-TYPE
    SYNTAX       CounterBasedGauge64
    MAX-ACCESS   read-only
    STATUS       current
    DESCRIPTION  "RPG5 blade 1 rcvd pkts dropped (pkts/s)"
    ::= { perimetaGlobalStatsEntry 497 }

  globalStatRPG5B1TransDropPacketRate OBJECT-TYPE
    SYNTAX       CounterBasedGauge64
    MAX-ACCESS   read-only
    STATUS       current
    DESCRIPTION  "RPG5 blade 1 transmission pkts dropped
                  (pkts/s)"
    ::= { perimetaGlobalStatsEntry 498 }

  globalStatRPG5B1RcvdMulticastRate OBJECT-TYPE
    SYNTAX       CounterBasedGauge64
    MAX-ACCESS   read-only
    STATUS       current
    DESCRIPTION  "RPG5 blade 1 multicast pkts rcvd
                  (pkts/s)"
    ::= { perimetaGlobalStatsEntry 499 }

  globalStatRPG5B1TransCollisionRate OBJECT-TYPE
    SYNTAX       CounterBasedGauge64
    MAX-ACCESS   read-only
    STATUS       current
    DESCRIPTION  "RPG5 blade 1 transmission collisions per
                  second"
    ::= { perimetaGlobalStatsEntry 500 }

  globalStatRPG5B1RcvdLengthErrRate OBJECT-TYPE
    SYNTAX       CounterBasedGauge64
    MAX-ACCESS   read-only
    STATUS       current
    DESCRIPTION  "RPG5 blade 1 rcvd length errors
                  (errors/s)"
    ::= { perimetaGlobalStatsEntry 501 }

  globalStatRPG5B1RcvdOverrunErrRate OBJECT-TYPE
    SYNTAX       CounterBasedGauge64
    MAX-ACCESS   read-only
    STATUS       current
    DESCRIPTION  "RPG5 blade 1 rcvd overrun errors
                  (errors/s)"
    ::= { perimetaGlobalStatsEntry 502 }

  globalStatRPG5B1RcvdCRCErrRate OBJECT-TYPE
    SYNTAX       CounterBasedGauge64
    MAX-ACCESS   read-only
    STATUS       current
    DESCRIPTION  "RPG5 blade 1 rcvd CRC errors (errors/s)"
    ::= { perimetaGlobalStatsEntry 503 }

  globalStatRPG5B1RcvdFrameErrRate OBJECT-TYPE
    SYNTAX       CounterBasedGauge64
    MAX-ACCESS   read-only
    STATUS       current
    DESCRIPTION  "RPG5 blade 1 rcvd frame errors
                  (errors/s)"
    ::= { perimetaGlobalStatsEntry 504 }

  globalStatRPG5B1RcvdFifoFrameErrRate OBJECT-TYPE
    SYNTAX       CounterBasedGauge64
    MAX-ACCESS   read-only
    STATUS       current
    DESCRIPTION  "RPG5 blade 1 rcvd Fifo frame errors
                  (errors/s)"
    ::= { perimetaGlobalStatsEntry 505 }

  globalStatRPG5B1RcvdMissedFrameErrRate OBJECT-TYPE
    SYNTAX       CounterBasedGauge64
    MAX-ACCESS   read-only
    STATUS       current
    DESCRIPTION  "RPG5 blade 1 rcvd missed frame errors
                  (errors/s)"
    ::= { perimetaGlobalStatsEntry 506 }

  globalStatRPG5B1TransAbortErrRate OBJECT-TYPE
    SYNTAX       CounterBasedGauge64
    MAX-ACCESS   read-only
    STATUS       current
    DESCRIPTION  "RPG5 blade 1 transmission aborted errors
                  (errors/s)"
    ::= { perimetaGlobalStatsEntry 507 }

  globalStatRPG5B1TransCarrierErrRate OBJECT-TYPE
    SYNTAX       CounterBasedGauge64
    MAX-ACCESS   read-only
    STATUS       current
    DESCRIPTION  "RPG5 blade 1 transmission carrier errors
                  (errors/s)"
    ::= { perimetaGlobalStatsEntry 508 }

  globalStatRPG5B1TransFifoErrRate OBJECT-TYPE
    SYNTAX       CounterBasedGauge64
    MAX-ACCESS   read-only
    STATUS       current
    DESCRIPTION  "RPG5 blade 1 transmission Fifo errors
                  (errors/s)"
    ::= { perimetaGlobalStatsEntry 509 }

  globalStatRPG5B1TransHtbtErrRate OBJECT-TYPE
    SYNTAX       CounterBasedGauge64
    MAX-ACCESS   read-only
    STATUS       current
    DESCRIPTION  "RPG5 blade 1 transmission heartbeat
                  errors (errors/s)"
    ::= { perimetaGlobalStatsEntry 510 }

  globalStatRPG5B1TransWindowErrRate OBJECT-TYPE
    SYNTAX       CounterBasedGauge64
    MAX-ACCESS   read-only
    STATUS       current
    DESCRIPTION  "RPG5 blade 1 transmission window errors
                  (errors/s)"
    ::= { perimetaGlobalStatsEntry 511 }

  globalStatRPG6B1RcvdPacketRate OBJECT-TYPE
    SYNTAX       CounterBasedGauge64
    MAX-ACCESS   read-only
    STATUS       current
    DESCRIPTION  "RPG6 blade 1 pkts rcvd (pkts/s)"
    ::= { perimetaGlobalStatsEntry 512 }

  globalStatRPG6B1TransPacketRate OBJECT-TYPE
    SYNTAX       CounterBasedGauge64
    MAX-ACCESS   read-only
    STATUS       current
    DESCRIPTION  "RPG6 blade 1 pkts sent (pkts/s)"
    ::= { perimetaGlobalStatsEntry 513 }

  globalStatRPG6B1RcvdByteRate OBJECT-TYPE
    SYNTAX       CounterBasedGauge64
    MAX-ACCESS   read-only
    STATUS       current
    DESCRIPTION  "RPG6 blade 1 bytes rcvd (bytes/s)"
    ::= { perimetaGlobalStatsEntry 514 }

  globalStatRPG6B1TransByteRate OBJECT-TYPE
    SYNTAX       CounterBasedGauge64
    MAX-ACCESS   read-only
    STATUS       current
    DESCRIPTION  "RPG6 blade 1 bytes sent (bytes/s)"
    ::= { perimetaGlobalStatsEntry 515 }

  globalStatRPG6B1RcvdErrorRate OBJECT-TYPE
    SYNTAX       CounterBasedGauge64
    MAX-ACCESS   read-only
    STATUS       current
    DESCRIPTION  "RPG6 blade 1 receive errors (errors/s)"
    ::= { perimetaGlobalStatsEntry 516 }

  globalStatRPG6B1TransErrorRate OBJECT-TYPE
    SYNTAX       CounterBasedGauge64
    MAX-ACCESS   read-only
    STATUS       current
    DESCRIPTION  "RPG6 blade 1 transmission errors
                  (errors/s)"
    ::= { perimetaGlobalStatsEntry 517 }

  globalStatRPG6B1RcvdDropPacketRate OBJECT-TYPE
    SYNTAX       CounterBasedGauge64
    MAX-ACCESS   read-only
    STATUS       current
    DESCRIPTION  "RPG6 blade 1 rcvd pkts dropped (pkts/s)"
    ::= { perimetaGlobalStatsEntry 518 }

  globalStatRPG6B1TransDropPacketRate OBJECT-TYPE
    SYNTAX       CounterBasedGauge64
    MAX-ACCESS   read-only
    STATUS       current
    DESCRIPTION  "RPG6 blade 1 transmission pkts dropped
                  (pkts/s)"
    ::= { perimetaGlobalStatsEntry 519 }

  globalStatRPG6B1RcvdMulticastRate OBJECT-TYPE
    SYNTAX       CounterBasedGauge64
    MAX-ACCESS   read-only
    STATUS       current
    DESCRIPTION  "RPG6 blade 1 multicast pkts rcvd
                  (pkts/s)"
    ::= { perimetaGlobalStatsEntry 520 }

  globalStatRPG6B1TransCollisionRate OBJECT-TYPE
    SYNTAX       CounterBasedGauge64
    MAX-ACCESS   read-only
    STATUS       current
    DESCRIPTION  "RPG6 blade 1 transmission collisions per
                  second"
    ::= { perimetaGlobalStatsEntry 521 }

  globalStatRPG6B1RcvdLengthErrRate OBJECT-TYPE
    SYNTAX       CounterBasedGauge64
    MAX-ACCESS   read-only
    STATUS       current
    DESCRIPTION  "RPG6 blade 1 rcvd length errors
                  (errors/s)"
    ::= { perimetaGlobalStatsEntry 522 }

  globalStatRPG6B1RcvdOverrunErrRate OBJECT-TYPE
    SYNTAX       CounterBasedGauge64
    MAX-ACCESS   read-only
    STATUS       current
    DESCRIPTION  "RPG6 blade 1 rcvd overrun errors
                  (errors/s)"
    ::= { perimetaGlobalStatsEntry 523 }

  globalStatRPG6B1RcvdCRCErrRate OBJECT-TYPE
    SYNTAX       CounterBasedGauge64
    MAX-ACCESS   read-only
    STATUS       current
    DESCRIPTION  "RPG6 blade 1 rcvd CRC errors (errors/s)"
    ::= { perimetaGlobalStatsEntry 524 }

  globalStatRPG6B1RcvdFrameErrRate OBJECT-TYPE
    SYNTAX       CounterBasedGauge64
    MAX-ACCESS   read-only
    STATUS       current
    DESCRIPTION  "RPG6 blade 1 rcvd frame errors
                  (errors/s)"
    ::= { perimetaGlobalStatsEntry 525 }

  globalStatRPG6B1RcvdFifoFrameErrRate OBJECT-TYPE
    SYNTAX       CounterBasedGauge64
    MAX-ACCESS   read-only
    STATUS       current
    DESCRIPTION  "RPG6 blade 1 rcvd Fifo frame errors
                  (errors/s)"
    ::= { perimetaGlobalStatsEntry 526 }

  globalStatRPG6B1RcvdMissedFrameErrRate OBJECT-TYPE
    SYNTAX       CounterBasedGauge64
    MAX-ACCESS   read-only
    STATUS       current
    DESCRIPTION  "RPG6 blade 1 rcvd missed frame errors
                  (errors/s)"
    ::= { perimetaGlobalStatsEntry 527 }

  globalStatRPG6B1TransAbortErrRate OBJECT-TYPE
    SYNTAX       CounterBasedGauge64
    MAX-ACCESS   read-only
    STATUS       current
    DESCRIPTION  "RPG6 blade 1 transmission aborted errors
                  (errors/s)"
    ::= { perimetaGlobalStatsEntry 528 }

  globalStatRPG6B1TransCarrierErrRate OBJECT-TYPE
    SYNTAX       CounterBasedGauge64
    MAX-ACCESS   read-only
    STATUS       current
    DESCRIPTION  "RPG6 blade 1 transmission carrier errors
                  (errors/s)"
    ::= { perimetaGlobalStatsEntry 529 }

  globalStatRPG6B1TransFifoErrRate OBJECT-TYPE
    SYNTAX       CounterBasedGauge64
    MAX-ACCESS   read-only
    STATUS       current
    DESCRIPTION  "RPG6 blade 1 transmission Fifo errors
                  (errors/s)"
    ::= { perimetaGlobalStatsEntry 530 }

  globalStatRPG6B1TransHtbtErrRate OBJECT-TYPE
    SYNTAX       CounterBasedGauge64
    MAX-ACCESS   read-only
    STATUS       current
    DESCRIPTION  "RPG6 blade 1 transmission heartbeat
                  errors (errors/s)"
    ::= { perimetaGlobalStatsEntry 531 }

  globalStatRPG6B1TransWindowErrRate OBJECT-TYPE
    SYNTAX       CounterBasedGauge64
    MAX-ACCESS   read-only
    STATUS       current
    DESCRIPTION  "RPG6 blade 1 transmission window errors
                  (errors/s)"
    ::= { perimetaGlobalStatsEntry 532 }

  globalStatRPG7B1RcvdPacketRate OBJECT-TYPE
    SYNTAX       CounterBasedGauge64
    MAX-ACCESS   read-only
    STATUS       current
    DESCRIPTION  "RPG7 blade 1 pkts rcvd (pkts/s)"
    ::= { perimetaGlobalStatsEntry 533 }

  globalStatRPG7B1TransPacketRate OBJECT-TYPE
    SYNTAX       CounterBasedGauge64
    MAX-ACCESS   read-only
    STATUS       current
    DESCRIPTION  "RPG7 blade 1 pkts sent (pkts/s)"
    ::= { perimetaGlobalStatsEntry 534 }

  globalStatRPG7B1RcvdByteRate OBJECT-TYPE
    SYNTAX       CounterBasedGauge64
    MAX-ACCESS   read-only
    STATUS       current
    DESCRIPTION  "RPG7 blade 1 bytes rcvd (bytes/s)"
    ::= { perimetaGlobalStatsEntry 535 }

  globalStatRPG7B1TransByteRate OBJECT-TYPE
    SYNTAX       CounterBasedGauge64
    MAX-ACCESS   read-only
    STATUS       current
    DESCRIPTION  "RPG7 blade 1 bytes sent (bytes/s)"
    ::= { perimetaGlobalStatsEntry 536 }

  globalStatRPG7B1RcvdErrorRate OBJECT-TYPE
    SYNTAX       CounterBasedGauge64
    MAX-ACCESS   read-only
    STATUS       current
    DESCRIPTION  "RPG7 blade 1 receive errors (errors/s)"
    ::= { perimetaGlobalStatsEntry 537 }

  globalStatRPG7B1TransErrorRate OBJECT-TYPE
    SYNTAX       CounterBasedGauge64
    MAX-ACCESS   read-only
    STATUS       current
    DESCRIPTION  "RPG7 blade 1 transmission errors
                  (errors/s)"
    ::= { perimetaGlobalStatsEntry 538 }

  globalStatRPG7B1RcvdDropPacketRate OBJECT-TYPE
    SYNTAX       CounterBasedGauge64
    MAX-ACCESS   read-only
    STATUS       current
    DESCRIPTION  "RPG7 blade 1 rcvd pkts dropped (pkts/s)"
    ::= { perimetaGlobalStatsEntry 539 }

  globalStatRPG7B1TransDropPacketRate OBJECT-TYPE
    SYNTAX       CounterBasedGauge64
    MAX-ACCESS   read-only
    STATUS       current
    DESCRIPTION  "RPG7 blade 1 transmission pkts dropped
                  (pkts/s)"
    ::= { perimetaGlobalStatsEntry 540 }

  globalStatRPG7B1RcvdMulticastRate OBJECT-TYPE
    SYNTAX       CounterBasedGauge64
    MAX-ACCESS   read-only
    STATUS       current
    DESCRIPTION  "RPG7 blade 1 multicast pkts rcvd
                  (pkts/s)"
    ::= { perimetaGlobalStatsEntry 541 }

  globalStatRPG7B1TransCollisionRate OBJECT-TYPE
    SYNTAX       CounterBasedGauge64
    MAX-ACCESS   read-only
    STATUS       current
    DESCRIPTION  "RPG7 blade 1 transmission collisions per
                  second"
    ::= { perimetaGlobalStatsEntry 542 }

  globalStatRPG7B1RcvdLengthErrRate OBJECT-TYPE
    SYNTAX       CounterBasedGauge64
    MAX-ACCESS   read-only
    STATUS       current
    DESCRIPTION  "RPG7 blade 1 rcvd length errors
                  (errors/s)"
    ::= { perimetaGlobalStatsEntry 543 }

  globalStatRPG7B1RcvdOverrunErrRate OBJECT-TYPE
    SYNTAX       CounterBasedGauge64
    MAX-ACCESS   read-only
    STATUS       current
    DESCRIPTION  "RPG7 blade 1 rcvd overrun errors
                  (errors/s)"
    ::= { perimetaGlobalStatsEntry 544 }

  globalStatRPG7B1RcvdCRCErrRate OBJECT-TYPE
    SYNTAX       CounterBasedGauge64
    MAX-ACCESS   read-only
    STATUS       current
    DESCRIPTION  "RPG7 blade 1 rcvd CRC errors (errors/s)"
    ::= { perimetaGlobalStatsEntry 545 }

  globalStatRPG7B1RcvdFrameErrRate OBJECT-TYPE
    SYNTAX       CounterBasedGauge64
    MAX-ACCESS   read-only
    STATUS       current
    DESCRIPTION  "RPG7 blade 1 rcvd frame errors
                  (errors/s)"
    ::= { perimetaGlobalStatsEntry 546 }

  globalStatRPG7B1RcvdFifoFrameErrRate OBJECT-TYPE
    SYNTAX       CounterBasedGauge64
    MAX-ACCESS   read-only
    STATUS       current
    DESCRIPTION  "RPG7 blade 1 rcvd Fifo frame errors
                  (errors/s)"
    ::= { perimetaGlobalStatsEntry 547 }

  globalStatRPG7B1RcvdMissedFrameErrRate OBJECT-TYPE
    SYNTAX       CounterBasedGauge64
    MAX-ACCESS   read-only
    STATUS       current
    DESCRIPTION  "RPG7 blade 1 rcvd missed frame errors
                  (errors/s)"
    ::= { perimetaGlobalStatsEntry 548 }

  globalStatRPG7B1TransAbortErrRate OBJECT-TYPE
    SYNTAX       CounterBasedGauge64
    MAX-ACCESS   read-only
    STATUS       current
    DESCRIPTION  "RPG7 blade 1 transmission aborted errors
                  (errors/s)"
    ::= { perimetaGlobalStatsEntry 549 }

  globalStatRPG7B1TransCarrierErrRate OBJECT-TYPE
    SYNTAX       CounterBasedGauge64
    MAX-ACCESS   read-only
    STATUS       current
    DESCRIPTION  "RPG7 blade 1 transmission carrier errors
                  (errors/s)"
    ::= { perimetaGlobalStatsEntry 550 }

  globalStatRPG7B1TransFifoErrRate OBJECT-TYPE
    SYNTAX       CounterBasedGauge64
    MAX-ACCESS   read-only
    STATUS       current
    DESCRIPTION  "RPG7 blade 1 transmission Fifo errors
                  (errors/s)"
    ::= { perimetaGlobalStatsEntry 551 }

  globalStatRPG7B1TransHtbtErrRate OBJECT-TYPE
    SYNTAX       CounterBasedGauge64
    MAX-ACCESS   read-only
    STATUS       current
    DESCRIPTION  "RPG7 blade 1 transmission heartbeat
                  errors (errors/s)"
    ::= { perimetaGlobalStatsEntry 552 }

  globalStatRPG7B1TransWindowErrRate OBJECT-TYPE
    SYNTAX       CounterBasedGauge64
    MAX-ACCESS   read-only
    STATUS       current
    DESCRIPTION  "RPG7 blade 1 transmission window errors
                  (errors/s)"
    ::= { perimetaGlobalStatsEntry 553 }

  globalStatRPG8B1RcvdPacketRate OBJECT-TYPE
    SYNTAX       CounterBasedGauge64
    MAX-ACCESS   read-only
    STATUS       current
    DESCRIPTION  "RPG8 blade 1 pkts rcvd (pkts/s)"
    ::= { perimetaGlobalStatsEntry 554 }

  globalStatRPG8B1TransPacketRate OBJECT-TYPE
    SYNTAX       CounterBasedGauge64
    MAX-ACCESS   read-only
    STATUS       current
    DESCRIPTION  "RPG8 blade 1 pkts sent (pkts/s)"
    ::= { perimetaGlobalStatsEntry 555 }

  globalStatRPG8B1RcvdByteRate OBJECT-TYPE
    SYNTAX       CounterBasedGauge64
    MAX-ACCESS   read-only
    STATUS       current
    DESCRIPTION  "RPG8 blade 1 bytes rcvd (bytes/s)"
    ::= { perimetaGlobalStatsEntry 556 }

  globalStatRPG8B1TransByteRate OBJECT-TYPE
    SYNTAX       CounterBasedGauge64
    MAX-ACCESS   read-only
    STATUS       current
    DESCRIPTION  "RPG8 blade 1 bytes sent (bytes/s)"
    ::= { perimetaGlobalStatsEntry 557 }

  globalStatRPG8B1RcvdErrorRate OBJECT-TYPE
    SYNTAX       CounterBasedGauge64
    MAX-ACCESS   read-only
    STATUS       current
    DESCRIPTION  "RPG8 blade 1 receive errors (errors/s)"
    ::= { perimetaGlobalStatsEntry 558 }

  globalStatRPG8B1TransErrorRate OBJECT-TYPE
    SYNTAX       CounterBasedGauge64
    MAX-ACCESS   read-only
    STATUS       current
    DESCRIPTION  "RPG8 blade 1 transmission errors
                  (errors/s)"
    ::= { perimetaGlobalStatsEntry 559 }

  globalStatRPG8B1RcvdDropPacketRate OBJECT-TYPE
    SYNTAX       CounterBasedGauge64
    MAX-ACCESS   read-only
    STATUS       current
    DESCRIPTION  "RPG8 blade 1 rcvd pkts dropped (pkts/s)"
    ::= { perimetaGlobalStatsEntry 560 }

  globalStatRPG8B1TransDropPacketRate OBJECT-TYPE
    SYNTAX       CounterBasedGauge64
    MAX-ACCESS   read-only
    STATUS       current
    DESCRIPTION  "RPG8 blade 1 transmission pkts dropped
                  (pkts/s)"
    ::= { perimetaGlobalStatsEntry 561 }

  globalStatRPG8B1RcvdMulticastRate OBJECT-TYPE
    SYNTAX       CounterBasedGauge64
    MAX-ACCESS   read-only
    STATUS       current
    DESCRIPTION  "RPG8 blade 1 multicast pkts rcvd
                  (pkts/s)"
    ::= { perimetaGlobalStatsEntry 562 }

  globalStatRPG8B1TransCollisionRate OBJECT-TYPE
    SYNTAX       CounterBasedGauge64
    MAX-ACCESS   read-only
    STATUS       current
    DESCRIPTION  "RPG8 blade 1 transmission collisions per
                  second"
    ::= { perimetaGlobalStatsEntry 563 }

  globalStatRPG8B1RcvdLengthErrRate OBJECT-TYPE
    SYNTAX       CounterBasedGauge64
    MAX-ACCESS   read-only
    STATUS       current
    DESCRIPTION  "RPG8 blade 1 rcvd length errors
                  (errors/s)"
    ::= { perimetaGlobalStatsEntry 564 }

  globalStatRPG8B1RcvdOverrunErrRate OBJECT-TYPE
    SYNTAX       CounterBasedGauge64
    MAX-ACCESS   read-only
    STATUS       current
    DESCRIPTION  "RPG8 blade 1 rcvd overrun errors
                  (errors/s)"
    ::= { perimetaGlobalStatsEntry 565 }

  globalStatRPG8B1RcvdCRCErrRate OBJECT-TYPE
    SYNTAX       CounterBasedGauge64
    MAX-ACCESS   read-only
    STATUS       current
    DESCRIPTION  "RPG8 blade 1 rcvd CRC errors (errors/s)"
    ::= { perimetaGlobalStatsEntry 566 }

  globalStatRPG8B1RcvdFrameErrRate OBJECT-TYPE
    SYNTAX       CounterBasedGauge64
    MAX-ACCESS   read-only
    STATUS       current
    DESCRIPTION  "RPG8 blade 1 rcvd frame errors
                  (errors/s)"
    ::= { perimetaGlobalStatsEntry 567 }

  globalStatRPG8B1RcvdFifoFrameErrRate OBJECT-TYPE
    SYNTAX       CounterBasedGauge64
    MAX-ACCESS   read-only
    STATUS       current
    DESCRIPTION  "RPG8 blade 1 rcvd Fifo frame errors
                  (errors/s)"
    ::= { perimetaGlobalStatsEntry 568 }

  globalStatRPG8B1RcvdMissedFrameErrRate OBJECT-TYPE
    SYNTAX       CounterBasedGauge64
    MAX-ACCESS   read-only
    STATUS       current
    DESCRIPTION  "RPG8 blade 1 rcvd missed frame errors
                  (errors/s)"
    ::= { perimetaGlobalStatsEntry 569 }

  globalStatRPG8B1TransAbortErrRate OBJECT-TYPE
    SYNTAX       CounterBasedGauge64
    MAX-ACCESS   read-only
    STATUS       current
    DESCRIPTION  "RPG8 blade 1 transmission aborted errors
                  (errors/s)"
    ::= { perimetaGlobalStatsEntry 570 }

  globalStatRPG8B1TransCarrierErrRate OBJECT-TYPE
    SYNTAX       CounterBasedGauge64
    MAX-ACCESS   read-only
    STATUS       current
    DESCRIPTION  "RPG8 blade 1 transmission carrier errors
                  (errors/s)"
    ::= { perimetaGlobalStatsEntry 571 }

  globalStatRPG8B1TransFifoErrRate OBJECT-TYPE
    SYNTAX       CounterBasedGauge64
    MAX-ACCESS   read-only
    STATUS       current
    DESCRIPTION  "RPG8 blade 1 transmission Fifo errors
                  (errors/s)"
    ::= { perimetaGlobalStatsEntry 572 }

  globalStatRPG8B1TransHtbtErrRate OBJECT-TYPE
    SYNTAX       CounterBasedGauge64
    MAX-ACCESS   read-only
    STATUS       current
    DESCRIPTION  "RPG8 blade 1 transmission heartbeat
                  errors (errors/s)"
    ::= { perimetaGlobalStatsEntry 573 }

  globalStatRPG8B1TransWindowErrRate OBJECT-TYPE
    SYNTAX       CounterBasedGauge64
    MAX-ACCESS   read-only
    STATUS       current
    DESCRIPTION  "RPG8 blade 1 transmission window errors
                  (errors/s)"
    ::= { perimetaGlobalStatsEntry 574 }

  globalStatIBG1MB1RcvdPacketRate OBJECT-TYPE
    SYNTAX       CounterBasedGauge64
    MAX-ACCESS   read-only
    STATUS       current
    DESCRIPTION  "IBG1_M blade 1 pkts rcvd (pkts/s)"
    ::= { perimetaGlobalStatsEntry 575 }

  globalStatIBG1MB1TransPacketRate OBJECT-TYPE
    SYNTAX       CounterBasedGauge64
    MAX-ACCESS   read-only
    STATUS       current
    DESCRIPTION  "IBG1_M blade 1 pkts sent (pkts/s)"
    ::= { perimetaGlobalStatsEntry 576 }

  globalStatIBG1MB1RcvdByteRate OBJECT-TYPE
    SYNTAX       CounterBasedGauge64
    MAX-ACCESS   read-only
    STATUS       current
    DESCRIPTION  "IBG1_M blade 1 bytes rcvd (bytes/s)"
    ::= { perimetaGlobalStatsEntry 577 }

  globalStatIBG1MB1TransByteRate OBJECT-TYPE
    SYNTAX       CounterBasedGauge64
    MAX-ACCESS   read-only
    STATUS       current
    DESCRIPTION  "IBG1_M blade 1 bytes sent (bytes/s)"
    ::= { perimetaGlobalStatsEntry 578 }

  globalStatIBG1MB1RcvdErrorRate OBJECT-TYPE
    SYNTAX       CounterBasedGauge64
    MAX-ACCESS   read-only
    STATUS       current
    DESCRIPTION  "IBG1_M blade 1 receive errors (errors/s)"
    ::= { perimetaGlobalStatsEntry 579 }

  globalStatIBG1MB1TransErrorRate OBJECT-TYPE
    SYNTAX       CounterBasedGauge64
    MAX-ACCESS   read-only
    STATUS       current
    DESCRIPTION  "IBG1_M blade 1 transmission errors
                  (errors/s)"
    ::= { perimetaGlobalStatsEntry 580 }

  globalStatIBG1MB1RcvdDropPacketRate OBJECT-TYPE
    SYNTAX       CounterBasedGauge64
    MAX-ACCESS   read-only
    STATUS       current
    DESCRIPTION  "IBG1_M blade 1 rcvd pkts dropped
                  (pkts/s)"
    ::= { perimetaGlobalStatsEntry 581 }

  globalStatIBG1MB1TransDropPacketRate OBJECT-TYPE
    SYNTAX       CounterBasedGauge64
    MAX-ACCESS   read-only
    STATUS       current
    DESCRIPTION  "IBG1_M blade 1 transmission pkts dropped
                  (pkts/s)"
    ::= { perimetaGlobalStatsEntry 582 }

  globalStatIBG1MB1RcvdMulticastRate OBJECT-TYPE
    SYNTAX       CounterBasedGauge64
    MAX-ACCESS   read-only
    STATUS       current
    DESCRIPTION  "IBG1_M blade 1 multicast pkts rcvd
                  (pkts/s)"
    ::= { perimetaGlobalStatsEntry 583 }

  globalStatIBG1MB1TransCollisionRate OBJECT-TYPE
    SYNTAX       CounterBasedGauge64
    MAX-ACCESS   read-only
    STATUS       current
    DESCRIPTION  "IBG1_M blade 1 transmission collisions
                  per second"
    ::= { perimetaGlobalStatsEntry 584 }

  globalStatIBG1MB1RcvdLengthErrRate OBJECT-TYPE
    SYNTAX       CounterBasedGauge64
    MAX-ACCESS   read-only
    STATUS       current
    DESCRIPTION  "IBG1_M blade 1 rcvd length errors
                  (errors/s)"
    ::= { perimetaGlobalStatsEntry 585 }

  globalStatIBG1MB1RcvdOverrunErrRate OBJECT-TYPE
    SYNTAX       CounterBasedGauge64
    MAX-ACCESS   read-only
    STATUS       current
    DESCRIPTION  "IBG1_M blade 1 rcvd overrun errors
                  (errors/s)"
    ::= { perimetaGlobalStatsEntry 586 }

  globalStatIBG1MB1RcvdCRCErrRate OBJECT-TYPE
    SYNTAX       CounterBasedGauge64
    MAX-ACCESS   read-only
    STATUS       current
    DESCRIPTION  "IBG1_M blade 1 rcvd CRC errors
                  (errors/s)"
    ::= { perimetaGlobalStatsEntry 587 }

  globalStatIBG1MB1RcvdFrameErrRate OBJECT-TYPE
    SYNTAX       CounterBasedGauge64
    MAX-ACCESS   read-only
    STATUS       current
    DESCRIPTION  "IBG1_M blade 1 rcvd frame errors
                  (errors/s)"
    ::= { perimetaGlobalStatsEntry 588 }

  globalStatIBG1MB1RcvdFifoFrameErrRate OBJECT-TYPE
    SYNTAX       CounterBasedGauge64
    MAX-ACCESS   read-only
    STATUS       current
    DESCRIPTION  "IBG1_M blade 1 rcvd Fifo frame errors
                  (errors/s)"
    ::= { perimetaGlobalStatsEntry 589 }

  globalStatIBG1MB1RcvdMissedFrameErrRate OBJECT-TYPE
    SYNTAX       CounterBasedGauge64
    MAX-ACCESS   read-only
    STATUS       current
    DESCRIPTION  "IBG1_M blade 1 rcvd missed frame errors
                  (errors/s)"
    ::= { perimetaGlobalStatsEntry 590 }

  globalStatIBG1MB1TransAbortErrRate OBJECT-TYPE
    SYNTAX       CounterBasedGauge64
    MAX-ACCESS   read-only
    STATUS       current
    DESCRIPTION  "IBG1_M blade 1 transmission aborted
                  errors (errors/s)"
    ::= { perimetaGlobalStatsEntry 591 }

  globalStatIBG1MB1TransCarrierErrRate OBJECT-TYPE
    SYNTAX       CounterBasedGauge64
    MAX-ACCESS   read-only
    STATUS       current
    DESCRIPTION  "IBG1_M blade 1 transmission carrier
                  errors (errors/s)"
    ::= { perimetaGlobalStatsEntry 592 }

  globalStatIBG1MB1TransFifoErrRate OBJECT-TYPE
    SYNTAX       CounterBasedGauge64
    MAX-ACCESS   read-only
    STATUS       current
    DESCRIPTION  "IBG1_M blade 1 transmission Fifo errors
                  (errors/s)"
    ::= { perimetaGlobalStatsEntry 593 }

  globalStatIBG1MB1TransHtbtErrRate OBJECT-TYPE
    SYNTAX       CounterBasedGauge64
    MAX-ACCESS   read-only
    STATUS       current
    DESCRIPTION  "IBG1_M blade 1 transmission heartbeat
                  errors (errors/s)"
    ::= { perimetaGlobalStatsEntry 594 }

  globalStatIBG1MB1TransWindowErrRate OBJECT-TYPE
    SYNTAX       CounterBasedGauge64
    MAX-ACCESS   read-only
    STATUS       current
    DESCRIPTION  "IBG1_M blade 1 transmission window
                  errors (errors/s)"
    ::= { perimetaGlobalStatsEntry 595 }

  globalStatIBG2MB1RcvdPacketRate OBJECT-TYPE
    SYNTAX       CounterBasedGauge64
    MAX-ACCESS   read-only
    STATUS       current
    DESCRIPTION  "IBG2_M blade 1 pkts rcvd (pkts/s)"
    ::= { perimetaGlobalStatsEntry 596 }

  globalStatIBG2MB1TransPacketRate OBJECT-TYPE
    SYNTAX       CounterBasedGauge64
    MAX-ACCESS   read-only
    STATUS       current
    DESCRIPTION  "IBG2_M blade 1 pkts sent (pkts/s)"
    ::= { perimetaGlobalStatsEntry 597 }

  globalStatIBG2MB1RcvdByteRate OBJECT-TYPE
    SYNTAX       CounterBasedGauge64
    MAX-ACCESS   read-only
    STATUS       current
    DESCRIPTION  "IBG2_M blade 1 bytes rcvd (bytes/s)"
    ::= { perimetaGlobalStatsEntry 598 }

  globalStatIBG2MB1TransByteRate OBJECT-TYPE
    SYNTAX       CounterBasedGauge64
    MAX-ACCESS   read-only
    STATUS       current
    DESCRIPTION  "IBG2_M blade 1 bytes sent (bytes/s)"
    ::= { perimetaGlobalStatsEntry 599 }

  globalStatIBG2MB1RcvdErrorRate OBJECT-TYPE
    SYNTAX       CounterBasedGauge64
    MAX-ACCESS   read-only
    STATUS       current
    DESCRIPTION  "IBG2_M blade 1 receive errors (errors/s)"
    ::= { perimetaGlobalStatsEntry 600 }

  globalStatIBG2MB1TransErrorRate OBJECT-TYPE
    SYNTAX       CounterBasedGauge64
    MAX-ACCESS   read-only
    STATUS       current
    DESCRIPTION  "IBG2_M blade 1 transmission errors
                  (errors/s)"
    ::= { perimetaGlobalStatsEntry 601 }

  globalStatIBG2MB1RcvdDropPacketRate OBJECT-TYPE
    SYNTAX       CounterBasedGauge64
    MAX-ACCESS   read-only
    STATUS       current
    DESCRIPTION  "IBG2_M blade 1 rcvd pkts dropped
                  (pkts/s)"
    ::= { perimetaGlobalStatsEntry 602 }

  globalStatIBG2MB1TransDropPacketRate OBJECT-TYPE
    SYNTAX       CounterBasedGauge64
    MAX-ACCESS   read-only
    STATUS       current
    DESCRIPTION  "IBG2_M blade 1 transmission pkts dropped
                  (pkts/s)"
    ::= { perimetaGlobalStatsEntry 603 }

  globalStatIBG2MB1RcvdMulticastRate OBJECT-TYPE
    SYNTAX       CounterBasedGauge64
    MAX-ACCESS   read-only
    STATUS       current
    DESCRIPTION  "IBG2_M blade 1 multicast pkts rcvd
                  (pkts/s)"
    ::= { perimetaGlobalStatsEntry 604 }

  globalStatIBG2MB1TransCollisionRate OBJECT-TYPE
    SYNTAX       CounterBasedGauge64
    MAX-ACCESS   read-only
    STATUS       current
    DESCRIPTION  "IBG2_M blade 1 transmission collisions
                  per second"
    ::= { perimetaGlobalStatsEntry 605 }

  globalStatIBG2MB1RcvdLengthErrRate OBJECT-TYPE
    SYNTAX       CounterBasedGauge64
    MAX-ACCESS   read-only
    STATUS       current
    DESCRIPTION  "IBG2_M blade 1 rcvd length errors
                  (errors/s)"
    ::= { perimetaGlobalStatsEntry 606 }

  globalStatIBG2MB1RcvdOverrunErrRate OBJECT-TYPE
    SYNTAX       CounterBasedGauge64
    MAX-ACCESS   read-only
    STATUS       current
    DESCRIPTION  "IBG2_M blade 1 rcvd overrun errors
                  (errors/s)"
    ::= { perimetaGlobalStatsEntry 607 }

  globalStatIBG2MB1RcvdCRCErrRate OBJECT-TYPE
    SYNTAX       CounterBasedGauge64
    MAX-ACCESS   read-only
    STATUS       current
    DESCRIPTION  "IBG2_M blade 1 rcvd CRC errors
                  (errors/s)"
    ::= { perimetaGlobalStatsEntry 608 }

  globalStatIBG2MB1RcvdFrameErrRate OBJECT-TYPE
    SYNTAX       CounterBasedGauge64
    MAX-ACCESS   read-only
    STATUS       current
    DESCRIPTION  "IBG2_M blade 1 rcvd frame errors
                  (errors/s)"
    ::= { perimetaGlobalStatsEntry 609 }

  globalStatIBG2MB1RcvdFifoFrameErrRate OBJECT-TYPE
    SYNTAX       CounterBasedGauge64
    MAX-ACCESS   read-only
    STATUS       current
    DESCRIPTION  "IBG2_M blade 1 rcvd Fifo frame errors
                  (errors/s)"
    ::= { perimetaGlobalStatsEntry 610 }

  globalStatIBG2MB1RcvdMissedFrameErrRate OBJECT-TYPE
    SYNTAX       CounterBasedGauge64
    MAX-ACCESS   read-only
    STATUS       current
    DESCRIPTION  "IBG2_M blade 1 rcvd missed frame errors
                  (errors/s)"
    ::= { perimetaGlobalStatsEntry 611 }

  globalStatIBG2MB1TransAbortErrRate OBJECT-TYPE
    SYNTAX       CounterBasedGauge64
    MAX-ACCESS   read-only
    STATUS       current
    DESCRIPTION  "IBG2_M blade 1 transmission aborted
                  errors (errors/s)"
    ::= { perimetaGlobalStatsEntry 612 }

  globalStatIBG2MB1TransCarrierErrRate OBJECT-TYPE
    SYNTAX       CounterBasedGauge64
    MAX-ACCESS   read-only
    STATUS       current
    DESCRIPTION  "IBG2_M blade 1 transmission carrier
                  errors (errors/s)"
    ::= { perimetaGlobalStatsEntry 613 }

  globalStatIBG2MB1TransFifoErrRate OBJECT-TYPE
    SYNTAX       CounterBasedGauge64
    MAX-ACCESS   read-only
    STATUS       current
    DESCRIPTION  "IBG2_M blade 1 transmission Fifo errors
                  (errors/s)"
    ::= { perimetaGlobalStatsEntry 614 }

  globalStatIBG2MB1TransHtbtErrRate OBJECT-TYPE
    SYNTAX       CounterBasedGauge64
    MAX-ACCESS   read-only
    STATUS       current
    DESCRIPTION  "IBG2_M blade 1 transmission heartbeat
                  errors (errors/s)"
    ::= { perimetaGlobalStatsEntry 615 }

  globalStatIBG2MB1TransWindowErrRate OBJECT-TYPE
    SYNTAX       CounterBasedGauge64
    MAX-ACCESS   read-only
    STATUS       current
    DESCRIPTION  "IBG2_M blade 1 transmission window
                  errors (errors/s)"
    ::= { perimetaGlobalStatsEntry 616 }

  globalStatIBG1B1RcvdPacketRate OBJECT-TYPE
    SYNTAX       CounterBasedGauge64
    MAX-ACCESS   read-only
    STATUS       current
    DESCRIPTION  "IBG1 blade 1 pkts rcvd (pkts/s)"
    ::= { perimetaGlobalStatsEntry 617 }

  globalStatIBG1B1TransPacketRate OBJECT-TYPE
    SYNTAX       CounterBasedGauge64
    MAX-ACCESS   read-only
    STATUS       current
    DESCRIPTION  "IBG1 blade 1 pkts sent (pkts/s)"
    ::= { perimetaGlobalStatsEntry 618 }

  globalStatIBG1B1RcvdByteRate OBJECT-TYPE
    SYNTAX       CounterBasedGauge64
    MAX-ACCESS   read-only
    STATUS       current
    DESCRIPTION  "IBG1 blade 1 bytes rcvd (bytes/s)"
    ::= { perimetaGlobalStatsEntry 619 }

  globalStatIBG1B1TransByteRate OBJECT-TYPE
    SYNTAX       CounterBasedGauge64
    MAX-ACCESS   read-only
    STATUS       current
    DESCRIPTION  "IBG1 blade 1 bytes sent (bytes/s)"
    ::= { perimetaGlobalStatsEntry 620 }

  globalStatIBG1B1RcvdErrorRate OBJECT-TYPE
    SYNTAX       CounterBasedGauge64
    MAX-ACCESS   read-only
    STATUS       current
    DESCRIPTION  "IBG1 blade 1 receive errors (errors/s)"
    ::= { perimetaGlobalStatsEntry 621 }

  globalStatIBG1B1TransErrorRate OBJECT-TYPE
    SYNTAX       CounterBasedGauge64
    MAX-ACCESS   read-only
    STATUS       current
    DESCRIPTION  "IBG1 blade 1 transmission errors
                  (errors/s)"
    ::= { perimetaGlobalStatsEntry 622 }

  globalStatIBG1B1RcvdDropPacketRate OBJECT-TYPE
    SYNTAX       CounterBasedGauge64
    MAX-ACCESS   read-only
    STATUS       current
    DESCRIPTION  "IBG1 blade 1 rcvd pkts dropped (pkts/s)"
    ::= { perimetaGlobalStatsEntry 623 }

  globalStatIBG1B1TransDropPacketRate OBJECT-TYPE
    SYNTAX       CounterBasedGauge64
    MAX-ACCESS   read-only
    STATUS       current
    DESCRIPTION  "IBG1 blade 1 transmission pkts dropped
                  (pkts/s)"
    ::= { perimetaGlobalStatsEntry 624 }

  globalStatIBG1B1RcvdMulticastRate OBJECT-TYPE
    SYNTAX       CounterBasedGauge64
    MAX-ACCESS   read-only
    STATUS       current
    DESCRIPTION  "IBG1 blade 1 multicast pkts rcvd
                  (pkts/s)"
    ::= { perimetaGlobalStatsEntry 625 }

  globalStatIBG1B1TransCollisionRate OBJECT-TYPE
    SYNTAX       CounterBasedGauge64
    MAX-ACCESS   read-only
    STATUS       current
    DESCRIPTION  "IBG1 blade 1 transmission collisions per
                  second"
    ::= { perimetaGlobalStatsEntry 626 }

  globalStatIBG1B1RcvdLengthErrRate OBJECT-TYPE
    SYNTAX       CounterBasedGauge64
    MAX-ACCESS   read-only
    STATUS       current
    DESCRIPTION  "IBG1 blade 1 rcvd length errors
                  (errors/s)"
    ::= { perimetaGlobalStatsEntry 627 }

  globalStatIBG1B1RcvdOverrunErrRate OBJECT-TYPE
    SYNTAX       CounterBasedGauge64
    MAX-ACCESS   read-only
    STATUS       current
    DESCRIPTION  "IBG1 blade 1 rcvd overrun errors
                  (errors/s)"
    ::= { perimetaGlobalStatsEntry 628 }

  globalStatIBG1B1RcvdCRCErrRate OBJECT-TYPE
    SYNTAX       CounterBasedGauge64
    MAX-ACCESS   read-only
    STATUS       current
    DESCRIPTION  "IBG1 blade 1 rcvd CRC errors (errors/s)"
    ::= { perimetaGlobalStatsEntry 629 }

  globalStatIBG1B1RcvdFrameErrRate OBJECT-TYPE
    SYNTAX       CounterBasedGauge64
    MAX-ACCESS   read-only
    STATUS       current
    DESCRIPTION  "IBG1 blade 1 rcvd frame errors
                  (errors/s)"
    ::= { perimetaGlobalStatsEntry 630 }

  globalStatIBG1B1RcvdFifoFrameErrRate OBJECT-TYPE
    SYNTAX       CounterBasedGauge64
    MAX-ACCESS   read-only
    STATUS       current
    DESCRIPTION  "IBG1 blade 1 rcvd Fifo frame errors
                  (errors/s)"
    ::= { perimetaGlobalStatsEntry 631 }

  globalStatIBG1B1RcvdMissedFrameErrRate OBJECT-TYPE
    SYNTAX       CounterBasedGauge64
    MAX-ACCESS   read-only
    STATUS       current
    DESCRIPTION  "IBG1 blade 1 rcvd missed frame errors
                  (errors/s)"
    ::= { perimetaGlobalStatsEntry 632 }

  globalStatIBG1B1TransAbortErrRate OBJECT-TYPE
    SYNTAX       CounterBasedGauge64
    MAX-ACCESS   read-only
    STATUS       current
    DESCRIPTION  "IBG1 blade 1 transmission aborted errors
                  (errors/s)"
    ::= { perimetaGlobalStatsEntry 633 }

  globalStatIBG1B1TransCarrierErrRate OBJECT-TYPE
    SYNTAX       CounterBasedGauge64
    MAX-ACCESS   read-only
    STATUS       current
    DESCRIPTION  "IBG1 blade 1 transmission carrier errors
                  (errors/s)"
    ::= { perimetaGlobalStatsEntry 634 }

  globalStatIBG1B1TransFifoErrRate OBJECT-TYPE
    SYNTAX       CounterBasedGauge64
    MAX-ACCESS   read-only
    STATUS       current
    DESCRIPTION  "IBG1 blade 1 transmission Fifo errors
                  (errors/s)"
    ::= { perimetaGlobalStatsEntry 635 }

  globalStatIBG1B1TransHtbtErrRate OBJECT-TYPE
    SYNTAX       CounterBasedGauge64
    MAX-ACCESS   read-only
    STATUS       current
    DESCRIPTION  "IBG1 blade 1 transmission heartbeat
                  errors (errors/s)"
    ::= { perimetaGlobalStatsEntry 636 }

  globalStatIBG1B1TransWindowErrRate OBJECT-TYPE
    SYNTAX       CounterBasedGauge64
    MAX-ACCESS   read-only
    STATUS       current
    DESCRIPTION  "IBG1 blade 1 transmission window errors
                  (errors/s)"
    ::= { perimetaGlobalStatsEntry 637 }

  globalStatIBG2B1RcvdPacketRate OBJECT-TYPE
    SYNTAX       CounterBasedGauge64
    MAX-ACCESS   read-only
    STATUS       current
    DESCRIPTION  "IBG2 blade 1 pkts rcvd (pkts/s)"
    ::= { perimetaGlobalStatsEntry 638 }

  globalStatIBG2B1TransPacketRate OBJECT-TYPE
    SYNTAX       CounterBasedGauge64
    MAX-ACCESS   read-only
    STATUS       current
    DESCRIPTION  "IBG2 blade 1 pkts sent (pkts/s)"
    ::= { perimetaGlobalStatsEntry 639 }

  globalStatIBG2B1RcvdByteRate OBJECT-TYPE
    SYNTAX       CounterBasedGauge64
    MAX-ACCESS   read-only
    STATUS       current
    DESCRIPTION  "IBG2 blade 1 bytes rcvd (bytes/s)"
    ::= { perimetaGlobalStatsEntry 640 }

  globalStatIBG2B1TransByteRate OBJECT-TYPE
    SYNTAX       CounterBasedGauge64
    MAX-ACCESS   read-only
    STATUS       current
    DESCRIPTION  "IBG2 blade 1 bytes sent (bytes/s)"
    ::= { perimetaGlobalStatsEntry 641 }

  globalStatIBG2B1RcvdErrorRate OBJECT-TYPE
    SYNTAX       CounterBasedGauge64
    MAX-ACCESS   read-only
    STATUS       current
    DESCRIPTION  "IBG2 blade 1 receive errors (errors/s)"
    ::= { perimetaGlobalStatsEntry 642 }

  globalStatIBG2B1TransErrorRate OBJECT-TYPE
    SYNTAX       CounterBasedGauge64
    MAX-ACCESS   read-only
    STATUS       current
    DESCRIPTION  "IBG2 blade 1 transmission errors
                  (errors/s)"
    ::= { perimetaGlobalStatsEntry 643 }

  globalStatIBG2B1RcvdDropPacketRate OBJECT-TYPE
    SYNTAX       CounterBasedGauge64
    MAX-ACCESS   read-only
    STATUS       current
    DESCRIPTION  "IBG2 blade 1 rcvd pkts dropped (pkts/s)"
    ::= { perimetaGlobalStatsEntry 644 }

  globalStatIBG2B1TransDropPacketRate OBJECT-TYPE
    SYNTAX       CounterBasedGauge64
    MAX-ACCESS   read-only
    STATUS       current
    DESCRIPTION  "IBG2 blade 1 transmission pkts dropped
                  (pkts/s)"
    ::= { perimetaGlobalStatsEntry 645 }

  globalStatIBG2B1RcvdMulticastRate OBJECT-TYPE
    SYNTAX       CounterBasedGauge64
    MAX-ACCESS   read-only
    STATUS       current
    DESCRIPTION  "IBG2 blade 1 multicast pkts rcvd
                  (pkts/s)"
    ::= { perimetaGlobalStatsEntry 646 }

  globalStatIBG2B1TransCollisionRate OBJECT-TYPE
    SYNTAX       CounterBasedGauge64
    MAX-ACCESS   read-only
    STATUS       current
    DESCRIPTION  "IBG2 blade 1 transmission collisions per
                  second"
    ::= { perimetaGlobalStatsEntry 647 }

  globalStatIBG2B1RcvdLengthErrRate OBJECT-TYPE
    SYNTAX       CounterBasedGauge64
    MAX-ACCESS   read-only
    STATUS       current
    DESCRIPTION  "IBG2 blade 1 rcvd length errors
                  (errors/s)"
    ::= { perimetaGlobalStatsEntry 648 }

  globalStatIBG2B1RcvdOverrunErrRate OBJECT-TYPE
    SYNTAX       CounterBasedGauge64
    MAX-ACCESS   read-only
    STATUS       current
    DESCRIPTION  "IBG2 blade 1 rcvd overrun errors
                  (errors/s)"
    ::= { perimetaGlobalStatsEntry 649 }

  globalStatIBG2B1RcvdCRCErrRate OBJECT-TYPE
    SYNTAX       CounterBasedGauge64
    MAX-ACCESS   read-only
    STATUS       current
    DESCRIPTION  "IBG2 blade 1 rcvd CRC errors (errors/s)"
    ::= { perimetaGlobalStatsEntry 650 }

  globalStatIBG2B1RcvdFrameErrRate OBJECT-TYPE
    SYNTAX       CounterBasedGauge64
    MAX-ACCESS   read-only
    STATUS       current
    DESCRIPTION  "IBG2 blade 1 rcvd frame errors
                  (errors/s)"
    ::= { perimetaGlobalStatsEntry 651 }

  globalStatIBG2B1RcvdFifoFrameErrRate OBJECT-TYPE
    SYNTAX       CounterBasedGauge64
    MAX-ACCESS   read-only
    STATUS       current
    DESCRIPTION  "IBG2 blade 1 rcvd Fifo frame errors
                  (errors/s)"
    ::= { perimetaGlobalStatsEntry 652 }

  globalStatIBG2B1RcvdMissedFrameErrRate OBJECT-TYPE
    SYNTAX       CounterBasedGauge64
    MAX-ACCESS   read-only
    STATUS       current
    DESCRIPTION  "IBG2 blade 1 rcvd missed frame errors
                  (errors/s)"
    ::= { perimetaGlobalStatsEntry 653 }

  globalStatIBG2B1TransAbortErrRate OBJECT-TYPE
    SYNTAX       CounterBasedGauge64
    MAX-ACCESS   read-only
    STATUS       current
    DESCRIPTION  "IBG2 blade 1 transmission aborted errors
                  (errors/s)"
    ::= { perimetaGlobalStatsEntry 654 }

  globalStatIBG2B1TransCarrierErrRate OBJECT-TYPE
    SYNTAX       CounterBasedGauge64
    MAX-ACCESS   read-only
    STATUS       current
    DESCRIPTION  "IBG2 blade 1 transmission carrier errors
                  (errors/s)"
    ::= { perimetaGlobalStatsEntry 655 }

  globalStatIBG2B1TransFifoErrRate OBJECT-TYPE
    SYNTAX       CounterBasedGauge64
    MAX-ACCESS   read-only
    STATUS       current
    DESCRIPTION  "IBG2 blade 1 transmission Fifo errors
                  (errors/s)"
    ::= { perimetaGlobalStatsEntry 656 }

  globalStatIBG2B1TransHtbtErrRate OBJECT-TYPE
    SYNTAX       CounterBasedGauge64
    MAX-ACCESS   read-only
    STATUS       current
    DESCRIPTION  "IBG2 blade 1 transmission heartbeat
                  errors (errors/s)"
    ::= { perimetaGlobalStatsEntry 657 }

  globalStatIBG2B1TransWindowErrRate OBJECT-TYPE
    SYNTAX       CounterBasedGauge64
    MAX-ACCESS   read-only
    STATUS       current
    DESCRIPTION  "IBG2 blade 1 transmission window errors
                  (errors/s)"
    ::= { perimetaGlobalStatsEntry 658 }

  globalStatIPG1B1RcvdPacketRate OBJECT-TYPE
    SYNTAX       CounterBasedGauge64
    MAX-ACCESS   read-only
    STATUS       current
    DESCRIPTION  "IPG1 blade 1 pkts rcvd (pkts/s)"
    ::= { perimetaGlobalStatsEntry 659 }

  globalStatIPG1B1TransPacketRate OBJECT-TYPE
    SYNTAX       CounterBasedGauge64
    MAX-ACCESS   read-only
    STATUS       current
    DESCRIPTION  "IPG1 blade 1 pkts sent (pkts/s)"
    ::= { perimetaGlobalStatsEntry 660 }

  globalStatIPG1B1RcvdByteRate OBJECT-TYPE
    SYNTAX       CounterBasedGauge64
    MAX-ACCESS   read-only
    STATUS       current
    DESCRIPTION  "IPG1 blade 1 bytes rcvd (bytes/s)"
    ::= { perimetaGlobalStatsEntry 661 }

  globalStatIPG1B1TransByteRate OBJECT-TYPE
    SYNTAX       CounterBasedGauge64
    MAX-ACCESS   read-only
    STATUS       current
    DESCRIPTION  "IPG1 blade 1 bytes sent (bytes/s)"
    ::= { perimetaGlobalStatsEntry 662 }

  globalStatIPG1B1RcvdErrorRate OBJECT-TYPE
    SYNTAX       CounterBasedGauge64
    MAX-ACCESS   read-only
    STATUS       current
    DESCRIPTION  "IPG1 blade 1 receive errors (errors/s)"
    ::= { perimetaGlobalStatsEntry 663 }

  globalStatIPG1B1TransErrorRate OBJECT-TYPE
    SYNTAX       CounterBasedGauge64
    MAX-ACCESS   read-only
    STATUS       current
    DESCRIPTION  "IPG1 blade 1 transmission errors
                  (errors/s)"
    ::= { perimetaGlobalStatsEntry 664 }

  globalStatIPG1B1RcvdDropPacketRate OBJECT-TYPE
    SYNTAX       CounterBasedGauge64
    MAX-ACCESS   read-only
    STATUS       current
    DESCRIPTION  "IPG1 blade 1 rcvd pkts dropped (pkts/s)"
    ::= { perimetaGlobalStatsEntry 665 }

  globalStatIPG1B1TransDropPacketRate OBJECT-TYPE
    SYNTAX       CounterBasedGauge64
    MAX-ACCESS   read-only
    STATUS       current
    DESCRIPTION  "IPG1 blade 1 transmission pkts dropped
                  (pkts/s)"
    ::= { perimetaGlobalStatsEntry 666 }

  globalStatIPG1B1RcvdMulticastRate OBJECT-TYPE
    SYNTAX       CounterBasedGauge64
    MAX-ACCESS   read-only
    STATUS       current
    DESCRIPTION  "IPG1 blade 1 multicast pkts rcvd
                  (pkts/s)"
    ::= { perimetaGlobalStatsEntry 667 }

  globalStatIPG1B1TransCollisionRate OBJECT-TYPE
    SYNTAX       CounterBasedGauge64
    MAX-ACCESS   read-only
    STATUS       current
    DESCRIPTION  "IPG1 blade 1 transmission collisions per
                  second"
    ::= { perimetaGlobalStatsEntry 668 }

  globalStatIPG1B1RcvdLengthErrRate OBJECT-TYPE
    SYNTAX       CounterBasedGauge64
    MAX-ACCESS   read-only
    STATUS       current
    DESCRIPTION  "IPG1 blade 1 rcvd length errors
                  (errors/s)"
    ::= { perimetaGlobalStatsEntry 669 }

  globalStatIPG1B1RcvdOverrunErrRate OBJECT-TYPE
    SYNTAX       CounterBasedGauge64
    MAX-ACCESS   read-only
    STATUS       current
    DESCRIPTION  "IPG1 blade 1 rcvd overrun errors
                  (errors/s)"
    ::= { perimetaGlobalStatsEntry 670 }

  globalStatIPG1B1RcvdCRCErrRate OBJECT-TYPE
    SYNTAX       CounterBasedGauge64
    MAX-ACCESS   read-only
    STATUS       current
    DESCRIPTION  "IPG1 blade 1 rcvd CRC errors (errors/s)"
    ::= { perimetaGlobalStatsEntry 671 }

  globalStatIPG1B1RcvdFrameErrRate OBJECT-TYPE
    SYNTAX       CounterBasedGauge64
    MAX-ACCESS   read-only
    STATUS       current
    DESCRIPTION  "IPG1 blade 1 rcvd frame errors
                  (errors/s)"
    ::= { perimetaGlobalStatsEntry 672 }

  globalStatIPG1B1RcvdFifoFrameErrRate OBJECT-TYPE
    SYNTAX       CounterBasedGauge64
    MAX-ACCESS   read-only
    STATUS       current
    DESCRIPTION  "IPG1 blade 1 rcvd Fifo frame errors
                  (errors/s)"
    ::= { perimetaGlobalStatsEntry 673 }

  globalStatIPG1B1RcvdMissedFrameErrRate OBJECT-TYPE
    SYNTAX       CounterBasedGauge64
    MAX-ACCESS   read-only
    STATUS       current
    DESCRIPTION  "IPG1 blade 1 rcvd missed frame errors
                  (errors/s)"
    ::= { perimetaGlobalStatsEntry 674 }

  globalStatIPG1B1TransAbortErrRate OBJECT-TYPE
    SYNTAX       CounterBasedGauge64
    MAX-ACCESS   read-only
    STATUS       current
    DESCRIPTION  "IPG1 blade 1 transmission aborted errors
                  (errors/s)"
    ::= { perimetaGlobalStatsEntry 675 }

  globalStatIPG1B1TransCarrierErrRate OBJECT-TYPE
    SYNTAX       CounterBasedGauge64
    MAX-ACCESS   read-only
    STATUS       current
    DESCRIPTION  "IPG1 blade 1 transmission carrier errors
                  (errors/s)"
    ::= { perimetaGlobalStatsEntry 676 }

  globalStatIPG1B1TransFifoErrRate OBJECT-TYPE
    SYNTAX       CounterBasedGauge64
    MAX-ACCESS   read-only
    STATUS       current
    DESCRIPTION  "IPG1 blade 1 transmission Fifo errors
                  (errors/s)"
    ::= { perimetaGlobalStatsEntry 677 }

  globalStatIPG1B1TransHtbtErrRate OBJECT-TYPE
    SYNTAX       CounterBasedGauge64
    MAX-ACCESS   read-only
    STATUS       current
    DESCRIPTION  "IPG1 blade 1 transmission heartbeat
                  errors (errors/s)"
    ::= { perimetaGlobalStatsEntry 678 }

  globalStatIPG1B1TransWindowErrRate OBJECT-TYPE
    SYNTAX       CounterBasedGauge64
    MAX-ACCESS   read-only
    STATUS       current
    DESCRIPTION  "IPG1 blade 1 transmission window errors
                  (errors/s)"
    ::= { perimetaGlobalStatsEntry 679 }

  globalStatIFXG1B1RcvdPacketRate OBJECT-TYPE
    SYNTAX       CounterBasedGauge64
    MAX-ACCESS   read-only
    STATUS       current
    DESCRIPTION  "IFXG1 blade 1 pkts rcvd (pkts/s)"
    ::= { perimetaGlobalStatsEntry 680 }

  globalStatIFXG1B1TransPacketRate OBJECT-TYPE
    SYNTAX       CounterBasedGauge64
    MAX-ACCESS   read-only
    STATUS       current
    DESCRIPTION  "IFXG1 blade 1 pkts sent (pkts/s)"
    ::= { perimetaGlobalStatsEntry 681 }

  globalStatIFXG1B1RcvdByteRate OBJECT-TYPE
    SYNTAX       CounterBasedGauge64
    MAX-ACCESS   read-only
    STATUS       current
    DESCRIPTION  "IFXG1 blade 1 bytes rcvd (bytes/s)"
    ::= { perimetaGlobalStatsEntry 682 }

  globalStatIFXG1B1TransByteRate OBJECT-TYPE
    SYNTAX       CounterBasedGauge64
    MAX-ACCESS   read-only
    STATUS       current
    DESCRIPTION  "IFXG1 blade 1 bytes sent (bytes/s)"
    ::= { perimetaGlobalStatsEntry 683 }

  globalStatIFXG1B1RcvdErrorRate OBJECT-TYPE
    SYNTAX       CounterBasedGauge64
    MAX-ACCESS   read-only
    STATUS       current
    DESCRIPTION  "IFXG1 blade 1 receive errors (errors/s)"
    ::= { perimetaGlobalStatsEntry 684 }

  globalStatIFXG1B1TransErrorRate OBJECT-TYPE
    SYNTAX       CounterBasedGauge64
    MAX-ACCESS   read-only
    STATUS       current
    DESCRIPTION  "IFXG1 blade 1 transmission errors
                  (errors/s)"
    ::= { perimetaGlobalStatsEntry 685 }

  globalStatIFXG1B1RcvdDropPacketRate OBJECT-TYPE
    SYNTAX       CounterBasedGauge64
    MAX-ACCESS   read-only
    STATUS       current
    DESCRIPTION  "IFXG1 blade 1 rcvd pkts dropped (pkts/s)"
    ::= { perimetaGlobalStatsEntry 686 }

  globalStatIFXG1B1TransDropPacketRate OBJECT-TYPE
    SYNTAX       CounterBasedGauge64
    MAX-ACCESS   read-only
    STATUS       current
    DESCRIPTION  "IFXG1 blade 1 transmission pkts dropped
                  (pkts/s)"
    ::= { perimetaGlobalStatsEntry 687 }

  globalStatIFXG1B1RcvdMulticastRate OBJECT-TYPE
    SYNTAX       CounterBasedGauge64
    MAX-ACCESS   read-only
    STATUS       current
    DESCRIPTION  "IFXG1 blade 1 multicast pkts rcvd
                  (pkts/s)"
    ::= { perimetaGlobalStatsEntry 688 }

  globalStatIFXG1B1TransCollisionRate OBJECT-TYPE
    SYNTAX       CounterBasedGauge64
    MAX-ACCESS   read-only
    STATUS       current
    DESCRIPTION  "IFXG1 blade 1 transmission collisions
                  per second"
    ::= { perimetaGlobalStatsEntry 689 }

  globalStatIFXG1B1RcvdLengthErrRate OBJECT-TYPE
    SYNTAX       CounterBasedGauge64
    MAX-ACCESS   read-only
    STATUS       current
    DESCRIPTION  "IFXG1 blade 1 rcvd length errors
                  (errors/s)"
    ::= { perimetaGlobalStatsEntry 690 }

  globalStatIFXG1B1RcvdOverrunErrRate OBJECT-TYPE
    SYNTAX       CounterBasedGauge64
    MAX-ACCESS   read-only
    STATUS       current
    DESCRIPTION  "IFXG1 blade 1 rcvd overrun errors
                  (errors/s)"
    ::= { perimetaGlobalStatsEntry 691 }

  globalStatIFXG1B1RcvdCRCErrRate OBJECT-TYPE
    SYNTAX       CounterBasedGauge64
    MAX-ACCESS   read-only
    STATUS       current
    DESCRIPTION  "IFXG1 blade 1 rcvd CRC errors (errors/s)"
    ::= { perimetaGlobalStatsEntry 692 }

  globalStatIFXG1B1RcvdFrameErrRate OBJECT-TYPE
    SYNTAX       CounterBasedGauge64
    MAX-ACCESS   read-only
    STATUS       current
    DESCRIPTION  "IFXG1 blade 1 rcvd frame errors
                  (errors/s)"
    ::= { perimetaGlobalStatsEntry 693 }

  globalStatIFXG1B1RcvdFifoFrameErrRate OBJECT-TYPE
    SYNTAX       CounterBasedGauge64
    MAX-ACCESS   read-only
    STATUS       current
    DESCRIPTION  "IFXG1 blade 1 rcvd Fifo frame errors
                  (errors/s)"
    ::= { perimetaGlobalStatsEntry 694 }

  globalStatIFXG1B1RcvdMissedFrameErrRate OBJECT-TYPE
    SYNTAX       CounterBasedGauge64
    MAX-ACCESS   read-only
    STATUS       current
    DESCRIPTION  "IFXG1 blade 1 rcvd missed frame errors
                  (errors/s)"
    ::= { perimetaGlobalStatsEntry 695 }

  globalStatIFXG1B1TransAbortErrRate OBJECT-TYPE
    SYNTAX       CounterBasedGauge64
    MAX-ACCESS   read-only
    STATUS       current
    DESCRIPTION  "IFXG1 blade 1 transmission aborted
                  errors (errors/s)"
    ::= { perimetaGlobalStatsEntry 696 }

  globalStatIFXG1B1TransCarrierErrRate OBJECT-TYPE
    SYNTAX       CounterBasedGauge64
    MAX-ACCESS   read-only
    STATUS       current
    DESCRIPTION  "IFXG1 blade 1 transmission carrier
                  errors (errors/s)"
    ::= { perimetaGlobalStatsEntry 697 }

  globalStatIFXG1B1TransFifoErrRate OBJECT-TYPE
    SYNTAX       CounterBasedGauge64
    MAX-ACCESS   read-only
    STATUS       current
    DESCRIPTION  "IFXG1 blade 1 transmission Fifo errors
                  (errors/s)"
    ::= { perimetaGlobalStatsEntry 698 }

  globalStatIFXG1B1TransHtbtErrRate OBJECT-TYPE
    SYNTAX       CounterBasedGauge64
    MAX-ACCESS   read-only
    STATUS       current
    DESCRIPTION  "IFXG1 blade 1 transmission heartbeat
                  errors (errors/s)"
    ::= { perimetaGlobalStatsEntry 699 }

  globalStatIFXG1B1TransWindowErrRate OBJECT-TYPE
    SYNTAX       CounterBasedGauge64
    MAX-ACCESS   read-only
    STATUS       current
    DESCRIPTION  "IFXG1 blade 1 transmission window errors
                  (errors/s)"
    ::= { perimetaGlobalStatsEntry 700 }

  globalStatIFXG2B1RcvdPacketRate OBJECT-TYPE
    SYNTAX       CounterBasedGauge64
    MAX-ACCESS   read-only
    STATUS       current
    DESCRIPTION  "IFXG2 blade 1 pkts rcvd (pkts/s)"
    ::= { perimetaGlobalStatsEntry 701 }

  globalStatIFXG2B1TransPacketRate OBJECT-TYPE
    SYNTAX       CounterBasedGauge64
    MAX-ACCESS   read-only
    STATUS       current
    DESCRIPTION  "IFXG2 blade 1 pkts sent (pkts/s)"
    ::= { perimetaGlobalStatsEntry 702 }

  globalStatIFXG2B1RcvdByteRate OBJECT-TYPE
    SYNTAX       CounterBasedGauge64
    MAX-ACCESS   read-only
    STATUS       current
    DESCRIPTION  "IFXG2 blade 1 bytes rcvd (bytes/s)"
    ::= { perimetaGlobalStatsEntry 703 }

  globalStatIFXG2B1TransByteRate OBJECT-TYPE
    SYNTAX       CounterBasedGauge64
    MAX-ACCESS   read-only
    STATUS       current
    DESCRIPTION  "IFXG2 blade 1 bytes sent (bytes/s)"
    ::= { perimetaGlobalStatsEntry 704 }

  globalStatIFXG2B1RcvdErrorRate OBJECT-TYPE
    SYNTAX       CounterBasedGauge64
    MAX-ACCESS   read-only
    STATUS       current
    DESCRIPTION  "IFXG2 blade 1 receive errors (errors/s)"
    ::= { perimetaGlobalStatsEntry 705 }

  globalStatIFXG2B1TransErrorRate OBJECT-TYPE
    SYNTAX       CounterBasedGauge64
    MAX-ACCESS   read-only
    STATUS       current
    DESCRIPTION  "IFXG2 blade 1 transmission errors
                  (errors/s)"
    ::= { perimetaGlobalStatsEntry 706 }

  globalStatIFXG2B1RcvdDropPacketRate OBJECT-TYPE
    SYNTAX       CounterBasedGauge64
    MAX-ACCESS   read-only
    STATUS       current
    DESCRIPTION  "IFXG2 blade 1 rcvd pkts dropped (pkts/s)"
    ::= { perimetaGlobalStatsEntry 707 }

  globalStatIFXG2B1TransDropPacketRate OBJECT-TYPE
    SYNTAX       CounterBasedGauge64
    MAX-ACCESS   read-only
    STATUS       current
    DESCRIPTION  "IFXG2 blade 1 transmission pkts dropped
                  (pkts/s)"
    ::= { perimetaGlobalStatsEntry 708 }

  globalStatIFXG2B1RcvdMulticastRate OBJECT-TYPE
    SYNTAX       CounterBasedGauge64
    MAX-ACCESS   read-only
    STATUS       current
    DESCRIPTION  "IFXG2 blade 1 multicast pkts rcvd
                  (pkts/s)"
    ::= { perimetaGlobalStatsEntry 709 }

  globalStatIFXG2B1TransCollisionRate OBJECT-TYPE
    SYNTAX       CounterBasedGauge64
    MAX-ACCESS   read-only
    STATUS       current
    DESCRIPTION  "IFXG2 blade 1 transmission collisions
                  per second"
    ::= { perimetaGlobalStatsEntry 710 }

  globalStatIFXG2B1RcvdLengthErrRate OBJECT-TYPE
    SYNTAX       CounterBasedGauge64
    MAX-ACCESS   read-only
    STATUS       current
    DESCRIPTION  "IFXG2 blade 1 rcvd length errors
                  (errors/s)"
    ::= { perimetaGlobalStatsEntry 711 }

  globalStatIFXG2B1RcvdOverrunErrRate OBJECT-TYPE
    SYNTAX       CounterBasedGauge64
    MAX-ACCESS   read-only
    STATUS       current
    DESCRIPTION  "IFXG2 blade 1 rcvd overrun errors
                  (errors/s)"
    ::= { perimetaGlobalStatsEntry 712 }

  globalStatIFXG2B1RcvdCRCErrRate OBJECT-TYPE
    SYNTAX       CounterBasedGauge64
    MAX-ACCESS   read-only
    STATUS       current
    DESCRIPTION  "IFXG2 blade 1 rcvd CRC errors (errors/s)"
    ::= { perimetaGlobalStatsEntry 713 }

  globalStatIFXG2B1RcvdFrameErrRate OBJECT-TYPE
    SYNTAX       CounterBasedGauge64
    MAX-ACCESS   read-only
    STATUS       current
    DESCRIPTION  "IFXG2 blade 1 rcvd frame errors
                  (errors/s)"
    ::= { perimetaGlobalStatsEntry 714 }

  globalStatIFXG2B1RcvdFifoFrameErrRate OBJECT-TYPE
    SYNTAX       CounterBasedGauge64
    MAX-ACCESS   read-only
    STATUS       current
    DESCRIPTION  "IFXG2 blade 1 rcvd Fifo frame errors
                  (errors/s)"
    ::= { perimetaGlobalStatsEntry 715 }

  globalStatIFXG2B1RcvdMissedFrameErrRate OBJECT-TYPE
    SYNTAX       CounterBasedGauge64
    MAX-ACCESS   read-only
    STATUS       current
    DESCRIPTION  "IFXG2 blade 1 rcvd missed frame errors
                  (errors/s)"
    ::= { perimetaGlobalStatsEntry 716 }

  globalStatIFXG2B1TransAbortErrRate OBJECT-TYPE
    SYNTAX       CounterBasedGauge64
    MAX-ACCESS   read-only
    STATUS       current
    DESCRIPTION  "IFXG2 blade 1 transmission aborted
                  errors (errors/s)"
    ::= { perimetaGlobalStatsEntry 717 }

  globalStatIFXG2B1TransCarrierErrRate OBJECT-TYPE
    SYNTAX       CounterBasedGauge64
    MAX-ACCESS   read-only
    STATUS       current
    DESCRIPTION  "IFXG2 blade 1 transmission carrier
                  errors (errors/s)"
    ::= { perimetaGlobalStatsEntry 718 }

  globalStatIFXG2B1TransFifoErrRate OBJECT-TYPE
    SYNTAX       CounterBasedGauge64
    MAX-ACCESS   read-only
    STATUS       current
    DESCRIPTION  "IFXG2 blade 1 transmission Fifo errors
                  (errors/s)"
    ::= { perimetaGlobalStatsEntry 719 }

  globalStatIFXG2B1TransHtbtErrRate OBJECT-TYPE
    SYNTAX       CounterBasedGauge64
    MAX-ACCESS   read-only
    STATUS       current
    DESCRIPTION  "IFXG2 blade 1 transmission heartbeat
                  errors (errors/s)"
    ::= { perimetaGlobalStatsEntry 720 }

  globalStatIFXG2B1TransWindowErrRate OBJECT-TYPE
    SYNTAX       CounterBasedGauge64
    MAX-ACCESS   read-only
    STATUS       current
    DESCRIPTION  "IFXG2 blade 1 transmission window errors
                  (errors/s)"
    ::= { perimetaGlobalStatsEntry 721 }

  globalStatRPXG1B1RcvdPacketRate OBJECT-TYPE
    SYNTAX       CounterBasedGauge64
    MAX-ACCESS   read-only
    STATUS       current
    DESCRIPTION  "RPXG1 blade 1 pkts rcvd (pkts/s)"
    ::= { perimetaGlobalStatsEntry 722 }

  globalStatRPXG1B1TransPacketRate OBJECT-TYPE
    SYNTAX       CounterBasedGauge64
    MAX-ACCESS   read-only
    STATUS       current
    DESCRIPTION  "RPXG1 blade 1 pkts sent (pkts/s)"
    ::= { perimetaGlobalStatsEntry 723 }

  globalStatRPXG1B1RcvdByteRate OBJECT-TYPE
    SYNTAX       CounterBasedGauge64
    MAX-ACCESS   read-only
    STATUS       current
    DESCRIPTION  "RPXG1 blade 1 bytes rcvd (bytes/s)"
    ::= { perimetaGlobalStatsEntry 724 }

  globalStatRPXG1B1TransByteRate OBJECT-TYPE
    SYNTAX       CounterBasedGauge64
    MAX-ACCESS   read-only
    STATUS       current
    DESCRIPTION  "RPXG1 blade 1 bytes sent (bytes/s)"
    ::= { perimetaGlobalStatsEntry 725 }

  globalStatRPXG1B1RcvdErrorRate OBJECT-TYPE
    SYNTAX       CounterBasedGauge64
    MAX-ACCESS   read-only
    STATUS       current
    DESCRIPTION  "RPXG1 blade 1 receive errors (errors/s)"
    ::= { perimetaGlobalStatsEntry 726 }

  globalStatRPXG1B1TransErrorRate OBJECT-TYPE
    SYNTAX       CounterBasedGauge64
    MAX-ACCESS   read-only
    STATUS       current
    DESCRIPTION  "RPXG1 blade 1 transmission errors
                  (errors/s)"
    ::= { perimetaGlobalStatsEntry 727 }

  globalStatRPXG1B1RcvdDropPacketRate OBJECT-TYPE
    SYNTAX       CounterBasedGauge64
    MAX-ACCESS   read-only
    STATUS       current
    DESCRIPTION  "RPXG1 blade 1 rcvd pkts dropped (pkts/s)"
    ::= { perimetaGlobalStatsEntry 728 }

  globalStatRPXG1B1TransDropPacketRate OBJECT-TYPE
    SYNTAX       CounterBasedGauge64
    MAX-ACCESS   read-only
    STATUS       current
    DESCRIPTION  "RPXG1 blade 1 transmission pkts dropped
                  (pkts/s)"
    ::= { perimetaGlobalStatsEntry 729 }

  globalStatRPXG1B1RcvdMulticastRate OBJECT-TYPE
    SYNTAX       CounterBasedGauge64
    MAX-ACCESS   read-only
    STATUS       current
    DESCRIPTION  "RPXG1 blade 1 multicast pkts rcvd
                  (pkts/s)"
    ::= { perimetaGlobalStatsEntry 730 }

  globalStatRPXG1B1TransCollisionRate OBJECT-TYPE
    SYNTAX       CounterBasedGauge64
    MAX-ACCESS   read-only
    STATUS       current
    DESCRIPTION  "RPXG1 blade 1 transmission collisions
                  per second"
    ::= { perimetaGlobalStatsEntry 731 }

  globalStatRPXG1B1RcvdLengthErrRate OBJECT-TYPE
    SYNTAX       CounterBasedGauge64
    MAX-ACCESS   read-only
    STATUS       current
    DESCRIPTION  "RPXG1 blade 1 rcvd length errors
                  (errors/s)"
    ::= { perimetaGlobalStatsEntry 732 }

  globalStatRPXG1B1RcvdOverrunErrRate OBJECT-TYPE
    SYNTAX       CounterBasedGauge64
    MAX-ACCESS   read-only
    STATUS       current
    DESCRIPTION  "RPXG1 blade 1 rcvd overrun errors
                  (errors/s)"
    ::= { perimetaGlobalStatsEntry 733 }

  globalStatRPXG1B1RcvdCRCErrRate OBJECT-TYPE
    SYNTAX       CounterBasedGauge64
    MAX-ACCESS   read-only
    STATUS       current
    DESCRIPTION  "RPXG1 blade 1 rcvd CRC errors (errors/s)"
    ::= { perimetaGlobalStatsEntry 734 }

  globalStatRPXG1B1RcvdFrameErrRate OBJECT-TYPE
    SYNTAX       CounterBasedGauge64
    MAX-ACCESS   read-only
    STATUS       current
    DESCRIPTION  "RPXG1 blade 1 rcvd frame errors
                  (errors/s)"
    ::= { perimetaGlobalStatsEntry 735 }

  globalStatRPXG1B1RcvdFifoFrameErrRate OBJECT-TYPE
    SYNTAX       CounterBasedGauge64
    MAX-ACCESS   read-only
    STATUS       current
    DESCRIPTION  "RPXG1 blade 1 rcvd Fifo frame errors
                  (errors/s)"
    ::= { perimetaGlobalStatsEntry 736 }

  globalStatRPXG1B1RcvdMissedFrameErrRate OBJECT-TYPE
    SYNTAX       CounterBasedGauge64
    MAX-ACCESS   read-only
    STATUS       current
    DESCRIPTION  "RPXG1 blade 1 rcvd missed frame errors
                  (errors/s)"
    ::= { perimetaGlobalStatsEntry 737 }

  globalStatRPXG1B1TransAbortErrRate OBJECT-TYPE
    SYNTAX       CounterBasedGauge64
    MAX-ACCESS   read-only
    STATUS       current
    DESCRIPTION  "RPXG1 blade 1 transmission aborted
                  errors (errors/s)"
    ::= { perimetaGlobalStatsEntry 738 }

  globalStatRPXG1B1TransCarrierErrRate OBJECT-TYPE
    SYNTAX       CounterBasedGauge64
    MAX-ACCESS   read-only
    STATUS       current
    DESCRIPTION  "RPXG1 blade 1 transmission carrier
                  errors (errors/s)"
    ::= { perimetaGlobalStatsEntry 739 }

  globalStatRPXG1B1TransFifoErrRate OBJECT-TYPE
    SYNTAX       CounterBasedGauge64
    MAX-ACCESS   read-only
    STATUS       current
    DESCRIPTION  "RPXG1 blade 1 transmission Fifo errors
                  (errors/s)"
    ::= { perimetaGlobalStatsEntry 740 }

  globalStatRPXG1B1TransHtbtErrRate OBJECT-TYPE
    SYNTAX       CounterBasedGauge64
    MAX-ACCESS   read-only
    STATUS       current
    DESCRIPTION  "RPXG1 blade 1 transmission heartbeat
                  errors (errors/s)"
    ::= { perimetaGlobalStatsEntry 741 }

  globalStatRPXG1B1TransWindowErrRate OBJECT-TYPE
    SYNTAX       CounterBasedGauge64
    MAX-ACCESS   read-only
    STATUS       current
    DESCRIPTION  "RPXG1 blade 1 transmission window errors
                  (errors/s)"
    ::= { perimetaGlobalStatsEntry 742 }

  globalStatRPXG2B1RcvdPacketRate OBJECT-TYPE
    SYNTAX       CounterBasedGauge64
    MAX-ACCESS   read-only
    STATUS       current
    DESCRIPTION  "RPXG2 blade 1 pkts rcvd (pkts/s)"
    ::= { perimetaGlobalStatsEntry 743 }

  globalStatRPXG2B1TransPacketRate OBJECT-TYPE
    SYNTAX       CounterBasedGauge64
    MAX-ACCESS   read-only
    STATUS       current
    DESCRIPTION  "RPXG2 blade 1 pkts sent (pkts/s)"
    ::= { perimetaGlobalStatsEntry 744 }

  globalStatRPXG2B1RcvdByteRate OBJECT-TYPE
    SYNTAX       CounterBasedGauge64
    MAX-ACCESS   read-only
    STATUS       current
    DESCRIPTION  "RPXG2 blade 1 bytes rcvd (bytes/s)"
    ::= { perimetaGlobalStatsEntry 745 }

  globalStatRPXG2B1TransByteRate OBJECT-TYPE
    SYNTAX       CounterBasedGauge64
    MAX-ACCESS   read-only
    STATUS       current
    DESCRIPTION  "RPXG2 blade 1 bytes sent (bytes/s)"
    ::= { perimetaGlobalStatsEntry 746 }

  globalStatRPXG2B1RcvdErrorRate OBJECT-TYPE
    SYNTAX       CounterBasedGauge64
    MAX-ACCESS   read-only
    STATUS       current
    DESCRIPTION  "RPXG2 blade 1 receive errors (errors/s)"
    ::= { perimetaGlobalStatsEntry 747 }

  globalStatRPXG2B1TransErrorRate OBJECT-TYPE
    SYNTAX       CounterBasedGauge64
    MAX-ACCESS   read-only
    STATUS       current
    DESCRIPTION  "RPXG2 blade 1 transmission errors
                  (errors/s)"
    ::= { perimetaGlobalStatsEntry 748 }

  globalStatRPXG2B1RcvdDropPacketRate OBJECT-TYPE
    SYNTAX       CounterBasedGauge64
    MAX-ACCESS   read-only
    STATUS       current
    DESCRIPTION  "RPXG2 blade 1 rcvd pkts dropped (pkts/s)"
    ::= { perimetaGlobalStatsEntry 749 }

  globalStatRPXG2B1TransDropPacketRate OBJECT-TYPE
    SYNTAX       CounterBasedGauge64
    MAX-ACCESS   read-only
    STATUS       current
    DESCRIPTION  "RPXG2 blade 1 transmission pkts dropped
                  (pkts/s)"
    ::= { perimetaGlobalStatsEntry 750 }

  globalStatRPXG2B1RcvdMulticastRate OBJECT-TYPE
    SYNTAX       CounterBasedGauge64
    MAX-ACCESS   read-only
    STATUS       current
    DESCRIPTION  "RPXG2 blade 1 multicast pkts rcvd
                  (pkts/s)"
    ::= { perimetaGlobalStatsEntry 751 }

  globalStatRPXG2B1TransCollisionRate OBJECT-TYPE
    SYNTAX       CounterBasedGauge64
    MAX-ACCESS   read-only
    STATUS       current
    DESCRIPTION  "RPXG2 blade 1 transmission collisions
                  per second"
    ::= { perimetaGlobalStatsEntry 752 }

  globalStatRPXG2B1RcvdLengthErrRate OBJECT-TYPE
    SYNTAX       CounterBasedGauge64
    MAX-ACCESS   read-only
    STATUS       current
    DESCRIPTION  "RPXG2 blade 1 rcvd length errors
                  (errors/s)"
    ::= { perimetaGlobalStatsEntry 753 }

  globalStatRPXG2B1RcvdOverrunErrRate OBJECT-TYPE
    SYNTAX       CounterBasedGauge64
    MAX-ACCESS   read-only
    STATUS       current
    DESCRIPTION  "RPXG2 blade 1 rcvd overrun errors
                  (errors/s)"
    ::= { perimetaGlobalStatsEntry 754 }

  globalStatRPXG2B1RcvdCRCErrRate OBJECT-TYPE
    SYNTAX       CounterBasedGauge64
    MAX-ACCESS   read-only
    STATUS       current
    DESCRIPTION  "RPXG2 blade 1 rcvd CRC errors (errors/s)"
    ::= { perimetaGlobalStatsEntry 755 }

  globalStatRPXG2B1RcvdFrameErrRate OBJECT-TYPE
    SYNTAX       CounterBasedGauge64
    MAX-ACCESS   read-only
    STATUS       current
    DESCRIPTION  "RPXG2 blade 1 rcvd frame errors
                  (errors/s)"
    ::= { perimetaGlobalStatsEntry 756 }

  globalStatRPXG2B1RcvdFifoFrameErrRate OBJECT-TYPE
    SYNTAX       CounterBasedGauge64
    MAX-ACCESS   read-only
    STATUS       current
    DESCRIPTION  "RPXG2 blade 1 rcvd Fifo frame errors
                  (errors/s)"
    ::= { perimetaGlobalStatsEntry 757 }

  globalStatRPXG2B1RcvdMissedFrameErrRate OBJECT-TYPE
    SYNTAX       CounterBasedGauge64
    MAX-ACCESS   read-only
    STATUS       current
    DESCRIPTION  "RPXG2 blade 1 rcvd missed frame errors
                  (errors/s)"
    ::= { perimetaGlobalStatsEntry 758 }

  globalStatRPXG2B1TransAbortErrRate OBJECT-TYPE
    SYNTAX       CounterBasedGauge64
    MAX-ACCESS   read-only
    STATUS       current
    DESCRIPTION  "RPXG2 blade 1 transmission aborted
                  errors (errors/s)"
    ::= { perimetaGlobalStatsEntry 759 }

  globalStatRPXG2B1TransCarrierErrRate OBJECT-TYPE
    SYNTAX       CounterBasedGauge64
    MAX-ACCESS   read-only
    STATUS       current
    DESCRIPTION  "RPXG2 blade 1 transmission carrier
                  errors (errors/s)"
    ::= { perimetaGlobalStatsEntry 760 }

  globalStatRPXG2B1TransFifoErrRate OBJECT-TYPE
    SYNTAX       CounterBasedGauge64
    MAX-ACCESS   read-only
    STATUS       current
    DESCRIPTION  "RPXG2 blade 1 transmission Fifo errors
                  (errors/s)"
    ::= { perimetaGlobalStatsEntry 761 }

  globalStatRPXG2B1TransHtbtErrRate OBJECT-TYPE
    SYNTAX       CounterBasedGauge64
    MAX-ACCESS   read-only
    STATUS       current
    DESCRIPTION  "RPXG2 blade 1 transmission heartbeat
                  errors (errors/s)"
    ::= { perimetaGlobalStatsEntry 762 }

  globalStatRPXG2B1TransWindowErrRate OBJECT-TYPE
    SYNTAX       CounterBasedGauge64
    MAX-ACCESS   read-only
    STATUS       current
    DESCRIPTION  "RPXG2 blade 1 transmission window errors
                  (errors/s)"
    ::= { perimetaGlobalStatsEntry 763 }

  globalStatRPXG3B1RcvdPacketRate OBJECT-TYPE
    SYNTAX       CounterBasedGauge64
    MAX-ACCESS   read-only
    STATUS       current
    DESCRIPTION  "RPXG3 blade 1 pkts rcvd (pkts/s)"
    ::= { perimetaGlobalStatsEntry 764 }

  globalStatRPXG3B1TransPacketRate OBJECT-TYPE
    SYNTAX       CounterBasedGauge64
    MAX-ACCESS   read-only
    STATUS       current
    DESCRIPTION  "RPXG3 blade 1 pkts sent (pkts/s)"
    ::= { perimetaGlobalStatsEntry 765 }

  globalStatRPXG3B1RcvdByteRate OBJECT-TYPE
    SYNTAX       CounterBasedGauge64
    MAX-ACCESS   read-only
    STATUS       current
    DESCRIPTION  "RPXG3 blade 1 bytes rcvd (bytes/s)"
    ::= { perimetaGlobalStatsEntry 766 }

  globalStatRPXG3B1TransByteRate OBJECT-TYPE
    SYNTAX       CounterBasedGauge64
    MAX-ACCESS   read-only
    STATUS       current
    DESCRIPTION  "RPXG3 blade 1 bytes sent (bytes/s)"
    ::= { perimetaGlobalStatsEntry 767 }

  globalStatRPXG3B1RcvdErrorRate OBJECT-TYPE
    SYNTAX       CounterBasedGauge64
    MAX-ACCESS   read-only
    STATUS       current
    DESCRIPTION  "RPXG3 blade 1 receive errors (errors/s)"
    ::= { perimetaGlobalStatsEntry 768 }

  globalStatRPXG3B1TransErrorRate OBJECT-TYPE
    SYNTAX       CounterBasedGauge64
    MAX-ACCESS   read-only
    STATUS       current
    DESCRIPTION  "RPXG3 blade 1 transmission errors
                  (errors/s)"
    ::= { perimetaGlobalStatsEntry 769 }

  globalStatRPXG3B1RcvdDropPacketRate OBJECT-TYPE
    SYNTAX       CounterBasedGauge64
    MAX-ACCESS   read-only
    STATUS       current
    DESCRIPTION  "RPXG3 blade 1 rcvd pkts dropped (pkts/s)"
    ::= { perimetaGlobalStatsEntry 770 }

  globalStatRPXG3B1TransDropPacketRate OBJECT-TYPE
    SYNTAX       CounterBasedGauge64
    MAX-ACCESS   read-only
    STATUS       current
    DESCRIPTION  "RPXG3 blade 1 transmission pkts dropped
                  (pkts/s)"
    ::= { perimetaGlobalStatsEntry 771 }

  globalStatRPXG3B1RcvdMulticastRate OBJECT-TYPE
    SYNTAX       CounterBasedGauge64
    MAX-ACCESS   read-only
    STATUS       current
    DESCRIPTION  "RPXG3 blade 1 multicast pkts rcvd
                  (pkts/s)"
    ::= { perimetaGlobalStatsEntry 772 }

  globalStatRPXG3B1TransCollisionRate OBJECT-TYPE
    SYNTAX       CounterBasedGauge64
    MAX-ACCESS   read-only
    STATUS       current
    DESCRIPTION  "RPXG3 blade 1 transmission collisions
                  per second"
    ::= { perimetaGlobalStatsEntry 773 }

  globalStatRPXG3B1RcvdLengthErrRate OBJECT-TYPE
    SYNTAX       CounterBasedGauge64
    MAX-ACCESS   read-only
    STATUS       current
    DESCRIPTION  "RPXG3 blade 1 rcvd length errors
                  (errors/s)"
    ::= { perimetaGlobalStatsEntry 774 }

  globalStatRPXG3B1RcvdOverrunErrRate OBJECT-TYPE
    SYNTAX       CounterBasedGauge64
    MAX-ACCESS   read-only
    STATUS       current
    DESCRIPTION  "RPXG3 blade 1 rcvd overrun errors
                  (errors/s)"
    ::= { perimetaGlobalStatsEntry 775 }

  globalStatRPXG3B1RcvdCRCErrRate OBJECT-TYPE
    SYNTAX       CounterBasedGauge64
    MAX-ACCESS   read-only
    STATUS       current
    DESCRIPTION  "RPXG3 blade 1 rcvd CRC errors (errors/s)"
    ::= { perimetaGlobalStatsEntry 776 }

  globalStatRPXG3B1RcvdFrameErrRate OBJECT-TYPE
    SYNTAX       CounterBasedGauge64
    MAX-ACCESS   read-only
    STATUS       current
    DESCRIPTION  "RPXG3 blade 1 rcvd frame errors
                  (errors/s)"
    ::= { perimetaGlobalStatsEntry 777 }

  globalStatRPXG3B1RcvdFifoFrameErrRate OBJECT-TYPE
    SYNTAX       CounterBasedGauge64
    MAX-ACCESS   read-only
    STATUS       current
    DESCRIPTION  "RPXG3 blade 1 rcvd Fifo frame errors
                  (errors/s)"
    ::= { perimetaGlobalStatsEntry 778 }

  globalStatRPXG3B1RcvdMissedFrameErrRate OBJECT-TYPE
    SYNTAX       CounterBasedGauge64
    MAX-ACCESS   read-only
    STATUS       current
    DESCRIPTION  "RPXG3 blade 1 rcvd missed frame errors
                  (errors/s)"
    ::= { perimetaGlobalStatsEntry 779 }

  globalStatRPXG3B1TransAbortErrRate OBJECT-TYPE
    SYNTAX       CounterBasedGauge64
    MAX-ACCESS   read-only
    STATUS       current
    DESCRIPTION  "RPXG3 blade 1 transmission aborted
                  errors (errors/s)"
    ::= { perimetaGlobalStatsEntry 780 }

  globalStatRPXG3B1TransCarrierErrRate OBJECT-TYPE
    SYNTAX       CounterBasedGauge64
    MAX-ACCESS   read-only
    STATUS       current
    DESCRIPTION  "RPXG3 blade 1 transmission carrier
                  errors (errors/s)"
    ::= { perimetaGlobalStatsEntry 781 }

  globalStatRPXG3B1TransFifoErrRate OBJECT-TYPE
    SYNTAX       CounterBasedGauge64
    MAX-ACCESS   read-only
    STATUS       current
    DESCRIPTION  "RPXG3 blade 1 transmission Fifo errors
                  (errors/s)"
    ::= { perimetaGlobalStatsEntry 782 }

  globalStatRPXG3B1TransHtbtErrRate OBJECT-TYPE
    SYNTAX       CounterBasedGauge64
    MAX-ACCESS   read-only
    STATUS       current
    DESCRIPTION  "RPXG3 blade 1 transmission heartbeat
                  errors (errors/s)"
    ::= { perimetaGlobalStatsEntry 783 }

  globalStatRPXG3B1TransWindowErrRate OBJECT-TYPE
    SYNTAX       CounterBasedGauge64
    MAX-ACCESS   read-only
    STATUS       current
    DESCRIPTION  "RPXG3 blade 1 transmission window errors
                  (errors/s)"
    ::= { perimetaGlobalStatsEntry 784 }

  globalStatRPXG4B1RcvdPacketRate OBJECT-TYPE
    SYNTAX       CounterBasedGauge64
    MAX-ACCESS   read-only
    STATUS       current
    DESCRIPTION  "RPXG4 blade 1 pkts rcvd (pkts/s)"
    ::= { perimetaGlobalStatsEntry 785 }

  globalStatRPXG4B1TransPacketRate OBJECT-TYPE
    SYNTAX       CounterBasedGauge64
    MAX-ACCESS   read-only
    STATUS       current
    DESCRIPTION  "RPXG4 blade 1 pkts sent (pkts/s)"
    ::= { perimetaGlobalStatsEntry 786 }

  globalStatRPXG4B1RcvdByteRate OBJECT-TYPE
    SYNTAX       CounterBasedGauge64
    MAX-ACCESS   read-only
    STATUS       current
    DESCRIPTION  "RPXG4 blade 1 bytes rcvd (bytes/s)"
    ::= { perimetaGlobalStatsEntry 787 }

  globalStatRPXG4B1TransByteRate OBJECT-TYPE
    SYNTAX       CounterBasedGauge64
    MAX-ACCESS   read-only
    STATUS       current
    DESCRIPTION  "RPXG4 blade 1 bytes sent (bytes/s)"
    ::= { perimetaGlobalStatsEntry 788 }

  globalStatRPXG4B1RcvdErrorRate OBJECT-TYPE
    SYNTAX       CounterBasedGauge64
    MAX-ACCESS   read-only
    STATUS       current
    DESCRIPTION  "RPXG4 blade 1 receive errors (errors/s)"
    ::= { perimetaGlobalStatsEntry 789 }

  globalStatRPXG4B1TransErrorRate OBJECT-TYPE
    SYNTAX       CounterBasedGauge64
    MAX-ACCESS   read-only
    STATUS       current
    DESCRIPTION  "RPXG4 blade 1 transmission errors
                  (errors/s)"
    ::= { perimetaGlobalStatsEntry 790 }

  globalStatRPXG4B1RcvdDropPacketRate OBJECT-TYPE
    SYNTAX       CounterBasedGauge64
    MAX-ACCESS   read-only
    STATUS       current
    DESCRIPTION  "RPXG4 blade 1 rcvd pkts dropped (pkts/s)"
    ::= { perimetaGlobalStatsEntry 791 }

  globalStatRPXG4B1TransDropPacketRate OBJECT-TYPE
    SYNTAX       CounterBasedGauge64
    MAX-ACCESS   read-only
    STATUS       current
    DESCRIPTION  "RPXG4 blade 1 transmission pkts dropped
                  (pkts/s)"
    ::= { perimetaGlobalStatsEntry 792 }

  globalStatRPXG4B1RcvdMulticastRate OBJECT-TYPE
    SYNTAX       CounterBasedGauge64
    MAX-ACCESS   read-only
    STATUS       current
    DESCRIPTION  "RPXG4 blade 1 multicast pkts rcvd
                  (pkts/s)"
    ::= { perimetaGlobalStatsEntry 793 }

  globalStatRPXG4B1TransCollisionRate OBJECT-TYPE
    SYNTAX       CounterBasedGauge64
    MAX-ACCESS   read-only
    STATUS       current
    DESCRIPTION  "RPXG4 blade 1 transmission collisions
                  per second"
    ::= { perimetaGlobalStatsEntry 794 }

  globalStatRPXG4B1RcvdLengthErrRate OBJECT-TYPE
    SYNTAX       CounterBasedGauge64
    MAX-ACCESS   read-only
    STATUS       current
    DESCRIPTION  "RPXG4 blade 1 rcvd length errors
                  (errors/s)"
    ::= { perimetaGlobalStatsEntry 795 }

  globalStatRPXG4B1RcvdOverrunErrRate OBJECT-TYPE
    SYNTAX       CounterBasedGauge64
    MAX-ACCESS   read-only
    STATUS       current
    DESCRIPTION  "RPXG4 blade 1 rcvd overrun errors
                  (errors/s)"
    ::= { perimetaGlobalStatsEntry 796 }

  globalStatRPXG4B1RcvdCRCErrRate OBJECT-TYPE
    SYNTAX       CounterBasedGauge64
    MAX-ACCESS   read-only
    STATUS       current
    DESCRIPTION  "RPXG4 blade 1 rcvd CRC errors (errors/s)"
    ::= { perimetaGlobalStatsEntry 797 }

  globalStatRPXG4B1RcvdFrameErrRate OBJECT-TYPE
    SYNTAX       CounterBasedGauge64
    MAX-ACCESS   read-only
    STATUS       current
    DESCRIPTION  "RPXG4 blade 1 rcvd frame errors
                  (errors/s)"
    ::= { perimetaGlobalStatsEntry 798 }

  globalStatRPXG4B1RcvdFifoFrameErrRate OBJECT-TYPE
    SYNTAX       CounterBasedGauge64
    MAX-ACCESS   read-only
    STATUS       current
    DESCRIPTION  "RPXG4 blade 1 rcvd Fifo frame errors
                  (errors/s)"
    ::= { perimetaGlobalStatsEntry 799 }

  globalStatRPXG4B1RcvdMissedFrameErrRate OBJECT-TYPE
    SYNTAX       CounterBasedGauge64
    MAX-ACCESS   read-only
    STATUS       current
    DESCRIPTION  "RPXG4 blade 1 rcvd missed frame errors
                  (errors/s)"
    ::= { perimetaGlobalStatsEntry 800 }

  globalStatRPXG4B1TransAbortErrRate OBJECT-TYPE
    SYNTAX       CounterBasedGauge64
    MAX-ACCESS   read-only
    STATUS       current
    DESCRIPTION  "RPXG4 blade 1 transmission aborted
                  errors (errors/s)"
    ::= { perimetaGlobalStatsEntry 801 }

  globalStatRPXG4B1TransCarrierErrRate OBJECT-TYPE
    SYNTAX       CounterBasedGauge64
    MAX-ACCESS   read-only
    STATUS       current
    DESCRIPTION  "RPXG4 blade 1 transmission carrier
                  errors (errors/s)"
    ::= { perimetaGlobalStatsEntry 802 }

  globalStatRPXG4B1TransFifoErrRate OBJECT-TYPE
    SYNTAX       CounterBasedGauge64
    MAX-ACCESS   read-only
    STATUS       current
    DESCRIPTION  "RPXG4 blade 1 transmission Fifo errors
                  (errors/s)"
    ::= { perimetaGlobalStatsEntry 803 }

  globalStatRPXG4B1TransHtbtErrRate OBJECT-TYPE
    SYNTAX       CounterBasedGauge64
    MAX-ACCESS   read-only
    STATUS       current
    DESCRIPTION  "RPXG4 blade 1 transmission heartbeat
                  errors (errors/s)"
    ::= { perimetaGlobalStatsEntry 804 }

  globalStatRPXG4B1TransWindowErrRate OBJECT-TYPE
    SYNTAX       CounterBasedGauge64
    MAX-ACCESS   read-only
    STATUS       current
    DESCRIPTION  "RPXG4 blade 1 transmission window errors
                  (errors/s)"
    ::= { perimetaGlobalStatsEntry 805 }

  globalStatRPG1B2RcvdPacketRate OBJECT-TYPE
    SYNTAX       CounterBasedGauge64
    MAX-ACCESS   read-only
    STATUS       current
    DESCRIPTION  "RPG1 blade 2 pkts rcvd (pkts/s)"
    ::= { perimetaGlobalStatsEntry 806 }

  globalStatRPG1B2TransPacketRate OBJECT-TYPE
    SYNTAX       CounterBasedGauge64
    MAX-ACCESS   read-only
    STATUS       current
    DESCRIPTION  "RPG1 blade 2 pkts sent (pkts/s)"
    ::= { perimetaGlobalStatsEntry 807 }

  globalStatRPG1B2RcvdByteRate OBJECT-TYPE
    SYNTAX       CounterBasedGauge64
    MAX-ACCESS   read-only
    STATUS       current
    DESCRIPTION  "RPG1 blade 2 bytes rcvd (bytes/s)"
    ::= { perimetaGlobalStatsEntry 808 }

  globalStatRPG1B2TransByteRate OBJECT-TYPE
    SYNTAX       CounterBasedGauge64
    MAX-ACCESS   read-only
    STATUS       current
    DESCRIPTION  "RPG1 blade 2 bytes sent (bytes/s)"
    ::= { perimetaGlobalStatsEntry 809 }

  globalStatRPG1B2RcvdErrorRate OBJECT-TYPE
    SYNTAX       CounterBasedGauge64
    MAX-ACCESS   read-only
    STATUS       current
    DESCRIPTION  "RPG1 blade 2 receive errors (errors/s)"
    ::= { perimetaGlobalStatsEntry 810 }

  globalStatRPG1B2TransErrorRate OBJECT-TYPE
    SYNTAX       CounterBasedGauge64
    MAX-ACCESS   read-only
    STATUS       current
    DESCRIPTION  "RPG1 blade 2 transmission errors
                  (errors/s)"
    ::= { perimetaGlobalStatsEntry 811 }

  globalStatRPG1B2RcvdDropPacketRate OBJECT-TYPE
    SYNTAX       CounterBasedGauge64
    MAX-ACCESS   read-only
    STATUS       current
    DESCRIPTION  "RPG1 blade 2 rcvd pkts dropped (pkts/s)"
    ::= { perimetaGlobalStatsEntry 812 }

  globalStatRPG1B2TransDropPacketRate OBJECT-TYPE
    SYNTAX       CounterBasedGauge64
    MAX-ACCESS   read-only
    STATUS       current
    DESCRIPTION  "RPG1 blade 2 transmission pkts dropped
                  (pkts/s)"
    ::= { perimetaGlobalStatsEntry 813 }

  globalStatRPG1B2RcvdMulticastRate OBJECT-TYPE
    SYNTAX       CounterBasedGauge64
    MAX-ACCESS   read-only
    STATUS       current
    DESCRIPTION  "RPG1 blade 2 multicast pkts rcvd
                  (pkts/s)"
    ::= { perimetaGlobalStatsEntry 814 }

  globalStatRPG1B2TransCollisionRate OBJECT-TYPE
    SYNTAX       CounterBasedGauge64
    MAX-ACCESS   read-only
    STATUS       current
    DESCRIPTION  "RPG1 blade 2 transmission collisions per
                  second"
    ::= { perimetaGlobalStatsEntry 815 }

  globalStatRPG1B2RcvdLengthErrRate OBJECT-TYPE
    SYNTAX       CounterBasedGauge64
    MAX-ACCESS   read-only
    STATUS       current
    DESCRIPTION  "RPG1 blade 2 rcvd length errors
                  (errors/s)"
    ::= { perimetaGlobalStatsEntry 816 }

  globalStatRPG1B2RcvdOverrunErrRate OBJECT-TYPE
    SYNTAX       CounterBasedGauge64
    MAX-ACCESS   read-only
    STATUS       current
    DESCRIPTION  "RPG1 blade 2 rcvd overrun errors
                  (errors/s)"
    ::= { perimetaGlobalStatsEntry 817 }

  globalStatRPG1B2RcvdCRCErrRate OBJECT-TYPE
    SYNTAX       CounterBasedGauge64
    MAX-ACCESS   read-only
    STATUS       current
    DESCRIPTION  "RPG1 blade 2 rcvd CRC errors (errors/s)"
    ::= { perimetaGlobalStatsEntry 818 }

  globalStatRPG1B2RcvdFrameErrRate OBJECT-TYPE
    SYNTAX       CounterBasedGauge64
    MAX-ACCESS   read-only
    STATUS       current
    DESCRIPTION  "RPG1 blade 2 rcvd frame errors
                  (errors/s)"
    ::= { perimetaGlobalStatsEntry 819 }

  globalStatRPG1B2RcvdFifoFrameErrRate OBJECT-TYPE
    SYNTAX       CounterBasedGauge64
    MAX-ACCESS   read-only
    STATUS       current
    DESCRIPTION  "RPG1 blade 2 rcvd Fifo frame errors
                  (errors/s)"
    ::= { perimetaGlobalStatsEntry 820 }

  globalStatRPG1B2RcvdMissedFrameErrRate OBJECT-TYPE
    SYNTAX       CounterBasedGauge64
    MAX-ACCESS   read-only
    STATUS       current
    DESCRIPTION  "RPG1 blade 2 rcvd missed frame errors
                  (errors/s)"
    ::= { perimetaGlobalStatsEntry 821 }

  globalStatRPG1B2TransAbortErrRate OBJECT-TYPE
    SYNTAX       CounterBasedGauge64
    MAX-ACCESS   read-only
    STATUS       current
    DESCRIPTION  "RPG1 blade 2 transmission aborted errors
                  (errors/s)"
    ::= { perimetaGlobalStatsEntry 822 }

  globalStatRPG1B2TransCarrierErrRate OBJECT-TYPE
    SYNTAX       CounterBasedGauge64
    MAX-ACCESS   read-only
    STATUS       current
    DESCRIPTION  "RPG1 blade 2 transmission carrier errors
                  (errors/s)"
    ::= { perimetaGlobalStatsEntry 823 }

  globalStatRPG1B2TransFifoErrRate OBJECT-TYPE
    SYNTAX       CounterBasedGauge64
    MAX-ACCESS   read-only
    STATUS       current
    DESCRIPTION  "RPG1 blade 2 transmission Fifo errors
                  (errors/s)"
    ::= { perimetaGlobalStatsEntry 824 }

  globalStatRPG1B2TransHtbtErrRate OBJECT-TYPE
    SYNTAX       CounterBasedGauge64
    MAX-ACCESS   read-only
    STATUS       current
    DESCRIPTION  "RPG1 blade 2 transmission heartbeat
                  errors (errors/s)"
    ::= { perimetaGlobalStatsEntry 825 }

  globalStatRPG1B2TransWindowErrRate OBJECT-TYPE
    SYNTAX       CounterBasedGauge64
    MAX-ACCESS   read-only
    STATUS       current
    DESCRIPTION  "RPG1 blade 2 transmission window errors
                  (errors/s)"
    ::= { perimetaGlobalStatsEntry 826 }

  globalStatRPG2B2RcvdPacketRate OBJECT-TYPE
    SYNTAX       CounterBasedGauge64
    MAX-ACCESS   read-only
    STATUS       current
    DESCRIPTION  "RPG2 blade 2 pkts rcvd (pkts/s)"
    ::= { perimetaGlobalStatsEntry 827 }

  globalStatRPG2B2TransPacketRate OBJECT-TYPE
    SYNTAX       CounterBasedGauge64
    MAX-ACCESS   read-only
    STATUS       current
    DESCRIPTION  "RPG2 blade 2 pkts sent (pkts/s)"
    ::= { perimetaGlobalStatsEntry 828 }

  globalStatRPG2B2RcvdByteRate OBJECT-TYPE
    SYNTAX       CounterBasedGauge64
    MAX-ACCESS   read-only
    STATUS       current
    DESCRIPTION  "RPG2 blade 2 bytes rcvd (bytes/s)"
    ::= { perimetaGlobalStatsEntry 829 }

  globalStatRPG2B2TransByteRate OBJECT-TYPE
    SYNTAX       CounterBasedGauge64
    MAX-ACCESS   read-only
    STATUS       current
    DESCRIPTION  "RPG2 blade 2 bytes sent (bytes/s)"
    ::= { perimetaGlobalStatsEntry 830 }

  globalStatRPG2B2RcvdErrorRate OBJECT-TYPE
    SYNTAX       CounterBasedGauge64
    MAX-ACCESS   read-only
    STATUS       current
    DESCRIPTION  "RPG2 blade 2 receive errors (errors/s)"
    ::= { perimetaGlobalStatsEntry 831 }

  globalStatRPG2B2TransErrorRate OBJECT-TYPE
    SYNTAX       CounterBasedGauge64
    MAX-ACCESS   read-only
    STATUS       current
    DESCRIPTION  "RPG2 blade 2 transmission errors
                  (errors/s)"
    ::= { perimetaGlobalStatsEntry 832 }

  globalStatRPG2B2RcvdDropPacketRate OBJECT-TYPE
    SYNTAX       CounterBasedGauge64
    MAX-ACCESS   read-only
    STATUS       current
    DESCRIPTION  "RPG2 blade 2 rcvd pkts dropped (pkts/s)"
    ::= { perimetaGlobalStatsEntry 833 }

  globalStatRPG2B2TransDropPacketRate OBJECT-TYPE
    SYNTAX       CounterBasedGauge64
    MAX-ACCESS   read-only
    STATUS       current
    DESCRIPTION  "RPG2 blade 2 transmission pkts dropped
                  (pkts/s)"
    ::= { perimetaGlobalStatsEntry 834 }

  globalStatRPG2B2RcvdMulticastRate OBJECT-TYPE
    SYNTAX       CounterBasedGauge64
    MAX-ACCESS   read-only
    STATUS       current
    DESCRIPTION  "RPG2 blade 2 multicast pkts rcvd
                  (pkts/s)"
    ::= { perimetaGlobalStatsEntry 835 }

  globalStatRPG2B2TransCollisionRate OBJECT-TYPE
    SYNTAX       CounterBasedGauge64
    MAX-ACCESS   read-only
    STATUS       current
    DESCRIPTION  "RPG2 blade 2 transmission collisions per
                  second"
    ::= { perimetaGlobalStatsEntry 836 }

  globalStatRPG2B2RcvdLengthErrRate OBJECT-TYPE
    SYNTAX       CounterBasedGauge64
    MAX-ACCESS   read-only
    STATUS       current
    DESCRIPTION  "RPG2 blade 2 rcvd length errors
                  (errors/s)"
    ::= { perimetaGlobalStatsEntry 837 }

  globalStatRPG2B2RcvdOverrunErrRate OBJECT-TYPE
    SYNTAX       CounterBasedGauge64
    MAX-ACCESS   read-only
    STATUS       current
    DESCRIPTION  "RPG2 blade 2 rcvd overrun errors
                  (errors/s)"
    ::= { perimetaGlobalStatsEntry 838 }

  globalStatRPG2B2RcvdCRCErrRate OBJECT-TYPE
    SYNTAX       CounterBasedGauge64
    MAX-ACCESS   read-only
    STATUS       current
    DESCRIPTION  "RPG2 blade 2 rcvd CRC errors (errors/s)"
    ::= { perimetaGlobalStatsEntry 839 }

  globalStatRPG2B2RcvdFrameErrRate OBJECT-TYPE
    SYNTAX       CounterBasedGauge64
    MAX-ACCESS   read-only
    STATUS       current
    DESCRIPTION  "RPG2 blade 2 rcvd frame errors
                  (errors/s)"
    ::= { perimetaGlobalStatsEntry 840 }

  globalStatRPG2B2RcvdFifoFrameErrRate OBJECT-TYPE
    SYNTAX       CounterBasedGauge64
    MAX-ACCESS   read-only
    STATUS       current
    DESCRIPTION  "RPG2 blade 2 rcvd Fifo frame errors
                  (errors/s)"
    ::= { perimetaGlobalStatsEntry 841 }

  globalStatRPG2B2RcvdMissedFrameErrRate OBJECT-TYPE
    SYNTAX       CounterBasedGauge64
    MAX-ACCESS   read-only
    STATUS       current
    DESCRIPTION  "RPG2 blade 2 rcvd missed frame errors
                  (errors/s)"
    ::= { perimetaGlobalStatsEntry 842 }

  globalStatRPG2B2TransAbortErrRate OBJECT-TYPE
    SYNTAX       CounterBasedGauge64
    MAX-ACCESS   read-only
    STATUS       current
    DESCRIPTION  "RPG2 blade 2 transmission aborted errors
                  (errors/s)"
    ::= { perimetaGlobalStatsEntry 843 }

  globalStatRPG2B2TransCarrierErrRate OBJECT-TYPE
    SYNTAX       CounterBasedGauge64
    MAX-ACCESS   read-only
    STATUS       current
    DESCRIPTION  "RPG2 blade 2 transmission carrier errors
                  (errors/s)"
    ::= { perimetaGlobalStatsEntry 844 }

  globalStatRPG2B2TransFifoErrRate OBJECT-TYPE
    SYNTAX       CounterBasedGauge64
    MAX-ACCESS   read-only
    STATUS       current
    DESCRIPTION  "RPG2 blade 2 transmission Fifo errors
                  (errors/s)"
    ::= { perimetaGlobalStatsEntry 845 }

  globalStatRPG2B2TransHtbtErrRate OBJECT-TYPE
    SYNTAX       CounterBasedGauge64
    MAX-ACCESS   read-only
    STATUS       current
    DESCRIPTION  "RPG2 blade 2 transmission heartbeat
                  errors (errors/s)"
    ::= { perimetaGlobalStatsEntry 846 }

  globalStatRPG2B2TransWindowErrRate OBJECT-TYPE
    SYNTAX       CounterBasedGauge64
    MAX-ACCESS   read-only
    STATUS       current
    DESCRIPTION  "RPG2 blade 2 transmission window errors
                  (errors/s)"
    ::= { perimetaGlobalStatsEntry 847 }

  globalStatRPG3B2RcvdPacketRate OBJECT-TYPE
    SYNTAX       CounterBasedGauge64
    MAX-ACCESS   read-only
    STATUS       current
    DESCRIPTION  "RPG3 blade 2 pkts rcvd (pkts/s)"
    ::= { perimetaGlobalStatsEntry 848 }

  globalStatRPG3B2TransPacketRate OBJECT-TYPE
    SYNTAX       CounterBasedGauge64
    MAX-ACCESS   read-only
    STATUS       current
    DESCRIPTION  "RPG3 blade 2 pkts sent (pkts/s)"
    ::= { perimetaGlobalStatsEntry 849 }

  globalStatRPG3B2RcvdByteRate OBJECT-TYPE
    SYNTAX       CounterBasedGauge64
    MAX-ACCESS   read-only
    STATUS       current
    DESCRIPTION  "RPG3 blade 2 bytes rcvd (bytes/s)"
    ::= { perimetaGlobalStatsEntry 850 }

  globalStatRPG3B2TransByteRate OBJECT-TYPE
    SYNTAX       CounterBasedGauge64
    MAX-ACCESS   read-only
    STATUS       current
    DESCRIPTION  "RPG3 blade 2 bytes sent (bytes/s)"
    ::= { perimetaGlobalStatsEntry 851 }

  globalStatRPG3B2RcvdErrorRate OBJECT-TYPE
    SYNTAX       CounterBasedGauge64
    MAX-ACCESS   read-only
    STATUS       current
    DESCRIPTION  "RPG3 blade 2 receive errors (errors/s)"
    ::= { perimetaGlobalStatsEntry 852 }

  globalStatRPG3B2TransErrorRate OBJECT-TYPE
    SYNTAX       CounterBasedGauge64
    MAX-ACCESS   read-only
    STATUS       current
    DESCRIPTION  "RPG3 blade 2 transmission errors
                  (errors/s)"
    ::= { perimetaGlobalStatsEntry 853 }

  globalStatRPG3B2RcvdDropPacketRate OBJECT-TYPE
    SYNTAX       CounterBasedGauge64
    MAX-ACCESS   read-only
    STATUS       current
    DESCRIPTION  "RPG3 blade 2 rcvd pkts dropped (pkts/s)"
    ::= { perimetaGlobalStatsEntry 854 }

  globalStatRPG3B2TransDropPacketRate OBJECT-TYPE
    SYNTAX       CounterBasedGauge64
    MAX-ACCESS   read-only
    STATUS       current
    DESCRIPTION  "RPG3 blade 2 transmission pkts dropped
                  (pkts/s)"
    ::= { perimetaGlobalStatsEntry 855 }

  globalStatRPG3B2RcvdMulticastRate OBJECT-TYPE
    SYNTAX       CounterBasedGauge64
    MAX-ACCESS   read-only
    STATUS       current
    DESCRIPTION  "RPG3 blade 2 multicast pkts rcvd
                  (pkts/s)"
    ::= { perimetaGlobalStatsEntry 856 }

  globalStatRPG3B2TransCollisionRate OBJECT-TYPE
    SYNTAX       CounterBasedGauge64
    MAX-ACCESS   read-only
    STATUS       current
    DESCRIPTION  "RPG3 blade 2 transmission collisions per
                  second"
    ::= { perimetaGlobalStatsEntry 857 }

  globalStatRPG3B2RcvdLengthErrRate OBJECT-TYPE
    SYNTAX       CounterBasedGauge64
    MAX-ACCESS   read-only
    STATUS       current
    DESCRIPTION  "RPG3 blade 2 rcvd length errors
                  (errors/s)"
    ::= { perimetaGlobalStatsEntry 858 }

  globalStatRPG3B2RcvdOverrunErrRate OBJECT-TYPE
    SYNTAX       CounterBasedGauge64
    MAX-ACCESS   read-only
    STATUS       current
    DESCRIPTION  "RPG3 blade 2 rcvd overrun errors
                  (errors/s)"
    ::= { perimetaGlobalStatsEntry 859 }

  globalStatRPG3B2RcvdCRCErrRate OBJECT-TYPE
    SYNTAX       CounterBasedGauge64
    MAX-ACCESS   read-only
    STATUS       current
    DESCRIPTION  "RPG3 blade 2 rcvd CRC errors (errors/s)"
    ::= { perimetaGlobalStatsEntry 860 }

  globalStatRPG3B2RcvdFrameErrRate OBJECT-TYPE
    SYNTAX       CounterBasedGauge64
    MAX-ACCESS   read-only
    STATUS       current
    DESCRIPTION  "RPG3 blade 2 rcvd frame errors
                  (errors/s)"
    ::= { perimetaGlobalStatsEntry 861 }

  globalStatRPG3B2RcvdFifoFrameErrRate OBJECT-TYPE
    SYNTAX       CounterBasedGauge64
    MAX-ACCESS   read-only
    STATUS       current
    DESCRIPTION  "RPG3 blade 2 rcvd Fifo frame errors
                  (errors/s)"
    ::= { perimetaGlobalStatsEntry 862 }

  globalStatRPG3B2RcvdMissedFrameErrRate OBJECT-TYPE
    SYNTAX       CounterBasedGauge64
    MAX-ACCESS   read-only
    STATUS       current
    DESCRIPTION  "RPG3 blade 2 rcvd missed frame errors
                  (errors/s)"
    ::= { perimetaGlobalStatsEntry 863 }

  globalStatRPG3B2TransAbortErrRate OBJECT-TYPE
    SYNTAX       CounterBasedGauge64
    MAX-ACCESS   read-only
    STATUS       current
    DESCRIPTION  "RPG3 blade 2 transmission aborted errors
                  (errors/s)"
    ::= { perimetaGlobalStatsEntry 864 }

  globalStatRPG3B2TransCarrierErrRate OBJECT-TYPE
    SYNTAX       CounterBasedGauge64
    MAX-ACCESS   read-only
    STATUS       current
    DESCRIPTION  "RPG3 blade 2 transmission carrier errors
                  (errors/s)"
    ::= { perimetaGlobalStatsEntry 865 }

  globalStatRPG3B2TransFifoErrRate OBJECT-TYPE
    SYNTAX       CounterBasedGauge64
    MAX-ACCESS   read-only
    STATUS       current
    DESCRIPTION  "RPG3 blade 2 transmission Fifo errors
                  (errors/s)"
    ::= { perimetaGlobalStatsEntry 866 }

  globalStatRPG3B2TransHtbtErrRate OBJECT-TYPE
    SYNTAX       CounterBasedGauge64
    MAX-ACCESS   read-only
    STATUS       current
    DESCRIPTION  "RPG3 blade 2 transmission heartbeat
                  errors (errors/s)"
    ::= { perimetaGlobalStatsEntry 867 }

  globalStatRPG3B2TransWindowErrRate OBJECT-TYPE
    SYNTAX       CounterBasedGauge64
    MAX-ACCESS   read-only
    STATUS       current
    DESCRIPTION  "RPG3 blade 2 transmission window errors
                  (errors/s)"
    ::= { perimetaGlobalStatsEntry 868 }

  globalStatRPG4B2RcvdPacketRate OBJECT-TYPE
    SYNTAX       CounterBasedGauge64
    MAX-ACCESS   read-only
    STATUS       current
    DESCRIPTION  "RPG4 blade 2 pkts rcvd (pkts/s)"
    ::= { perimetaGlobalStatsEntry 869 }

  globalStatRPG4B2TransPacketRate OBJECT-TYPE
    SYNTAX       CounterBasedGauge64
    MAX-ACCESS   read-only
    STATUS       current
    DESCRIPTION  "RPG4 blade 2 pkts sent (pkts/s)"
    ::= { perimetaGlobalStatsEntry 870 }

  globalStatRPG4B2RcvdByteRate OBJECT-TYPE
    SYNTAX       CounterBasedGauge64
    MAX-ACCESS   read-only
    STATUS       current
    DESCRIPTION  "RPG4 blade 2 bytes rcvd (bytes/s)"
    ::= { perimetaGlobalStatsEntry 871 }

  globalStatRPG4B2TransByteRate OBJECT-TYPE
    SYNTAX       CounterBasedGauge64
    MAX-ACCESS   read-only
    STATUS       current
    DESCRIPTION  "RPG4 blade 2 bytes sent (bytes/s)"
    ::= { perimetaGlobalStatsEntry 872 }

  globalStatRPG4B2RcvdErrorRate OBJECT-TYPE
    SYNTAX       CounterBasedGauge64
    MAX-ACCESS   read-only
    STATUS       current
    DESCRIPTION  "RPG4 blade 2 receive errors (errors/s)"
    ::= { perimetaGlobalStatsEntry 873 }

  globalStatRPG4B2TransErrorRate OBJECT-TYPE
    SYNTAX       CounterBasedGauge64
    MAX-ACCESS   read-only
    STATUS       current
    DESCRIPTION  "RPG4 blade 2 transmission errors
                  (errors/s)"
    ::= { perimetaGlobalStatsEntry 874 }

  globalStatRPG4B2RcvdDropPacketRate OBJECT-TYPE
    SYNTAX       CounterBasedGauge64
    MAX-ACCESS   read-only
    STATUS       current
    DESCRIPTION  "RPG4 blade 2 rcvd pkts dropped (pkts/s)"
    ::= { perimetaGlobalStatsEntry 875 }

  globalStatRPG4B2TransDropPacketRate OBJECT-TYPE
    SYNTAX       CounterBasedGauge64
    MAX-ACCESS   read-only
    STATUS       current
    DESCRIPTION  "RPG4 blade 2 transmission pkts dropped
                  (pkts/s)"
    ::= { perimetaGlobalStatsEntry 876 }

  globalStatRPG4B2RcvdMulticastRate OBJECT-TYPE
    SYNTAX       CounterBasedGauge64
    MAX-ACCESS   read-only
    STATUS       current
    DESCRIPTION  "RPG4 blade 2 multicast pkts rcvd
                  (pkts/s)"
    ::= { perimetaGlobalStatsEntry 877 }

  globalStatRPG4B2TransCollisionRate OBJECT-TYPE
    SYNTAX       CounterBasedGauge64
    MAX-ACCESS   read-only
    STATUS       current
    DESCRIPTION  "RPG4 blade 2 transmission collisions per
                  second"
    ::= { perimetaGlobalStatsEntry 878 }

  globalStatRPG4B2RcvdLengthErrRate OBJECT-TYPE
    SYNTAX       CounterBasedGauge64
    MAX-ACCESS   read-only
    STATUS       current
    DESCRIPTION  "RPG4 blade 2 rcvd length errors
                  (errors/s)"
    ::= { perimetaGlobalStatsEntry 879 }

  globalStatRPG4B2RcvdOverrunErrRate OBJECT-TYPE
    SYNTAX       CounterBasedGauge64
    MAX-ACCESS   read-only
    STATUS       current
    DESCRIPTION  "RPG4 blade 2 rcvd overrun errors
                  (errors/s)"
    ::= { perimetaGlobalStatsEntry 880 }

  globalStatRPG4B2RcvdCRCErrRate OBJECT-TYPE
    SYNTAX       CounterBasedGauge64
    MAX-ACCESS   read-only
    STATUS       current
    DESCRIPTION  "RPG4 blade 2 rcvd CRC errors (errors/s)"
    ::= { perimetaGlobalStatsEntry 881 }

  globalStatRPG4B2RcvdFrameErrRate OBJECT-TYPE
    SYNTAX       CounterBasedGauge64
    MAX-ACCESS   read-only
    STATUS       current
    DESCRIPTION  "RPG4 blade 2 rcvd frame errors
                  (errors/s)"
    ::= { perimetaGlobalStatsEntry 882 }

  globalStatRPG4B2RcvdFifoFrameErrRate OBJECT-TYPE
    SYNTAX       CounterBasedGauge64
    MAX-ACCESS   read-only
    STATUS       current
    DESCRIPTION  "RPG4 blade 2 rcvd Fifo frame errors
                  (errors/s)"
    ::= { perimetaGlobalStatsEntry 883 }

  globalStatRPG4B2RcvdMissedFrameErrRate OBJECT-TYPE
    SYNTAX       CounterBasedGauge64
    MAX-ACCESS   read-only
    STATUS       current
    DESCRIPTION  "RPG4 blade 2 rcvd missed frame errors
                  (errors/s)"
    ::= { perimetaGlobalStatsEntry 884 }

  globalStatRPG4B2TransAbortErrRate OBJECT-TYPE
    SYNTAX       CounterBasedGauge64
    MAX-ACCESS   read-only
    STATUS       current
    DESCRIPTION  "RPG4 blade 2 transmission aborted errors
                  (errors/s)"
    ::= { perimetaGlobalStatsEntry 885 }

  globalStatRPG4B2TransCarrierErrRate OBJECT-TYPE
    SYNTAX       CounterBasedGauge64
    MAX-ACCESS   read-only
    STATUS       current
    DESCRIPTION  "RPG4 blade 2 transmission carrier errors
                  (errors/s)"
    ::= { perimetaGlobalStatsEntry 886 }

  globalStatRPG4B2TransFifoErrRate OBJECT-TYPE
    SYNTAX       CounterBasedGauge64
    MAX-ACCESS   read-only
    STATUS       current
    DESCRIPTION  "RPG4 blade 2 transmission Fifo errors
                  (errors/s)"
    ::= { perimetaGlobalStatsEntry 887 }

  globalStatRPG4B2TransHtbtErrRate OBJECT-TYPE
    SYNTAX       CounterBasedGauge64
    MAX-ACCESS   read-only
    STATUS       current
    DESCRIPTION  "RPG4 blade 2 transmission heartbeat
                  errors (errors/s)"
    ::= { perimetaGlobalStatsEntry 888 }

  globalStatRPG4B2TransWindowErrRate OBJECT-TYPE
    SYNTAX       CounterBasedGauge64
    MAX-ACCESS   read-only
    STATUS       current
    DESCRIPTION  "RPG4 blade 2 transmission window errors
                  (errors/s)"
    ::= { perimetaGlobalStatsEntry 889 }

  globalStatRPG5B2RcvdPacketRate OBJECT-TYPE
    SYNTAX       CounterBasedGauge64
    MAX-ACCESS   read-only
    STATUS       current
    DESCRIPTION  "RPG5 blade 2 pkts rcvd (pkts/s)"
    ::= { perimetaGlobalStatsEntry 890 }

  globalStatRPG5B2TransPacketRate OBJECT-TYPE
    SYNTAX       CounterBasedGauge64
    MAX-ACCESS   read-only
    STATUS       current
    DESCRIPTION  "RPG5 blade 2 pkts sent (pkts/s)"
    ::= { perimetaGlobalStatsEntry 891 }

  globalStatRPG5B2RcvdByteRate OBJECT-TYPE
    SYNTAX       CounterBasedGauge64
    MAX-ACCESS   read-only
    STATUS       current
    DESCRIPTION  "RPG5 blade 2 bytes rcvd (bytes/s)"
    ::= { perimetaGlobalStatsEntry 892 }

  globalStatRPG5B2TransByteRate OBJECT-TYPE
    SYNTAX       CounterBasedGauge64
    MAX-ACCESS   read-only
    STATUS       current
    DESCRIPTION  "RPG5 blade 2 bytes sent (bytes/s)"
    ::= { perimetaGlobalStatsEntry 893 }

  globalStatRPG5B2RcvdErrorRate OBJECT-TYPE
    SYNTAX       CounterBasedGauge64
    MAX-ACCESS   read-only
    STATUS       current
    DESCRIPTION  "RPG5 blade 2 receive errors (errors/s)"
    ::= { perimetaGlobalStatsEntry 894 }

  globalStatRPG5B2TransErrorRate OBJECT-TYPE
    SYNTAX       CounterBasedGauge64
    MAX-ACCESS   read-only
    STATUS       current
    DESCRIPTION  "RPG5 blade 2 transmission errors
                  (errors/s)"
    ::= { perimetaGlobalStatsEntry 895 }

  globalStatRPG5B2RcvdDropPacketRate OBJECT-TYPE
    SYNTAX       CounterBasedGauge64
    MAX-ACCESS   read-only
    STATUS       current
    DESCRIPTION  "RPG5 blade 2 rcvd pkts dropped (pkts/s)"
    ::= { perimetaGlobalStatsEntry 896 }

  globalStatRPG5B2TransDropPacketRate OBJECT-TYPE
    SYNTAX       CounterBasedGauge64
    MAX-ACCESS   read-only
    STATUS       current
    DESCRIPTION  "RPG5 blade 2 transmission pkts dropped
                  (pkts/s)"
    ::= { perimetaGlobalStatsEntry 897 }

  globalStatRPG5B2RcvdMulticastRate OBJECT-TYPE
    SYNTAX       CounterBasedGauge64
    MAX-ACCESS   read-only
    STATUS       current
    DESCRIPTION  "RPG5 blade 2 multicast pkts rcvd
                  (pkts/s)"
    ::= { perimetaGlobalStatsEntry 898 }

  globalStatRPG5B2TransCollisionRate OBJECT-TYPE
    SYNTAX       CounterBasedGauge64
    MAX-ACCESS   read-only
    STATUS       current
    DESCRIPTION  "RPG5 blade 2 transmission collisions per
                  second"
    ::= { perimetaGlobalStatsEntry 899 }

  globalStatRPG5B2RcvdLengthErrRate OBJECT-TYPE
    SYNTAX       CounterBasedGauge64
    MAX-ACCESS   read-only
    STATUS       current
    DESCRIPTION  "RPG5 blade 2 rcvd length errors
                  (errors/s)"
    ::= { perimetaGlobalStatsEntry 900 }

  globalStatRPG5B2RcvdOverrunErrRate OBJECT-TYPE
    SYNTAX       CounterBasedGauge64
    MAX-ACCESS   read-only
    STATUS       current
    DESCRIPTION  "RPG5 blade 2 rcvd overrun errors
                  (errors/s)"
    ::= { perimetaGlobalStatsEntry 901 }

  globalStatRPG5B2RcvdCRCErrRate OBJECT-TYPE
    SYNTAX       CounterBasedGauge64
    MAX-ACCESS   read-only
    STATUS       current
    DESCRIPTION  "RPG5 blade 2 rcvd CRC errors (errors/s)"
    ::= { perimetaGlobalStatsEntry 902 }

  globalStatRPG5B2RcvdFrameErrRate OBJECT-TYPE
    SYNTAX       CounterBasedGauge64
    MAX-ACCESS   read-only
    STATUS       current
    DESCRIPTION  "RPG5 blade 2 rcvd frame errors
                  (errors/s)"
    ::= { perimetaGlobalStatsEntry 903 }

  globalStatRPG5B2RcvdFifoFrameErrRate OBJECT-TYPE
    SYNTAX       CounterBasedGauge64
    MAX-ACCESS   read-only
    STATUS       current
    DESCRIPTION  "RPG5 blade 2 rcvd Fifo frame errors
                  (errors/s)"
    ::= { perimetaGlobalStatsEntry 904 }

  globalStatRPG5B2RcvdMissedFrameErrRate OBJECT-TYPE
    SYNTAX       CounterBasedGauge64
    MAX-ACCESS   read-only
    STATUS       current
    DESCRIPTION  "RPG5 blade 2 rcvd missed frame errors
                  (errors/s)"
    ::= { perimetaGlobalStatsEntry 905 }

  globalStatRPG5B2TransAbortErrRate OBJECT-TYPE
    SYNTAX       CounterBasedGauge64
    MAX-ACCESS   read-only
    STATUS       current
    DESCRIPTION  "RPG5 blade 2 transmission aborted errors
                  (errors/s)"
    ::= { perimetaGlobalStatsEntry 906 }

  globalStatRPG5B2TransCarrierErrRate OBJECT-TYPE
    SYNTAX       CounterBasedGauge64
    MAX-ACCESS   read-only
    STATUS       current
    DESCRIPTION  "RPG5 blade 2 transmission carrier errors
                  (errors/s)"
    ::= { perimetaGlobalStatsEntry 907 }

  globalStatRPG5B2TransFifoErrRate OBJECT-TYPE
    SYNTAX       CounterBasedGauge64
    MAX-ACCESS   read-only
    STATUS       current
    DESCRIPTION  "RPG5 blade 2 transmission Fifo errors
                  (errors/s)"
    ::= { perimetaGlobalStatsEntry 908 }

  globalStatRPG5B2TransHtbtErrRate OBJECT-TYPE
    SYNTAX       CounterBasedGauge64
    MAX-ACCESS   read-only
    STATUS       current
    DESCRIPTION  "RPG5 blade 2 transmission heartbeat
                  errors (errors/s)"
    ::= { perimetaGlobalStatsEntry 909 }

  globalStatRPG5B2TransWindowErrRate OBJECT-TYPE
    SYNTAX       CounterBasedGauge64
    MAX-ACCESS   read-only
    STATUS       current
    DESCRIPTION  "RPG5 blade 2 transmission window errors
                  (errors/s)"
    ::= { perimetaGlobalStatsEntry 910 }

  globalStatRPG6B2RcvdPacketRate OBJECT-TYPE
    SYNTAX       CounterBasedGauge64
    MAX-ACCESS   read-only
    STATUS       current
    DESCRIPTION  "RPG6 blade 2 pkts rcvd (pkts/s)"
    ::= { perimetaGlobalStatsEntry 911 }

  globalStatRPG6B2TransPacketRate OBJECT-TYPE
    SYNTAX       CounterBasedGauge64
    MAX-ACCESS   read-only
    STATUS       current
    DESCRIPTION  "RPG6 blade 2 pkts sent (pkts/s)"
    ::= { perimetaGlobalStatsEntry 912 }

  globalStatRPG6B2RcvdByteRate OBJECT-TYPE
    SYNTAX       CounterBasedGauge64
    MAX-ACCESS   read-only
    STATUS       current
    DESCRIPTION  "RPG6 blade 2 bytes rcvd (bytes/s)"
    ::= { perimetaGlobalStatsEntry 913 }

  globalStatRPG6B2TransByteRate OBJECT-TYPE
    SYNTAX       CounterBasedGauge64
    MAX-ACCESS   read-only
    STATUS       current
    DESCRIPTION  "RPG6 blade 2 bytes sent (bytes/s)"
    ::= { perimetaGlobalStatsEntry 914 }

  globalStatRPG6B2RcvdErrorRate OBJECT-TYPE
    SYNTAX       CounterBasedGauge64
    MAX-ACCESS   read-only
    STATUS       current
    DESCRIPTION  "RPG6 blade 2 receive errors (errors/s)"
    ::= { perimetaGlobalStatsEntry 915 }

  globalStatRPG6B2TransErrorRate OBJECT-TYPE
    SYNTAX       CounterBasedGauge64
    MAX-ACCESS   read-only
    STATUS       current
    DESCRIPTION  "RPG6 blade 2 transmission errors
                  (errors/s)"
    ::= { perimetaGlobalStatsEntry 916 }

  globalStatRPG6B2RcvdDropPacketRate OBJECT-TYPE
    SYNTAX       CounterBasedGauge64
    MAX-ACCESS   read-only
    STATUS       current
    DESCRIPTION  "RPG6 blade 2 rcvd pkts dropped (pkts/s)"
    ::= { perimetaGlobalStatsEntry 917 }

  globalStatRPG6B2TransDropPacketRate OBJECT-TYPE
    SYNTAX       CounterBasedGauge64
    MAX-ACCESS   read-only
    STATUS       current
    DESCRIPTION  "RPG6 blade 2 transmission pkts dropped
                  (pkts/s)"
    ::= { perimetaGlobalStatsEntry 918 }

  globalStatRPG6B2RcvdMulticastRate OBJECT-TYPE
    SYNTAX       CounterBasedGauge64
    MAX-ACCESS   read-only
    STATUS       current
    DESCRIPTION  "RPG6 blade 2 multicast pkts rcvd
                  (pkts/s)"
    ::= { perimetaGlobalStatsEntry 919 }

  globalStatRPG6B2TransCollisionRate OBJECT-TYPE
    SYNTAX       CounterBasedGauge64
    MAX-ACCESS   read-only
    STATUS       current
    DESCRIPTION  "RPG6 blade 2 transmission collisions per
                  second"
    ::= { perimetaGlobalStatsEntry 920 }

  globalStatRPG6B2RcvdLengthErrRate OBJECT-TYPE
    SYNTAX       CounterBasedGauge64
    MAX-ACCESS   read-only
    STATUS       current
    DESCRIPTION  "RPG6 blade 2 rcvd length errors
                  (errors/s)"
    ::= { perimetaGlobalStatsEntry 921 }

  globalStatRPG6B2RcvdOverrunErrRate OBJECT-TYPE
    SYNTAX       CounterBasedGauge64
    MAX-ACCESS   read-only
    STATUS       current
    DESCRIPTION  "RPG6 blade 2 rcvd overrun errors
                  (errors/s)"
    ::= { perimetaGlobalStatsEntry 922 }

  globalStatRPG6B2RcvdCRCErrRate OBJECT-TYPE
    SYNTAX       CounterBasedGauge64
    MAX-ACCESS   read-only
    STATUS       current
    DESCRIPTION  "RPG6 blade 2 rcvd CRC errors (errors/s)"
    ::= { perimetaGlobalStatsEntry 923 }

  globalStatRPG6B2RcvdFrameErrRate OBJECT-TYPE
    SYNTAX       CounterBasedGauge64
    MAX-ACCESS   read-only
    STATUS       current
    DESCRIPTION  "RPG6 blade 2 rcvd frame errors
                  (errors/s)"
    ::= { perimetaGlobalStatsEntry 924 }

  globalStatRPG6B2RcvdFifoFrameErrRate OBJECT-TYPE
    SYNTAX       CounterBasedGauge64
    MAX-ACCESS   read-only
    STATUS       current
    DESCRIPTION  "RPG6 blade 2 rcvd Fifo frame errors
                  (errors/s)"
    ::= { perimetaGlobalStatsEntry 925 }

  globalStatRPG6B2RcvdMissedFrameErrRate OBJECT-TYPE
    SYNTAX       CounterBasedGauge64
    MAX-ACCESS   read-only
    STATUS       current
    DESCRIPTION  "RPG6 blade 2 rcvd missed frame errors
                  (errors/s)"
    ::= { perimetaGlobalStatsEntry 926 }

  globalStatRPG6B2TransAbortErrRate OBJECT-TYPE
    SYNTAX       CounterBasedGauge64
    MAX-ACCESS   read-only
    STATUS       current
    DESCRIPTION  "RPG6 blade 2 transmission aborted errors
                  (errors/s)"
    ::= { perimetaGlobalStatsEntry 927 }

  globalStatRPG6B2TransCarrierErrRate OBJECT-TYPE
    SYNTAX       CounterBasedGauge64
    MAX-ACCESS   read-only
    STATUS       current
    DESCRIPTION  "RPG6 blade 2 transmission carrier errors
                  (errors/s)"
    ::= { perimetaGlobalStatsEntry 928 }

  globalStatRPG6B2TransFifoErrRate OBJECT-TYPE
    SYNTAX       CounterBasedGauge64
    MAX-ACCESS   read-only
    STATUS       current
    DESCRIPTION  "RPG6 blade 2 transmission Fifo errors
                  (errors/s)"
    ::= { perimetaGlobalStatsEntry 929 }

  globalStatRPG6B2TransHtbtErrRate OBJECT-TYPE
    SYNTAX       CounterBasedGauge64
    MAX-ACCESS   read-only
    STATUS       current
    DESCRIPTION  "RPG6 blade 2 transmission heartbeat
                  errors (errors/s)"
    ::= { perimetaGlobalStatsEntry 930 }

  globalStatRPG6B2TransWindowErrRate OBJECT-TYPE
    SYNTAX       CounterBasedGauge64
    MAX-ACCESS   read-only
    STATUS       current
    DESCRIPTION  "RPG6 blade 2 transmission window errors
                  (errors/s)"
    ::= { perimetaGlobalStatsEntry 931 }

  globalStatRPG7B2RcvdPacketRate OBJECT-TYPE
    SYNTAX       CounterBasedGauge64
    MAX-ACCESS   read-only
    STATUS       current
    DESCRIPTION  "RPG7 blade 2 pkts rcvd (pkts/s)"
    ::= { perimetaGlobalStatsEntry 932 }

  globalStatRPG7B2TransPacketRate OBJECT-TYPE
    SYNTAX       CounterBasedGauge64
    MAX-ACCESS   read-only
    STATUS       current
    DESCRIPTION  "RPG7 blade 2 pkts sent (pkts/s)"
    ::= { perimetaGlobalStatsEntry 933 }

  globalStatRPG7B2RcvdByteRate OBJECT-TYPE
    SYNTAX       CounterBasedGauge64
    MAX-ACCESS   read-only
    STATUS       current
    DESCRIPTION  "RPG7 blade 2 bytes rcvd (bytes/s)"
    ::= { perimetaGlobalStatsEntry 934 }

  globalStatRPG7B2TransByteRate OBJECT-TYPE
    SYNTAX       CounterBasedGauge64
    MAX-ACCESS   read-only
    STATUS       current
    DESCRIPTION  "RPG7 blade 2 bytes sent (bytes/s)"
    ::= { perimetaGlobalStatsEntry 935 }

  globalStatRPG7B2RcvdErrorRate OBJECT-TYPE
    SYNTAX       CounterBasedGauge64
    MAX-ACCESS   read-only
    STATUS       current
    DESCRIPTION  "RPG7 blade 2 receive errors (errors/s)"
    ::= { perimetaGlobalStatsEntry 936 }

  globalStatRPG7B2TransErrorRate OBJECT-TYPE
    SYNTAX       CounterBasedGauge64
    MAX-ACCESS   read-only
    STATUS       current
    DESCRIPTION  "RPG7 blade 2 transmission errors
                  (errors/s)"
    ::= { perimetaGlobalStatsEntry 937 }

  globalStatRPG7B2RcvdDropPacketRate OBJECT-TYPE
    SYNTAX       CounterBasedGauge64
    MAX-ACCESS   read-only
    STATUS       current
    DESCRIPTION  "RPG7 blade 2 rcvd pkts dropped (pkts/s)"
    ::= { perimetaGlobalStatsEntry 938 }

  globalStatRPG7B2TransDropPacketRate OBJECT-TYPE
    SYNTAX       CounterBasedGauge64
    MAX-ACCESS   read-only
    STATUS       current
    DESCRIPTION  "RPG7 blade 2 transmission pkts dropped
                  (pkts/s)"
    ::= { perimetaGlobalStatsEntry 939 }

  globalStatRPG7B2RcvdMulticastRate OBJECT-TYPE
    SYNTAX       CounterBasedGauge64
    MAX-ACCESS   read-only
    STATUS       current
    DESCRIPTION  "RPG7 blade 2 multicast pkts rcvd
                  (pkts/s)"
    ::= { perimetaGlobalStatsEntry 940 }

  globalStatRPG7B2TransCollisionRate OBJECT-TYPE
    SYNTAX       CounterBasedGauge64
    MAX-ACCESS   read-only
    STATUS       current
    DESCRIPTION  "RPG7 blade 2 transmission collisions per
                  second"
    ::= { perimetaGlobalStatsEntry 941 }

  globalStatRPG7B2RcvdLengthErrRate OBJECT-TYPE
    SYNTAX       CounterBasedGauge64
    MAX-ACCESS   read-only
    STATUS       current
    DESCRIPTION  "RPG7 blade 2 rcvd length errors
                  (errors/s)"
    ::= { perimetaGlobalStatsEntry 942 }

  globalStatRPG7B2RcvdOverrunErrRate OBJECT-TYPE
    SYNTAX       CounterBasedGauge64
    MAX-ACCESS   read-only
    STATUS       current
    DESCRIPTION  "RPG7 blade 2 rcvd overrun errors
                  (errors/s)"
    ::= { perimetaGlobalStatsEntry 943 }

  globalStatRPG7B2RcvdCRCErrRate OBJECT-TYPE
    SYNTAX       CounterBasedGauge64
    MAX-ACCESS   read-only
    STATUS       current
    DESCRIPTION  "RPG7 blade 2 rcvd CRC errors (errors/s)"
    ::= { perimetaGlobalStatsEntry 944 }

  globalStatRPG7B2RcvdFrameErrRate OBJECT-TYPE
    SYNTAX       CounterBasedGauge64
    MAX-ACCESS   read-only
    STATUS       current
    DESCRIPTION  "RPG7 blade 2 rcvd frame errors
                  (errors/s)"
    ::= { perimetaGlobalStatsEntry 945 }

  globalStatRPG7B2RcvdFifoFrameErrRate OBJECT-TYPE
    SYNTAX       CounterBasedGauge64
    MAX-ACCESS   read-only
    STATUS       current
    DESCRIPTION  "RPG7 blade 2 rcvd Fifo frame errors
                  (errors/s)"
    ::= { perimetaGlobalStatsEntry 946 }

  globalStatRPG7B2RcvdMissedFrameErrRate OBJECT-TYPE
    SYNTAX       CounterBasedGauge64
    MAX-ACCESS   read-only
    STATUS       current
    DESCRIPTION  "RPG7 blade 2 rcvd missed frame errors
                  (errors/s)"
    ::= { perimetaGlobalStatsEntry 947 }

  globalStatRPG7B2TransAbortErrRate OBJECT-TYPE
    SYNTAX       CounterBasedGauge64
    MAX-ACCESS   read-only
    STATUS       current
    DESCRIPTION  "RPG7 blade 2 transmission aborted errors
                  (errors/s)"
    ::= { perimetaGlobalStatsEntry 948 }

  globalStatRPG7B2TransCarrierErrRate OBJECT-TYPE
    SYNTAX       CounterBasedGauge64
    MAX-ACCESS   read-only
    STATUS       current
    DESCRIPTION  "RPG7 blade 2 transmission carrier errors
                  (errors/s)"
    ::= { perimetaGlobalStatsEntry 949 }

  globalStatRPG7B2TransFifoErrRate OBJECT-TYPE
    SYNTAX       CounterBasedGauge64
    MAX-ACCESS   read-only
    STATUS       current
    DESCRIPTION  "RPG7 blade 2 transmission Fifo errors
                  (errors/s)"
    ::= { perimetaGlobalStatsEntry 950 }

  globalStatRPG7B2TransHtbtErrRate OBJECT-TYPE
    SYNTAX       CounterBasedGauge64
    MAX-ACCESS   read-only
    STATUS       current
    DESCRIPTION  "RPG7 blade 2 transmission heartbeat
                  errors (errors/s)"
    ::= { perimetaGlobalStatsEntry 951 }

  globalStatRPG7B2TransWindowErrRate OBJECT-TYPE
    SYNTAX       CounterBasedGauge64
    MAX-ACCESS   read-only
    STATUS       current
    DESCRIPTION  "RPG7 blade 2 transmission window errors
                  (errors/s)"
    ::= { perimetaGlobalStatsEntry 952 }

  globalStatRPG8B2RcvdPacketRate OBJECT-TYPE
    SYNTAX       CounterBasedGauge64
    MAX-ACCESS   read-only
    STATUS       current
    DESCRIPTION  "RPG8 blade 2 pkts rcvd (pkts/s)"
    ::= { perimetaGlobalStatsEntry 953 }

  globalStatRPG8B2TransPacketRate OBJECT-TYPE
    SYNTAX       CounterBasedGauge64
    MAX-ACCESS   read-only
    STATUS       current
    DESCRIPTION  "RPG8 blade 2 pkts sent (pkts/s)"
    ::= { perimetaGlobalStatsEntry 954 }

  globalStatRPG8B2RcvdByteRate OBJECT-TYPE
    SYNTAX       CounterBasedGauge64
    MAX-ACCESS   read-only
    STATUS       current
    DESCRIPTION  "RPG8 blade 2 bytes rcvd (bytes/s)"
    ::= { perimetaGlobalStatsEntry 955 }

  globalStatRPG8B2TransByteRate OBJECT-TYPE
    SYNTAX       CounterBasedGauge64
    MAX-ACCESS   read-only
    STATUS       current
    DESCRIPTION  "RPG8 blade 2 bytes sent (bytes/s)"
    ::= { perimetaGlobalStatsEntry 956 }

  globalStatRPG8B2RcvdErrorRate OBJECT-TYPE
    SYNTAX       CounterBasedGauge64
    MAX-ACCESS   read-only
    STATUS       current
    DESCRIPTION  "RPG8 blade 2 receive errors (errors/s)"
    ::= { perimetaGlobalStatsEntry 957 }

  globalStatRPG8B2TransErrorRate OBJECT-TYPE
    SYNTAX       CounterBasedGauge64
    MAX-ACCESS   read-only
    STATUS       current
    DESCRIPTION  "RPG8 blade 2 transmission errors
                  (errors/s)"
    ::= { perimetaGlobalStatsEntry 958 }

  globalStatRPG8B2RcvdDropPacketRate OBJECT-TYPE
    SYNTAX       CounterBasedGauge64
    MAX-ACCESS   read-only
    STATUS       current
    DESCRIPTION  "RPG8 blade 2 rcvd pkts dropped (pkts/s)"
    ::= { perimetaGlobalStatsEntry 959 }

  globalStatRPG8B2TransDropPacketRate OBJECT-TYPE
    SYNTAX       CounterBasedGauge64
    MAX-ACCESS   read-only
    STATUS       current
    DESCRIPTION  "RPG8 blade 2 transmission pkts dropped
                  (pkts/s)"
    ::= { perimetaGlobalStatsEntry 960 }

  globalStatRPG8B2RcvdMulticastRate OBJECT-TYPE
    SYNTAX       CounterBasedGauge64
    MAX-ACCESS   read-only
    STATUS       current
    DESCRIPTION  "RPG8 blade 2 multicast pkts rcvd
                  (pkts/s)"
    ::= { perimetaGlobalStatsEntry 961 }

  globalStatRPG8B2TransCollisionRate OBJECT-TYPE
    SYNTAX       CounterBasedGauge64
    MAX-ACCESS   read-only
    STATUS       current
    DESCRIPTION  "RPG8 blade 2 transmission collisions per
                  second"
    ::= { perimetaGlobalStatsEntry 962 }

  globalStatRPG8B2RcvdLengthErrRate OBJECT-TYPE
    SYNTAX       CounterBasedGauge64
    MAX-ACCESS   read-only
    STATUS       current
    DESCRIPTION  "RPG8 blade 2 rcvd length errors
                  (errors/s)"
    ::= { perimetaGlobalStatsEntry 963 }

  globalStatRPG8B2RcvdOverrunErrRate OBJECT-TYPE
    SYNTAX       CounterBasedGauge64
    MAX-ACCESS   read-only
    STATUS       current
    DESCRIPTION  "RPG8 blade 2 rcvd overrun errors
                  (errors/s)"
    ::= { perimetaGlobalStatsEntry 964 }

  globalStatRPG8B2RcvdCRCErrRate OBJECT-TYPE
    SYNTAX       CounterBasedGauge64
    MAX-ACCESS   read-only
    STATUS       current
    DESCRIPTION  "RPG8 blade 2 rcvd CRC errors (errors/s)"
    ::= { perimetaGlobalStatsEntry 965 }

  globalStatRPG8B2RcvdFrameErrRate OBJECT-TYPE
    SYNTAX       CounterBasedGauge64
    MAX-ACCESS   read-only
    STATUS       current
    DESCRIPTION  "RPG8 blade 2 rcvd frame errors
                  (errors/s)"
    ::= { perimetaGlobalStatsEntry 966 }

  globalStatRPG8B2RcvdFifoFrameErrRate OBJECT-TYPE
    SYNTAX       CounterBasedGauge64
    MAX-ACCESS   read-only
    STATUS       current
    DESCRIPTION  "RPG8 blade 2 rcvd Fifo frame errors
                  (errors/s)"
    ::= { perimetaGlobalStatsEntry 967 }

  globalStatRPG8B2RcvdMissedFrameErrRate OBJECT-TYPE
    SYNTAX       CounterBasedGauge64
    MAX-ACCESS   read-only
    STATUS       current
    DESCRIPTION  "RPG8 blade 2 rcvd missed frame errors
                  (errors/s)"
    ::= { perimetaGlobalStatsEntry 968 }

  globalStatRPG8B2TransAbortErrRate OBJECT-TYPE
    SYNTAX       CounterBasedGauge64
    MAX-ACCESS   read-only
    STATUS       current
    DESCRIPTION  "RPG8 blade 2 transmission aborted errors
                  (errors/s)"
    ::= { perimetaGlobalStatsEntry 969 }

  globalStatRPG8B2TransCarrierErrRate OBJECT-TYPE
    SYNTAX       CounterBasedGauge64
    MAX-ACCESS   read-only
    STATUS       current
    DESCRIPTION  "RPG8 blade 2 transmission carrier errors
                  (errors/s)"
    ::= { perimetaGlobalStatsEntry 970 }

  globalStatRPG8B2TransFifoErrRate OBJECT-TYPE
    SYNTAX       CounterBasedGauge64
    MAX-ACCESS   read-only
    STATUS       current
    DESCRIPTION  "RPG8 blade 2 transmission Fifo errors
                  (errors/s)"
    ::= { perimetaGlobalStatsEntry 971 }

  globalStatRPG8B2TransHtbtErrRate OBJECT-TYPE
    SYNTAX       CounterBasedGauge64
    MAX-ACCESS   read-only
    STATUS       current
    DESCRIPTION  "RPG8 blade 2 transmission heartbeat
                  errors (errors/s)"
    ::= { perimetaGlobalStatsEntry 972 }

  globalStatRPG8B2TransWindowErrRate OBJECT-TYPE
    SYNTAX       CounterBasedGauge64
    MAX-ACCESS   read-only
    STATUS       current
    DESCRIPTION  "RPG8 blade 2 transmission window errors
                  (errors/s)"
    ::= { perimetaGlobalStatsEntry 973 }

  globalStatIBG1MB2RcvdPacketRate OBJECT-TYPE
    SYNTAX       CounterBasedGauge64
    MAX-ACCESS   read-only
    STATUS       current
    DESCRIPTION  "IBG1_M blade 2 pkts rcvd (pkts/s)"
    ::= { perimetaGlobalStatsEntry 974 }

  globalStatIBG1MB2TransPacketRate OBJECT-TYPE
    SYNTAX       CounterBasedGauge64
    MAX-ACCESS   read-only
    STATUS       current
    DESCRIPTION  "IBG1_M blade 2 pkts sent (pkts/s)"
    ::= { perimetaGlobalStatsEntry 975 }

  globalStatIBG1MB2RcvdByteRate OBJECT-TYPE
    SYNTAX       CounterBasedGauge64
    MAX-ACCESS   read-only
    STATUS       current
    DESCRIPTION  "IBG1_M blade 2 bytes rcvd (bytes/s)"
    ::= { perimetaGlobalStatsEntry 976 }

  globalStatIBG1MB2TransByteRate OBJECT-TYPE
    SYNTAX       CounterBasedGauge64
    MAX-ACCESS   read-only
    STATUS       current
    DESCRIPTION  "IBG1_M blade 2 bytes sent (bytes/s)"
    ::= { perimetaGlobalStatsEntry 977 }

  globalStatIBG1MB2RcvdErrorRate OBJECT-TYPE
    SYNTAX       CounterBasedGauge64
    MAX-ACCESS   read-only
    STATUS       current
    DESCRIPTION  "IBG1_M blade 2 receive errors (errors/s)"
    ::= { perimetaGlobalStatsEntry 978 }

  globalStatIBG1MB2TransErrorRate OBJECT-TYPE
    SYNTAX       CounterBasedGauge64
    MAX-ACCESS   read-only
    STATUS       current
    DESCRIPTION  "IBG1_M blade 2 transmission errors
                  (errors/s)"
    ::= { perimetaGlobalStatsEntry 979 }

  globalStatIBG1MB2RcvdDropPacketRate OBJECT-TYPE
    SYNTAX       CounterBasedGauge64
    MAX-ACCESS   read-only
    STATUS       current
    DESCRIPTION  "IBG1_M blade 2 rcvd pkts dropped
                  (pkts/s)"
    ::= { perimetaGlobalStatsEntry 980 }

  globalStatIBG1MB2TransDropPacketRate OBJECT-TYPE
    SYNTAX       CounterBasedGauge64
    MAX-ACCESS   read-only
    STATUS       current
    DESCRIPTION  "IBG1_M blade 2 transmission pkts dropped
                  (pkts/s)"
    ::= { perimetaGlobalStatsEntry 981 }

  globalStatIBG1MB2RcvdMulticastRate OBJECT-TYPE
    SYNTAX       CounterBasedGauge64
    MAX-ACCESS   read-only
    STATUS       current
    DESCRIPTION  "IBG1_M blade 2 multicast pkts rcvd
                  (pkts/s)"
    ::= { perimetaGlobalStatsEntry 982 }

  globalStatIBG1MB2TransCollisionRate OBJECT-TYPE
    SYNTAX       CounterBasedGauge64
    MAX-ACCESS   read-only
    STATUS       current
    DESCRIPTION  "IBG1_M blade 2 transmission collisions
                  per second"
    ::= { perimetaGlobalStatsEntry 983 }

  globalStatIBG1MB2RcvdLengthErrRate OBJECT-TYPE
    SYNTAX       CounterBasedGauge64
    MAX-ACCESS   read-only
    STATUS       current
    DESCRIPTION  "IBG1_M blade 2 rcvd length errors
                  (errors/s)"
    ::= { perimetaGlobalStatsEntry 984 }

  globalStatIBG1MB2RcvdOverrunErrRate OBJECT-TYPE
    SYNTAX       CounterBasedGauge64
    MAX-ACCESS   read-only
    STATUS       current
    DESCRIPTION  "IBG1_M blade 2 rcvd overrun errors
                  (errors/s)"
    ::= { perimetaGlobalStatsEntry 985 }

  globalStatIBG1MB2RcvdCRCErrRate OBJECT-TYPE
    SYNTAX       CounterBasedGauge64
    MAX-ACCESS   read-only
    STATUS       current
    DESCRIPTION  "IBG1_M blade 2 rcvd CRC errors
                  (errors/s)"
    ::= { perimetaGlobalStatsEntry 986 }

  globalStatIBG1MB2RcvdFrameErrRate OBJECT-TYPE
    SYNTAX       CounterBasedGauge64
    MAX-ACCESS   read-only
    STATUS       current
    DESCRIPTION  "IBG1_M blade 2 rcvd frame errors
                  (errors/s)"
    ::= { perimetaGlobalStatsEntry 987 }

  globalStatIBG1MB2RcvdFifoFrameErrRate OBJECT-TYPE
    SYNTAX       CounterBasedGauge64
    MAX-ACCESS   read-only
    STATUS       current
    DESCRIPTION  "IBG1_M blade 2 rcvd Fifo frame errors
                  (errors/s)"
    ::= { perimetaGlobalStatsEntry 988 }

  globalStatIBG1MB2RcvdMissedFrameErrRate OBJECT-TYPE
    SYNTAX       CounterBasedGauge64
    MAX-ACCESS   read-only
    STATUS       current
    DESCRIPTION  "IBG1_M blade 2 rcvd missed frame errors
                  (errors/s)"
    ::= { perimetaGlobalStatsEntry 989 }

  globalStatIBG1MB2TransAbortErrRate OBJECT-TYPE
    SYNTAX       CounterBasedGauge64
    MAX-ACCESS   read-only
    STATUS       current
    DESCRIPTION  "IBG1_M blade 2 transmission aborted
                  errors (errors/s)"
    ::= { perimetaGlobalStatsEntry 990 }

  globalStatIBG1MB2TransCarrierErrRate OBJECT-TYPE
    SYNTAX       CounterBasedGauge64
    MAX-ACCESS   read-only
    STATUS       current
    DESCRIPTION  "IBG1_M blade 2 transmission carrier
                  errors (errors/s)"
    ::= { perimetaGlobalStatsEntry 991 }

  globalStatIBG1MB2TransFifoErrRate OBJECT-TYPE
    SYNTAX       CounterBasedGauge64
    MAX-ACCESS   read-only
    STATUS       current
    DESCRIPTION  "IBG1_M blade 2 transmission Fifo errors
                  (errors/s)"
    ::= { perimetaGlobalStatsEntry 992 }

  globalStatIBG1MB2TransHtbtErrRate OBJECT-TYPE
    SYNTAX       CounterBasedGauge64
    MAX-ACCESS   read-only
    STATUS       current
    DESCRIPTION  "IBG1_M blade 2 transmission heartbeat
                  errors (errors/s)"
    ::= { perimetaGlobalStatsEntry 993 }

  globalStatIBG1MB2TransWindowErrRate OBJECT-TYPE
    SYNTAX       CounterBasedGauge64
    MAX-ACCESS   read-only
    STATUS       current
    DESCRIPTION  "IBG1_M blade 2 transmission window
                  errors (errors/s)"
    ::= { perimetaGlobalStatsEntry 994 }

  globalStatIBG2MB2RcvdPacketRate OBJECT-TYPE
    SYNTAX       CounterBasedGauge64
    MAX-ACCESS   read-only
    STATUS       current
    DESCRIPTION  "IBG2_M blade 2 pkts rcvd (pkts/s)"
    ::= { perimetaGlobalStatsEntry 995 }

  globalStatIBG2MB2TransPacketRate OBJECT-TYPE
    SYNTAX       CounterBasedGauge64
    MAX-ACCESS   read-only
    STATUS       current
    DESCRIPTION  "IBG2_M blade 2 pkts sent (pkts/s)"
    ::= { perimetaGlobalStatsEntry 996 }

  globalStatIBG2MB2RcvdByteRate OBJECT-TYPE
    SYNTAX       CounterBasedGauge64
    MAX-ACCESS   read-only
    STATUS       current
    DESCRIPTION  "IBG2_M blade 2 bytes rcvd (bytes/s)"
    ::= { perimetaGlobalStatsEntry 997 }

  globalStatIBG2MB2TransByteRate OBJECT-TYPE
    SYNTAX       CounterBasedGauge64
    MAX-ACCESS   read-only
    STATUS       current
    DESCRIPTION  "IBG2_M blade 2 bytes sent (bytes/s)"
    ::= { perimetaGlobalStatsEntry 998 }

  globalStatIBG2MB2RcvdErrorRate OBJECT-TYPE
    SYNTAX       CounterBasedGauge64
    MAX-ACCESS   read-only
    STATUS       current
    DESCRIPTION  "IBG2_M blade 2 receive errors (errors/s)"
    ::= { perimetaGlobalStatsEntry 999 }

  globalStatIBG2MB2TransErrorRate OBJECT-TYPE
    SYNTAX       CounterBasedGauge64
    MAX-ACCESS   read-only
    STATUS       current
    DESCRIPTION  "IBG2_M blade 2 transmission errors
                  (errors/s)"
    ::= { perimetaGlobalStatsEntry 1000 }

  globalStatIBG2MB2RcvdDropPacketRate OBJECT-TYPE
    SYNTAX       CounterBasedGauge64
    MAX-ACCESS   read-only
    STATUS       current
    DESCRIPTION  "IBG2_M blade 2 rcvd pkts dropped
                  (pkts/s)"
    ::= { perimetaGlobalStatsEntry 1001 }

  globalStatIBG2MB2TransDropPacketRate OBJECT-TYPE
    SYNTAX       CounterBasedGauge64
    MAX-ACCESS   read-only
    STATUS       current
    DESCRIPTION  "IBG2_M blade 2 transmission pkts dropped
                  (pkts/s)"
    ::= { perimetaGlobalStatsEntry 1002 }

  globalStatIBG2MB2RcvdMulticastRate OBJECT-TYPE
    SYNTAX       CounterBasedGauge64
    MAX-ACCESS   read-only
    STATUS       current
    DESCRIPTION  "IBG2_M blade 2 multicast pkts rcvd
                  (pkts/s)"
    ::= { perimetaGlobalStatsEntry 1003 }

  globalStatIBG2MB2TransCollisionRate OBJECT-TYPE
    SYNTAX       CounterBasedGauge64
    MAX-ACCESS   read-only
    STATUS       current
    DESCRIPTION  "IBG2_M blade 2 transmission collisions
                  per second"
    ::= { perimetaGlobalStatsEntry 1004 }

  globalStatIBG2MB2RcvdLengthErrRate OBJECT-TYPE
    SYNTAX       CounterBasedGauge64
    MAX-ACCESS   read-only
    STATUS       current
    DESCRIPTION  "IBG2_M blade 2 rcvd length errors
                  (errors/s)"
    ::= { perimetaGlobalStatsEntry 1005 }

  globalStatIBG2MB2RcvdOverrunErrRate OBJECT-TYPE
    SYNTAX       CounterBasedGauge64
    MAX-ACCESS   read-only
    STATUS       current
    DESCRIPTION  "IBG2_M blade 2 rcvd overrun errors
                  (errors/s)"
    ::= { perimetaGlobalStatsEntry 1006 }

  globalStatIBG2MB2RcvdCRCErrRate OBJECT-TYPE
    SYNTAX       CounterBasedGauge64
    MAX-ACCESS   read-only
    STATUS       current
    DESCRIPTION  "IBG2_M blade 2 rcvd CRC errors
                  (errors/s)"
    ::= { perimetaGlobalStatsEntry 1007 }

  globalStatIBG2MB2RcvdFrameErrRate OBJECT-TYPE
    SYNTAX       CounterBasedGauge64
    MAX-ACCESS   read-only
    STATUS       current
    DESCRIPTION  "IBG2_M blade 2 rcvd frame errors
                  (errors/s)"
    ::= { perimetaGlobalStatsEntry 1008 }

  globalStatIBG2MB2RcvdFifoFrameErrRate OBJECT-TYPE
    SYNTAX       CounterBasedGauge64
    MAX-ACCESS   read-only
    STATUS       current
    DESCRIPTION  "IBG2_M blade 2 rcvd Fifo frame errors
                  (errors/s)"
    ::= { perimetaGlobalStatsEntry 1009 }

  globalStatIBG2MB2RcvdMissedFrameErrRate OBJECT-TYPE
    SYNTAX       CounterBasedGauge64
    MAX-ACCESS   read-only
    STATUS       current
    DESCRIPTION  "IBG2_M blade 2 rcvd missed frame errors
                  (errors/s)"
    ::= { perimetaGlobalStatsEntry 1010 }

  globalStatIBG2MB2TransAbortErrRate OBJECT-TYPE
    SYNTAX       CounterBasedGauge64
    MAX-ACCESS   read-only
    STATUS       current
    DESCRIPTION  "IBG2_M blade 2 transmission aborted
                  errors (errors/s)"
    ::= { perimetaGlobalStatsEntry 1011 }

  globalStatIBG2MB2TransCarrierErrRate OBJECT-TYPE
    SYNTAX       CounterBasedGauge64
    MAX-ACCESS   read-only
    STATUS       current
    DESCRIPTION  "IBG2_M blade 2 transmission carrier
                  errors (errors/s)"
    ::= { perimetaGlobalStatsEntry 1012 }

  globalStatIBG2MB2TransFifoErrRate OBJECT-TYPE
    SYNTAX       CounterBasedGauge64
    MAX-ACCESS   read-only
    STATUS       current
    DESCRIPTION  "IBG2_M blade 2 transmission Fifo errors
                  (errors/s)"
    ::= { perimetaGlobalStatsEntry 1013 }

  globalStatIBG2MB2TransHtbtErrRate OBJECT-TYPE
    SYNTAX       CounterBasedGauge64
    MAX-ACCESS   read-only
    STATUS       current
    DESCRIPTION  "IBG2_M blade 2 transmission heartbeat
                  errors (errors/s)"
    ::= { perimetaGlobalStatsEntry 1014 }

  globalStatIBG2MB2TransWindowErrRate OBJECT-TYPE
    SYNTAX       CounterBasedGauge64
    MAX-ACCESS   read-only
    STATUS       current
    DESCRIPTION  "IBG2_M blade 2 transmission window
                  errors (errors/s)"
    ::= { perimetaGlobalStatsEntry 1015 }

  globalStatIBG1B2RcvdPacketRate OBJECT-TYPE
    SYNTAX       CounterBasedGauge64
    MAX-ACCESS   read-only
    STATUS       current
    DESCRIPTION  "IBG1 blade 2 pkts rcvd (pkts/s)"
    ::= { perimetaGlobalStatsEntry 1016 }

  globalStatIBG1B2TransPacketRate OBJECT-TYPE
    SYNTAX       CounterBasedGauge64
    MAX-ACCESS   read-only
    STATUS       current
    DESCRIPTION  "IBG1 blade 2 pkts sent (pkts/s)"
    ::= { perimetaGlobalStatsEntry 1017 }

  globalStatIBG1B2RcvdByteRate OBJECT-TYPE
    SYNTAX       CounterBasedGauge64
    MAX-ACCESS   read-only
    STATUS       current
    DESCRIPTION  "IBG1 blade 2 bytes rcvd (bytes/s)"
    ::= { perimetaGlobalStatsEntry 1018 }

  globalStatIBG1B2TransByteRate OBJECT-TYPE
    SYNTAX       CounterBasedGauge64
    MAX-ACCESS   read-only
    STATUS       current
    DESCRIPTION  "IBG1 blade 2 bytes sent (bytes/s)"
    ::= { perimetaGlobalStatsEntry 1019 }

  globalStatIBG1B2RcvdErrorRate OBJECT-TYPE
    SYNTAX       CounterBasedGauge64
    MAX-ACCESS   read-only
    STATUS       current
    DESCRIPTION  "IBG1 blade 2 receive errors (errors/s)"
    ::= { perimetaGlobalStatsEntry 1020 }

  globalStatIBG1B2TransErrorRate OBJECT-TYPE
    SYNTAX       CounterBasedGauge64
    MAX-ACCESS   read-only
    STATUS       current
    DESCRIPTION  "IBG1 blade 2 transmission errors
                  (errors/s)"
    ::= { perimetaGlobalStatsEntry 1021 }

  globalStatIBG1B2RcvdDropPacketRate OBJECT-TYPE
    SYNTAX       CounterBasedGauge64
    MAX-ACCESS   read-only
    STATUS       current
    DESCRIPTION  "IBG1 blade 2 rcvd pkts dropped (pkts/s)"
    ::= { perimetaGlobalStatsEntry 1022 }

  globalStatIBG1B2TransDropPacketRate OBJECT-TYPE
    SYNTAX       CounterBasedGauge64
    MAX-ACCESS   read-only
    STATUS       current
    DESCRIPTION  "IBG1 blade 2 transmission pkts dropped
                  (pkts/s)"
    ::= { perimetaGlobalStatsEntry 1023 }

  globalStatIBG1B2RcvdMulticastRate OBJECT-TYPE
    SYNTAX       CounterBasedGauge64
    MAX-ACCESS   read-only
    STATUS       current
    DESCRIPTION  "IBG1 blade 2 multicast pkts rcvd
                  (pkts/s)"
    ::= { perimetaGlobalStatsEntry 1024 }

  globalStatIBG1B2TransCollisionRate OBJECT-TYPE
    SYNTAX       CounterBasedGauge64
    MAX-ACCESS   read-only
    STATUS       current
    DESCRIPTION  "IBG1 blade 2 transmission collisions per
                  second"
    ::= { perimetaGlobalStatsEntry 1025 }

  globalStatIBG1B2RcvdLengthErrRate OBJECT-TYPE
    SYNTAX       CounterBasedGauge64
    MAX-ACCESS   read-only
    STATUS       current
    DESCRIPTION  "IBG1 blade 2 rcvd length errors
                  (errors/s)"
    ::= { perimetaGlobalStatsEntry 1026 }

  globalStatIBG1B2RcvdOverrunErrRate OBJECT-TYPE
    SYNTAX       CounterBasedGauge64
    MAX-ACCESS   read-only
    STATUS       current
    DESCRIPTION  "IBG1 blade 2 rcvd overrun errors
                  (errors/s)"
    ::= { perimetaGlobalStatsEntry 1027 }

  globalStatIBG1B2RcvdCRCErrRate OBJECT-TYPE
    SYNTAX       CounterBasedGauge64
    MAX-ACCESS   read-only
    STATUS       current
    DESCRIPTION  "IBG1 blade 2 rcvd CRC errors (errors/s)"
    ::= { perimetaGlobalStatsEntry 1028 }

  globalStatIBG1B2RcvdFrameErrRate OBJECT-TYPE
    SYNTAX       CounterBasedGauge64
    MAX-ACCESS   read-only
    STATUS       current
    DESCRIPTION  "IBG1 blade 2 rcvd frame errors
                  (errors/s)"
    ::= { perimetaGlobalStatsEntry 1029 }

  globalStatIBG1B2RcvdFifoFrameErrRate OBJECT-TYPE
    SYNTAX       CounterBasedGauge64
    MAX-ACCESS   read-only
    STATUS       current
    DESCRIPTION  "IBG1 blade 2 rcvd Fifo frame errors
                  (errors/s)"
    ::= { perimetaGlobalStatsEntry 1030 }

  globalStatIBG1B2RcvdMissedFrameErrRate OBJECT-TYPE
    SYNTAX       CounterBasedGauge64
    MAX-ACCESS   read-only
    STATUS       current
    DESCRIPTION  "IBG1 blade 2 rcvd missed frame errors
                  (errors/s)"
    ::= { perimetaGlobalStatsEntry 1031 }

  globalStatIBG1B2TransAbortErrRate OBJECT-TYPE
    SYNTAX       CounterBasedGauge64
    MAX-ACCESS   read-only
    STATUS       current
    DESCRIPTION  "IBG1 blade 2 transmission aborted errors
                  (errors/s)"
    ::= { perimetaGlobalStatsEntry 1032 }

  globalStatIBG1B2TransCarrierErrRate OBJECT-TYPE
    SYNTAX       CounterBasedGauge64
    MAX-ACCESS   read-only
    STATUS       current
    DESCRIPTION  "IBG1 blade 2 transmission carrier errors
                  (errors/s)"
    ::= { perimetaGlobalStatsEntry 1033 }

  globalStatIBG1B2TransFifoErrRate OBJECT-TYPE
    SYNTAX       CounterBasedGauge64
    MAX-ACCESS   read-only
    STATUS       current
    DESCRIPTION  "IBG1 blade 2 transmission Fifo errors
                  (errors/s)"
    ::= { perimetaGlobalStatsEntry 1034 }

  globalStatIBG1B2TransHtbtErrRate OBJECT-TYPE
    SYNTAX       CounterBasedGauge64
    MAX-ACCESS   read-only
    STATUS       current
    DESCRIPTION  "IBG1 blade 2 transmission heartbeat
                  errors (errors/s)"
    ::= { perimetaGlobalStatsEntry 1035 }

  globalStatIBG1B2TransWindowErrRate OBJECT-TYPE
    SYNTAX       CounterBasedGauge64
    MAX-ACCESS   read-only
    STATUS       current
    DESCRIPTION  "IBG1 blade 2 transmission window errors
                  (errors/s)"
    ::= { perimetaGlobalStatsEntry 1036 }

  globalStatIBG2B2RcvdPacketRate OBJECT-TYPE
    SYNTAX       CounterBasedGauge64
    MAX-ACCESS   read-only
    STATUS       current
    DESCRIPTION  "IBG2 blade 2 pkts rcvd (pkts/s)"
    ::= { perimetaGlobalStatsEntry 1037 }

  globalStatIBG2B2TransPacketRate OBJECT-TYPE
    SYNTAX       CounterBasedGauge64
    MAX-ACCESS   read-only
    STATUS       current
    DESCRIPTION  "IBG2 blade 2 pkts sent (pkts/s)"
    ::= { perimetaGlobalStatsEntry 1038 }

  globalStatIBG2B2RcvdByteRate OBJECT-TYPE
    SYNTAX       CounterBasedGauge64
    MAX-ACCESS   read-only
    STATUS       current
    DESCRIPTION  "IBG2 blade 2 bytes rcvd (bytes/s)"
    ::= { perimetaGlobalStatsEntry 1039 }

  globalStatIBG2B2TransByteRate OBJECT-TYPE
    SYNTAX       CounterBasedGauge64
    MAX-ACCESS   read-only
    STATUS       current
    DESCRIPTION  "IBG2 blade 2 bytes sent (bytes/s)"
    ::= { perimetaGlobalStatsEntry 1040 }

  globalStatIBG2B2RcvdErrorRate OBJECT-TYPE
    SYNTAX       CounterBasedGauge64
    MAX-ACCESS   read-only
    STATUS       current
    DESCRIPTION  "IBG2 blade 2 receive errors (errors/s)"
    ::= { perimetaGlobalStatsEntry 1041 }

  globalStatIBG2B2TransErrorRate OBJECT-TYPE
    SYNTAX       CounterBasedGauge64
    MAX-ACCESS   read-only
    STATUS       current
    DESCRIPTION  "IBG2 blade 2 transmission errors
                  (errors/s)"
    ::= { perimetaGlobalStatsEntry 1042 }

  globalStatIBG2B2RcvdDropPacketRate OBJECT-TYPE
    SYNTAX       CounterBasedGauge64
    MAX-ACCESS   read-only
    STATUS       current
    DESCRIPTION  "IBG2 blade 2 rcvd pkts dropped (pkts/s)"
    ::= { perimetaGlobalStatsEntry 1043 }

  globalStatIBG2B2TransDropPacketRate OBJECT-TYPE
    SYNTAX       CounterBasedGauge64
    MAX-ACCESS   read-only
    STATUS       current
    DESCRIPTION  "IBG2 blade 2 transmission pkts dropped
                  (pkts/s)"
    ::= { perimetaGlobalStatsEntry 1044 }

  globalStatIBG2B2RcvdMulticastRate OBJECT-TYPE
    SYNTAX       CounterBasedGauge64
    MAX-ACCESS   read-only
    STATUS       current
    DESCRIPTION  "IBG2 blade 2 multicast pkts rcvd
                  (pkts/s)"
    ::= { perimetaGlobalStatsEntry 1045 }

  globalStatIBG2B2TransCollisionRate OBJECT-TYPE
    SYNTAX       CounterBasedGauge64
    MAX-ACCESS   read-only
    STATUS       current
    DESCRIPTION  "IBG2 blade 2 transmission collisions per
                  second"
    ::= { perimetaGlobalStatsEntry 1046 }

  globalStatIBG2B2RcvdLengthErrRate OBJECT-TYPE
    SYNTAX       CounterBasedGauge64
    MAX-ACCESS   read-only
    STATUS       current
    DESCRIPTION  "IBG2 blade 2 rcvd length errors
                  (errors/s)"
    ::= { perimetaGlobalStatsEntry 1047 }

  globalStatIBG2B2RcvdOverrunErrRate OBJECT-TYPE
    SYNTAX       CounterBasedGauge64
    MAX-ACCESS   read-only
    STATUS       current
    DESCRIPTION  "IBG2 blade 2 rcvd overrun errors
                  (errors/s)"
    ::= { perimetaGlobalStatsEntry 1048 }

  globalStatIBG2B2RcvdCRCErrRate OBJECT-TYPE
    SYNTAX       CounterBasedGauge64
    MAX-ACCESS   read-only
    STATUS       current
    DESCRIPTION  "IBG2 blade 2 rcvd CRC errors (errors/s)"
    ::= { perimetaGlobalStatsEntry 1049 }

  globalStatIBG2B2RcvdFrameErrRate OBJECT-TYPE
    SYNTAX       CounterBasedGauge64
    MAX-ACCESS   read-only
    STATUS       current
    DESCRIPTION  "IBG2 blade 2 rcvd frame errors
                  (errors/s)"
    ::= { perimetaGlobalStatsEntry 1050 }

  globalStatIBG2B2RcvdFifoFrameErrRate OBJECT-TYPE
    SYNTAX       CounterBasedGauge64
    MAX-ACCESS   read-only
    STATUS       current
    DESCRIPTION  "IBG2 blade 2 rcvd Fifo frame errors
                  (errors/s)"
    ::= { perimetaGlobalStatsEntry 1051 }

  globalStatIBG2B2RcvdMissedFrameErrRate OBJECT-TYPE
    SYNTAX       CounterBasedGauge64
    MAX-ACCESS   read-only
    STATUS       current
    DESCRIPTION  "IBG2 blade 2 rcvd missed frame errors
                  (errors/s)"
    ::= { perimetaGlobalStatsEntry 1052 }

  globalStatIBG2B2TransAbortErrRate OBJECT-TYPE
    SYNTAX       CounterBasedGauge64
    MAX-ACCESS   read-only
    STATUS       current
    DESCRIPTION  "IBG2 blade 2 transmission aborted errors
                  (errors/s)"
    ::= { perimetaGlobalStatsEntry 1053 }

  globalStatIBG2B2TransCarrierErrRate OBJECT-TYPE
    SYNTAX       CounterBasedGauge64
    MAX-ACCESS   read-only
    STATUS       current
    DESCRIPTION  "IBG2 blade 2 transmission carrier errors
                  (errors/s)"
    ::= { perimetaGlobalStatsEntry 1054 }

  globalStatIBG2B2TransFifoErrRate OBJECT-TYPE
    SYNTAX       CounterBasedGauge64
    MAX-ACCESS   read-only
    STATUS       current
    DESCRIPTION  "IBG2 blade 2 transmission Fifo errors
                  (errors/s)"
    ::= { perimetaGlobalStatsEntry 1055 }

  globalStatIBG2B2TransHtbtErrRate OBJECT-TYPE
    SYNTAX       CounterBasedGauge64
    MAX-ACCESS   read-only
    STATUS       current
    DESCRIPTION  "IBG2 blade 2 transmission heartbeat
                  errors (errors/s)"
    ::= { perimetaGlobalStatsEntry 1056 }

  globalStatIBG2B2TransWindowErrRate OBJECT-TYPE
    SYNTAX       CounterBasedGauge64
    MAX-ACCESS   read-only
    STATUS       current
    DESCRIPTION  "IBG2 blade 2 transmission window errors
                  (errors/s)"
    ::= { perimetaGlobalStatsEntry 1057 }

  globalStatIPG1B2RcvdPacketRate OBJECT-TYPE
    SYNTAX       CounterBasedGauge64
    MAX-ACCESS   read-only
    STATUS       current
    DESCRIPTION  "IPG1 blade 2 pkts rcvd (pkts/s)"
    ::= { perimetaGlobalStatsEntry 1058 }

  globalStatIPG1B2TransPacketRate OBJECT-TYPE
    SYNTAX       CounterBasedGauge64
    MAX-ACCESS   read-only
    STATUS       current
    DESCRIPTION  "IPG1 blade 2 pkts sent (pkts/s)"
    ::= { perimetaGlobalStatsEntry 1059 }

  globalStatIPG1B2RcvdByteRate OBJECT-TYPE
    SYNTAX       CounterBasedGauge64
    MAX-ACCESS   read-only
    STATUS       current
    DESCRIPTION  "IPG1 blade 2 bytes rcvd (bytes/s)"
    ::= { perimetaGlobalStatsEntry 1060 }

  globalStatIPG1B2TransByteRate OBJECT-TYPE
    SYNTAX       CounterBasedGauge64
    MAX-ACCESS   read-only
    STATUS       current
    DESCRIPTION  "IPG1 blade 2 bytes sent (bytes/s)"
    ::= { perimetaGlobalStatsEntry 1061 }

  globalStatIPG1B2RcvdErrorRate OBJECT-TYPE
    SYNTAX       CounterBasedGauge64
    MAX-ACCESS   read-only
    STATUS       current
    DESCRIPTION  "IPG1 blade 2 receive errors (errors/s)"
    ::= { perimetaGlobalStatsEntry 1062 }

  globalStatIPG1B2TransErrorRate OBJECT-TYPE
    SYNTAX       CounterBasedGauge64
    MAX-ACCESS   read-only
    STATUS       current
    DESCRIPTION  "IPG1 blade 2 transmission errors
                  (errors/s)"
    ::= { perimetaGlobalStatsEntry 1063 }

  globalStatIPG1B2RcvdDropPacketRate OBJECT-TYPE
    SYNTAX       CounterBasedGauge64
    MAX-ACCESS   read-only
    STATUS       current
    DESCRIPTION  "IPG1 blade 2 rcvd pkts dropped (pkts/s)"
    ::= { perimetaGlobalStatsEntry 1064 }

  globalStatIPG1B2TransDropPacketRate OBJECT-TYPE
    SYNTAX       CounterBasedGauge64
    MAX-ACCESS   read-only
    STATUS       current
    DESCRIPTION  "IPG1 blade 2 transmission pkts dropped
                  (pkts/s)"
    ::= { perimetaGlobalStatsEntry 1065 }

  globalStatIPG1B2RcvdMulticastRate OBJECT-TYPE
    SYNTAX       CounterBasedGauge64
    MAX-ACCESS   read-only
    STATUS       current
    DESCRIPTION  "IPG1 blade 2 multicast pkts rcvd
                  (pkts/s)"
    ::= { perimetaGlobalStatsEntry 1066 }

  globalStatIPG1B2TransCollisionRate OBJECT-TYPE
    SYNTAX       CounterBasedGauge64
    MAX-ACCESS   read-only
    STATUS       current
    DESCRIPTION  "IPG1 blade 2 transmission collisions per
                  second"
    ::= { perimetaGlobalStatsEntry 1067 }

  globalStatIPG1B2RcvdLengthErrRate OBJECT-TYPE
    SYNTAX       CounterBasedGauge64
    MAX-ACCESS   read-only
    STATUS       current
    DESCRIPTION  "IPG1 blade 2 rcvd length errors
                  (errors/s)"
    ::= { perimetaGlobalStatsEntry 1068 }

  globalStatIPG1B2RcvdOverrunErrRate OBJECT-TYPE
    SYNTAX       CounterBasedGauge64
    MAX-ACCESS   read-only
    STATUS       current
    DESCRIPTION  "IPG1 blade 2 rcvd overrun errors
                  (errors/s)"
    ::= { perimetaGlobalStatsEntry 1069 }

  globalStatIPG1B2RcvdCRCErrRate OBJECT-TYPE
    SYNTAX       CounterBasedGauge64
    MAX-ACCESS   read-only
    STATUS       current
    DESCRIPTION  "IPG1 blade 2 rcvd CRC errors (errors/s)"
    ::= { perimetaGlobalStatsEntry 1070 }

  globalStatIPG1B2RcvdFrameErrRate OBJECT-TYPE
    SYNTAX       CounterBasedGauge64
    MAX-ACCESS   read-only
    STATUS       current
    DESCRIPTION  "IPG1 blade 2 rcvd frame errors
                  (errors/s)"
    ::= { perimetaGlobalStatsEntry 1071 }

  globalStatIPG1B2RcvdFifoFrameErrRate OBJECT-TYPE
    SYNTAX       CounterBasedGauge64
    MAX-ACCESS   read-only
    STATUS       current
    DESCRIPTION  "IPG1 blade 2 rcvd Fifo frame errors
                  (errors/s)"
    ::= { perimetaGlobalStatsEntry 1072 }

  globalStatIPG1B2RcvdMissedFrameErrRate OBJECT-TYPE
    SYNTAX       CounterBasedGauge64
    MAX-ACCESS   read-only
    STATUS       current
    DESCRIPTION  "IPG1 blade 2 rcvd missed frame errors
                  (errors/s)"
    ::= { perimetaGlobalStatsEntry 1073 }

  globalStatIPG1B2TransAbortErrRate OBJECT-TYPE
    SYNTAX       CounterBasedGauge64
    MAX-ACCESS   read-only
    STATUS       current
    DESCRIPTION  "IPG1 blade 2 transmission aborted errors
                  (errors/s)"
    ::= { perimetaGlobalStatsEntry 1074 }

  globalStatIPG1B2TransCarrierErrRate OBJECT-TYPE
    SYNTAX       CounterBasedGauge64
    MAX-ACCESS   read-only
    STATUS       current
    DESCRIPTION  "IPG1 blade 2 transmission carrier errors
                  (errors/s)"
    ::= { perimetaGlobalStatsEntry 1075 }

  globalStatIPG1B2TransFifoErrRate OBJECT-TYPE
    SYNTAX       CounterBasedGauge64
    MAX-ACCESS   read-only
    STATUS       current
    DESCRIPTION  "IPG1 blade 2 transmission Fifo errors
                  (errors/s)"
    ::= { perimetaGlobalStatsEntry 1076 }

  globalStatIPG1B2TransHtbtErrRate OBJECT-TYPE
    SYNTAX       CounterBasedGauge64
    MAX-ACCESS   read-only
    STATUS       current
    DESCRIPTION  "IPG1 blade 2 transmission heartbeat
                  errors (errors/s)"
    ::= { perimetaGlobalStatsEntry 1077 }

  globalStatIPG1B2TransWindowErrRate OBJECT-TYPE
    SYNTAX       CounterBasedGauge64
    MAX-ACCESS   read-only
    STATUS       current
    DESCRIPTION  "IPG1 blade 2 transmission window errors
                  (errors/s)"
    ::= { perimetaGlobalStatsEntry 1078 }

  globalStatIFXG1B2RcvdPacketRate OBJECT-TYPE
    SYNTAX       CounterBasedGauge64
    MAX-ACCESS   read-only
    STATUS       current
    DESCRIPTION  "IFXG1 blade 2 pkts rcvd (pkts/s)"
    ::= { perimetaGlobalStatsEntry 1079 }

  globalStatIFXG1B2TransPacketRate OBJECT-TYPE
    SYNTAX       CounterBasedGauge64
    MAX-ACCESS   read-only
    STATUS       current
    DESCRIPTION  "IFXG1 blade 2 pkts sent (pkts/s)"
    ::= { perimetaGlobalStatsEntry 1080 }

  globalStatIFXG1B2RcvdByteRate OBJECT-TYPE
    SYNTAX       CounterBasedGauge64
    MAX-ACCESS   read-only
    STATUS       current
    DESCRIPTION  "IFXG1 blade 2 bytes rcvd (bytes/s)"
    ::= { perimetaGlobalStatsEntry 1081 }

  globalStatIFXG1B2TransByteRate OBJECT-TYPE
    SYNTAX       CounterBasedGauge64
    MAX-ACCESS   read-only
    STATUS       current
    DESCRIPTION  "IFXG1 blade 2 bytes sent (bytes/s)"
    ::= { perimetaGlobalStatsEntry 1082 }

  globalStatIFXG1B2RcvdErrorRate OBJECT-TYPE
    SYNTAX       CounterBasedGauge64
    MAX-ACCESS   read-only
    STATUS       current
    DESCRIPTION  "IFXG1 blade 2 receive errors (errors/s)"
    ::= { perimetaGlobalStatsEntry 1083 }

  globalStatIFXG1B2TransErrorRate OBJECT-TYPE
    SYNTAX       CounterBasedGauge64
    MAX-ACCESS   read-only
    STATUS       current
    DESCRIPTION  "IFXG1 blade 2 transmission errors
                  (errors/s)"
    ::= { perimetaGlobalStatsEntry 1084 }

  globalStatIFXG1B2RcvdDropPacketRate OBJECT-TYPE
    SYNTAX       CounterBasedGauge64
    MAX-ACCESS   read-only
    STATUS       current
    DESCRIPTION  "IFXG1 blade 2 rcvd pkts dropped (pkts/s)"
    ::= { perimetaGlobalStatsEntry 1085 }

  globalStatIFXG1B2TransDropPacketRate OBJECT-TYPE
    SYNTAX       CounterBasedGauge64
    MAX-ACCESS   read-only
    STATUS       current
    DESCRIPTION  "IFXG1 blade 2 transmission pkts dropped
                  (pkts/s)"
    ::= { perimetaGlobalStatsEntry 1086 }

  globalStatIFXG1B2RcvdMulticastRate OBJECT-TYPE
    SYNTAX       CounterBasedGauge64
    MAX-ACCESS   read-only
    STATUS       current
    DESCRIPTION  "IFXG1 blade 2 multicast pkts rcvd
                  (pkts/s)"
    ::= { perimetaGlobalStatsEntry 1087 }

  globalStatIFXG1B2TransCollisionRate OBJECT-TYPE
    SYNTAX       CounterBasedGauge64
    MAX-ACCESS   read-only
    STATUS       current
    DESCRIPTION  "IFXG1 blade 2 transmission collisions
                  per second"
    ::= { perimetaGlobalStatsEntry 1088 }

  globalStatIFXG1B2RcvdLengthErrRate OBJECT-TYPE
    SYNTAX       CounterBasedGauge64
    MAX-ACCESS   read-only
    STATUS       current
    DESCRIPTION  "IFXG1 blade 2 rcvd length errors
                  (errors/s)"
    ::= { perimetaGlobalStatsEntry 1089 }

  globalStatIFXG1B2RcvdOverrunErrRate OBJECT-TYPE
    SYNTAX       CounterBasedGauge64
    MAX-ACCESS   read-only
    STATUS       current
    DESCRIPTION  "IFXG1 blade 2 rcvd overrun errors
                  (errors/s)"
    ::= { perimetaGlobalStatsEntry 1090 }

  globalStatIFXG1B2RcvdCRCErrRate OBJECT-TYPE
    SYNTAX       CounterBasedGauge64
    MAX-ACCESS   read-only
    STATUS       current
    DESCRIPTION  "IFXG1 blade 2 rcvd CRC errors (errors/s)"
    ::= { perimetaGlobalStatsEntry 1091 }

  globalStatIFXG1B2RcvdFrameErrRate OBJECT-TYPE
    SYNTAX       CounterBasedGauge64
    MAX-ACCESS   read-only
    STATUS       current
    DESCRIPTION  "IFXG1 blade 2 rcvd frame errors
                  (errors/s)"
    ::= { perimetaGlobalStatsEntry 1092 }

  globalStatIFXG1B2RcvdFifoFrameErrRate OBJECT-TYPE
    SYNTAX       CounterBasedGauge64
    MAX-ACCESS   read-only
    STATUS       current
    DESCRIPTION  "IFXG1 blade 2 rcvd Fifo frame errors
                  (errors/s)"
    ::= { perimetaGlobalStatsEntry 1093 }

  globalStatIFXG1B2RcvdMissedFrameErrRate OBJECT-TYPE
    SYNTAX       CounterBasedGauge64
    MAX-ACCESS   read-only
    STATUS       current
    DESCRIPTION  "IFXG1 blade 2 rcvd missed frame errors
                  (errors/s)"
    ::= { perimetaGlobalStatsEntry 1094 }

  globalStatIFXG1B2TransAbortErrRate OBJECT-TYPE
    SYNTAX       CounterBasedGauge64
    MAX-ACCESS   read-only
    STATUS       current
    DESCRIPTION  "IFXG1 blade 2 transmission aborted
                  errors (errors/s)"
    ::= { perimetaGlobalStatsEntry 1095 }

  globalStatIFXG1B2TransCarrierErrRate OBJECT-TYPE
    SYNTAX       CounterBasedGauge64
    MAX-ACCESS   read-only
    STATUS       current
    DESCRIPTION  "IFXG1 blade 2 transmission carrier
                  errors (errors/s)"
    ::= { perimetaGlobalStatsEntry 1096 }

  globalStatIFXG1B2TransFifoErrRate OBJECT-TYPE
    SYNTAX       CounterBasedGauge64
    MAX-ACCESS   read-only
    STATUS       current
    DESCRIPTION  "IFXG1 blade 2 transmission Fifo errors
                  (errors/s)"
    ::= { perimetaGlobalStatsEntry 1097 }

  globalStatIFXG1B2TransHtbtErrRate OBJECT-TYPE
    SYNTAX       CounterBasedGauge64
    MAX-ACCESS   read-only
    STATUS       current
    DESCRIPTION  "IFXG1 blade 2 transmission heartbeat
                  errors (errors/s)"
    ::= { perimetaGlobalStatsEntry 1098 }

  globalStatIFXG1B2TransWindowErrRate OBJECT-TYPE
    SYNTAX       CounterBasedGauge64
    MAX-ACCESS   read-only
    STATUS       current
    DESCRIPTION  "IFXG1 blade 2 transmission window errors
                  (errors/s)"
    ::= { perimetaGlobalStatsEntry 1099 }

  globalStatIFXG2B2RcvdPacketRate OBJECT-TYPE
    SYNTAX       CounterBasedGauge64
    MAX-ACCESS   read-only
    STATUS       current
    DESCRIPTION  "IFXG2 blade 2 pkts rcvd (pkts/s)"
    ::= { perimetaGlobalStatsEntry 1100 }

  globalStatIFXG2B2TransPacketRate OBJECT-TYPE
    SYNTAX       CounterBasedGauge64
    MAX-ACCESS   read-only
    STATUS       current
    DESCRIPTION  "IFXG2 blade 2 pkts sent (pkts/s)"
    ::= { perimetaGlobalStatsEntry 1101 }

  globalStatIFXG2B2RcvdByteRate OBJECT-TYPE
    SYNTAX       CounterBasedGauge64
    MAX-ACCESS   read-only
    STATUS       current
    DESCRIPTION  "IFXG2 blade 2 bytes rcvd (bytes/s)"
    ::= { perimetaGlobalStatsEntry 1102 }

  globalStatIFXG2B2TransByteRate OBJECT-TYPE
    SYNTAX       CounterBasedGauge64
    MAX-ACCESS   read-only
    STATUS       current
    DESCRIPTION  "IFXG2 blade 2 bytes sent (bytes/s)"
    ::= { perimetaGlobalStatsEntry 1103 }

  globalStatIFXG2B2RcvdErrorRate OBJECT-TYPE
    SYNTAX       CounterBasedGauge64
    MAX-ACCESS   read-only
    STATUS       current
    DESCRIPTION  "IFXG2 blade 2 receive errors (errors/s)"
    ::= { perimetaGlobalStatsEntry 1104 }

  globalStatIFXG2B2TransErrorRate OBJECT-TYPE
    SYNTAX       CounterBasedGauge64
    MAX-ACCESS   read-only
    STATUS       current
    DESCRIPTION  "IFXG2 blade 2 transmission errors
                  (errors/s)"
    ::= { perimetaGlobalStatsEntry 1105 }

  globalStatIFXG2B2RcvdDropPacketRate OBJECT-TYPE
    SYNTAX       CounterBasedGauge64
    MAX-ACCESS   read-only
    STATUS       current
    DESCRIPTION  "IFXG2 blade 2 rcvd pkts dropped (pkts/s)"
    ::= { perimetaGlobalStatsEntry 1106 }

  globalStatIFXG2B2TransDropPacketRate OBJECT-TYPE
    SYNTAX       CounterBasedGauge64
    MAX-ACCESS   read-only
    STATUS       current
    DESCRIPTION  "IFXG2 blade 2 transmission pkts dropped
                  (pkts/s)"
    ::= { perimetaGlobalStatsEntry 1107 }

  globalStatIFXG2B2RcvdMulticastRate OBJECT-TYPE
    SYNTAX       CounterBasedGauge64
    MAX-ACCESS   read-only
    STATUS       current
    DESCRIPTION  "IFXG2 blade 2 multicast pkts rcvd
                  (pkts/s)"
    ::= { perimetaGlobalStatsEntry 1108 }

  globalStatIFXG2B2TransCollisionRate OBJECT-TYPE
    SYNTAX       CounterBasedGauge64
    MAX-ACCESS   read-only
    STATUS       current
    DESCRIPTION  "IFXG2 blade 2 transmission collisions
                  per second"
    ::= { perimetaGlobalStatsEntry 1109 }

  globalStatIFXG2B2RcvdLengthErrRate OBJECT-TYPE
    SYNTAX       CounterBasedGauge64
    MAX-ACCESS   read-only
    STATUS       current
    DESCRIPTION  "IFXG2 blade 2 rcvd length errors
                  (errors/s)"
    ::= { perimetaGlobalStatsEntry 1110 }

  globalStatIFXG2B2RcvdOverrunErrRate OBJECT-TYPE
    SYNTAX       CounterBasedGauge64
    MAX-ACCESS   read-only
    STATUS       current
    DESCRIPTION  "IFXG2 blade 2 rcvd overrun errors
                  (errors/s)"
    ::= { perimetaGlobalStatsEntry 1111 }

  globalStatIFXG2B2RcvdCRCErrRate OBJECT-TYPE
    SYNTAX       CounterBasedGauge64
    MAX-ACCESS   read-only
    STATUS       current
    DESCRIPTION  "IFXG2 blade 2 rcvd CRC errors (errors/s)"
    ::= { perimetaGlobalStatsEntry 1112 }

  globalStatIFXG2B2RcvdFrameErrRate OBJECT-TYPE
    SYNTAX       CounterBasedGauge64
    MAX-ACCESS   read-only
    STATUS       current
    DESCRIPTION  "IFXG2 blade 2 rcvd frame errors
                  (errors/s)"
    ::= { perimetaGlobalStatsEntry 1113 }

  globalStatIFXG2B2RcvdFifoFrameErrRate OBJECT-TYPE
    SYNTAX       CounterBasedGauge64
    MAX-ACCESS   read-only
    STATUS       current
    DESCRIPTION  "IFXG2 blade 2 rcvd Fifo frame errors
                  (errors/s)"
    ::= { perimetaGlobalStatsEntry 1114 }

  globalStatIFXG2B2RcvdMissedFrameErrRate OBJECT-TYPE
    SYNTAX       CounterBasedGauge64
    MAX-ACCESS   read-only
    STATUS       current
    DESCRIPTION  "IFXG2 blade 2 rcvd missed frame errors
                  (errors/s)"
    ::= { perimetaGlobalStatsEntry 1115 }

  globalStatIFXG2B2TransAbortErrRate OBJECT-TYPE
    SYNTAX       CounterBasedGauge64
    MAX-ACCESS   read-only
    STATUS       current
    DESCRIPTION  "IFXG2 blade 2 transmission aborted
                  errors (errors/s)"
    ::= { perimetaGlobalStatsEntry 1116 }

  globalStatIFXG2B2TransCarrierErrRate OBJECT-TYPE
    SYNTAX       CounterBasedGauge64
    MAX-ACCESS   read-only
    STATUS       current
    DESCRIPTION  "IFXG2 blade 2 transmission carrier
                  errors (errors/s)"
    ::= { perimetaGlobalStatsEntry 1117 }

  globalStatIFXG2B2TransFifoErrRate OBJECT-TYPE
    SYNTAX       CounterBasedGauge64
    MAX-ACCESS   read-only
    STATUS       current
    DESCRIPTION  "IFXG2 blade 2 transmission Fifo errors
                  (errors/s)"
    ::= { perimetaGlobalStatsEntry 1118 }

  globalStatIFXG2B2TransHtbtErrRate OBJECT-TYPE
    SYNTAX       CounterBasedGauge64
    MAX-ACCESS   read-only
    STATUS       current
    DESCRIPTION  "IFXG2 blade 2 transmission heartbeat
                  errors (errors/s)"
    ::= { perimetaGlobalStatsEntry 1119 }

  globalStatIFXG2B2TransWindowErrRate OBJECT-TYPE
    SYNTAX       CounterBasedGauge64
    MAX-ACCESS   read-only
    STATUS       current
    DESCRIPTION  "IFXG2 blade 2 transmission window errors
                  (errors/s)"
    ::= { perimetaGlobalStatsEntry 1120 }

  globalStatRPXG1B2RcvdPacketRate OBJECT-TYPE
    SYNTAX       CounterBasedGauge64
    MAX-ACCESS   read-only
    STATUS       current
    DESCRIPTION  "RPXG1 blade 2 pkts rcvd (pkts/s)"
    ::= { perimetaGlobalStatsEntry 1121 }

  globalStatRPXG1B2TransPacketRate OBJECT-TYPE
    SYNTAX       CounterBasedGauge64
    MAX-ACCESS   read-only
    STATUS       current
    DESCRIPTION  "RPXG1 blade 2 pkts sent (pkts/s)"
    ::= { perimetaGlobalStatsEntry 1122 }

  globalStatRPXG1B2RcvdByteRate OBJECT-TYPE
    SYNTAX       CounterBasedGauge64
    MAX-ACCESS   read-only
    STATUS       current
    DESCRIPTION  "RPXG1 blade 2 bytes rcvd (bytes/s)"
    ::= { perimetaGlobalStatsEntry 1123 }

  globalStatRPXG1B2TransByteRate OBJECT-TYPE
    SYNTAX       CounterBasedGauge64
    MAX-ACCESS   read-only
    STATUS       current
    DESCRIPTION  "RPXG1 blade 2 bytes sent (bytes/s)"
    ::= { perimetaGlobalStatsEntry 1124 }

  globalStatRPXG1B2RcvdErrorRate OBJECT-TYPE
    SYNTAX       CounterBasedGauge64
    MAX-ACCESS   read-only
    STATUS       current
    DESCRIPTION  "RPXG1 blade 2 receive errors (errors/s)"
    ::= { perimetaGlobalStatsEntry 1125 }

  globalStatRPXG1B2TransErrorRate OBJECT-TYPE
    SYNTAX       CounterBasedGauge64
    MAX-ACCESS   read-only
    STATUS       current
    DESCRIPTION  "RPXG1 blade 2 transmission errors
                  (errors/s)"
    ::= { perimetaGlobalStatsEntry 1126 }

  globalStatRPXG1B2RcvdDropPacketRate OBJECT-TYPE
    SYNTAX       CounterBasedGauge64
    MAX-ACCESS   read-only
    STATUS       current
    DESCRIPTION  "RPXG1 blade 2 rcvd pkts dropped (pkts/s)"
    ::= { perimetaGlobalStatsEntry 1127 }

  globalStatRPXG1B2TransDropPacketRate OBJECT-TYPE
    SYNTAX       CounterBasedGauge64
    MAX-ACCESS   read-only
    STATUS       current
    DESCRIPTION  "RPXG1 blade 2 transmission pkts dropped
                  (pkts/s)"
    ::= { perimetaGlobalStatsEntry 1128 }

  globalStatRPXG1B2RcvdMulticastRate OBJECT-TYPE
    SYNTAX       CounterBasedGauge64
    MAX-ACCESS   read-only
    STATUS       current
    DESCRIPTION  "RPXG1 blade 2 multicast pkts rcvd
                  (pkts/s)"
    ::= { perimetaGlobalStatsEntry 1129 }

  globalStatRPXG1B2TransCollisionRate OBJECT-TYPE
    SYNTAX       CounterBasedGauge64
    MAX-ACCESS   read-only
    STATUS       current
    DESCRIPTION  "RPXG1 blade 2 transmission collisions
                  per second"
    ::= { perimetaGlobalStatsEntry 1130 }

  globalStatRPXG1B2RcvdLengthErrRate OBJECT-TYPE
    SYNTAX       CounterBasedGauge64
    MAX-ACCESS   read-only
    STATUS       current
    DESCRIPTION  "RPXG1 blade 2 rcvd length errors
                  (errors/s)"
    ::= { perimetaGlobalStatsEntry 1131 }

  globalStatRPXG1B2RcvdOverrunErrRate OBJECT-TYPE
    SYNTAX       CounterBasedGauge64
    MAX-ACCESS   read-only
    STATUS       current
    DESCRIPTION  "RPXG1 blade 2 rcvd overrun errors
                  (errors/s)"
    ::= { perimetaGlobalStatsEntry 1132 }

  globalStatRPXG1B2RcvdCRCErrRate OBJECT-TYPE
    SYNTAX       CounterBasedGauge64
    MAX-ACCESS   read-only
    STATUS       current
    DESCRIPTION  "RPXG1 blade 2 rcvd CRC errors (errors/s)"
    ::= { perimetaGlobalStatsEntry 1133 }

  globalStatRPXG1B2RcvdFrameErrRate OBJECT-TYPE
    SYNTAX       CounterBasedGauge64
    MAX-ACCESS   read-only
    STATUS       current
    DESCRIPTION  "RPXG1 blade 2 rcvd frame errors
                  (errors/s)"
    ::= { perimetaGlobalStatsEntry 1134 }

  globalStatRPXG1B2RcvdFifoFrameErrRate OBJECT-TYPE
    SYNTAX       CounterBasedGauge64
    MAX-ACCESS   read-only
    STATUS       current
    DESCRIPTION  "RPXG1 blade 2 rcvd Fifo frame errors
                  (errors/s)"
    ::= { perimetaGlobalStatsEntry 1135 }

  globalStatRPXG1B2RcvdMissedFrameErrRate OBJECT-TYPE
    SYNTAX       CounterBasedGauge64
    MAX-ACCESS   read-only
    STATUS       current
    DESCRIPTION  "RPXG1 blade 2 rcvd missed frame errors
                  (errors/s)"
    ::= { perimetaGlobalStatsEntry 1136 }

  globalStatRPXG1B2TransAbortErrRate OBJECT-TYPE
    SYNTAX       CounterBasedGauge64
    MAX-ACCESS   read-only
    STATUS       current
    DESCRIPTION  "RPXG1 blade 2 transmission aborted
                  errors (errors/s)"
    ::= { perimetaGlobalStatsEntry 1137 }

  globalStatRPXG1B2TransCarrierErrRate OBJECT-TYPE
    SYNTAX       CounterBasedGauge64
    MAX-ACCESS   read-only
    STATUS       current
    DESCRIPTION  "RPXG1 blade 2 transmission carrier
                  errors (errors/s)"
    ::= { perimetaGlobalStatsEntry 1138 }

  globalStatRPXG1B2TransFifoErrRate OBJECT-TYPE
    SYNTAX       CounterBasedGauge64
    MAX-ACCESS   read-only
    STATUS       current
    DESCRIPTION  "RPXG1 blade 2 transmission Fifo errors
                  (errors/s)"
    ::= { perimetaGlobalStatsEntry 1139 }

  globalStatRPXG1B2TransHtbtErrRate OBJECT-TYPE
    SYNTAX       CounterBasedGauge64
    MAX-ACCESS   read-only
    STATUS       current
    DESCRIPTION  "RPXG1 blade 2 transmission heartbeat
                  errors (errors/s)"
    ::= { perimetaGlobalStatsEntry 1140 }

  globalStatRPXG1B2TransWindowErrRate OBJECT-TYPE
    SYNTAX       CounterBasedGauge64
    MAX-ACCESS   read-only
    STATUS       current
    DESCRIPTION  "RPXG1 blade 2 transmission window errors
                  (errors/s)"
    ::= { perimetaGlobalStatsEntry 1141 }

  globalStatRPXG2B2RcvdPacketRate OBJECT-TYPE
    SYNTAX       CounterBasedGauge64
    MAX-ACCESS   read-only
    STATUS       current
    DESCRIPTION  "RPXG2 blade 2 pkts rcvd (pkts/s)"
    ::= { perimetaGlobalStatsEntry 1142 }

  globalStatRPXG2B2TransPacketRate OBJECT-TYPE
    SYNTAX       CounterBasedGauge64
    MAX-ACCESS   read-only
    STATUS       current
    DESCRIPTION  "RPXG2 blade 2 pkts sent (pkts/s)"
    ::= { perimetaGlobalStatsEntry 1143 }

  globalStatRPXG2B2RcvdByteRate OBJECT-TYPE
    SYNTAX       CounterBasedGauge64
    MAX-ACCESS   read-only
    STATUS       current
    DESCRIPTION  "RPXG2 blade 2 bytes rcvd (bytes/s)"
    ::= { perimetaGlobalStatsEntry 1144 }

  globalStatRPXG2B2TransByteRate OBJECT-TYPE
    SYNTAX       CounterBasedGauge64
    MAX-ACCESS   read-only
    STATUS       current
    DESCRIPTION  "RPXG2 blade 2 bytes sent (bytes/s)"
    ::= { perimetaGlobalStatsEntry 1145 }

  globalStatRPXG2B2RcvdErrorRate OBJECT-TYPE
    SYNTAX       CounterBasedGauge64
    MAX-ACCESS   read-only
    STATUS       current
    DESCRIPTION  "RPXG2 blade 2 receive errors (errors/s)"
    ::= { perimetaGlobalStatsEntry 1146 }

  globalStatRPXG2B2TransErrorRate OBJECT-TYPE
    SYNTAX       CounterBasedGauge64
    MAX-ACCESS   read-only
    STATUS       current
    DESCRIPTION  "RPXG2 blade 2 transmission errors
                  (errors/s)"
    ::= { perimetaGlobalStatsEntry 1147 }

  globalStatRPXG2B2RcvdDropPacketRate OBJECT-TYPE
    SYNTAX       CounterBasedGauge64
    MAX-ACCESS   read-only
    STATUS       current
    DESCRIPTION  "RPXG2 blade 2 rcvd pkts dropped (pkts/s)"
    ::= { perimetaGlobalStatsEntry 1148 }

  globalStatRPXG2B2TransDropPacketRate OBJECT-TYPE
    SYNTAX       CounterBasedGauge64
    MAX-ACCESS   read-only
    STATUS       current
    DESCRIPTION  "RPXG2 blade 2 transmission pkts dropped
                  (pkts/s)"
    ::= { perimetaGlobalStatsEntry 1149 }

  globalStatRPXG2B2RcvdMulticastRate OBJECT-TYPE
    SYNTAX       CounterBasedGauge64
    MAX-ACCESS   read-only
    STATUS       current
    DESCRIPTION  "RPXG2 blade 2 multicast pkts rcvd
                  (pkts/s)"
    ::= { perimetaGlobalStatsEntry 1150 }

  globalStatRPXG2B2TransCollisionRate OBJECT-TYPE
    SYNTAX       CounterBasedGauge64
    MAX-ACCESS   read-only
    STATUS       current
    DESCRIPTION  "RPXG2 blade 2 transmission collisions
                  per second"
    ::= { perimetaGlobalStatsEntry 1151 }

  globalStatRPXG2B2RcvdLengthErrRate OBJECT-TYPE
    SYNTAX       CounterBasedGauge64
    MAX-ACCESS   read-only
    STATUS       current
    DESCRIPTION  "RPXG2 blade 2 rcvd length errors
                  (errors/s)"
    ::= { perimetaGlobalStatsEntry 1152 }

  globalStatRPXG2B2RcvdOverrunErrRate OBJECT-TYPE
    SYNTAX       CounterBasedGauge64
    MAX-ACCESS   read-only
    STATUS       current
    DESCRIPTION  "RPXG2 blade 2 rcvd overrun errors
                  (errors/s)"
    ::= { perimetaGlobalStatsEntry 1153 }

  globalStatRPXG2B2RcvdCRCErrRate OBJECT-TYPE
    SYNTAX       CounterBasedGauge64
    MAX-ACCESS   read-only
    STATUS       current
    DESCRIPTION  "RPXG2 blade 2 rcvd CRC errors (errors/s)"
    ::= { perimetaGlobalStatsEntry 1154 }

  globalStatRPXG2B2RcvdFrameErrRate OBJECT-TYPE
    SYNTAX       CounterBasedGauge64
    MAX-ACCESS   read-only
    STATUS       current
    DESCRIPTION  "RPXG2 blade 2 rcvd frame errors
                  (errors/s)"
    ::= { perimetaGlobalStatsEntry 1155 }

  globalStatRPXG2B2RcvdFifoFrameErrRate OBJECT-TYPE
    SYNTAX       CounterBasedGauge64
    MAX-ACCESS   read-only
    STATUS       current
    DESCRIPTION  "RPXG2 blade 2 rcvd Fifo frame errors
                  (errors/s)"
    ::= { perimetaGlobalStatsEntry 1156 }

  globalStatRPXG2B2RcvdMissedFrameErrRate OBJECT-TYPE
    SYNTAX       CounterBasedGauge64
    MAX-ACCESS   read-only
    STATUS       current
    DESCRIPTION  "RPXG2 blade 2 rcvd missed frame errors
                  (errors/s)"
    ::= { perimetaGlobalStatsEntry 1157 }

  globalStatRPXG2B2TransAbortErrRate OBJECT-TYPE
    SYNTAX       CounterBasedGauge64
    MAX-ACCESS   read-only
    STATUS       current
    DESCRIPTION  "RPXG2 blade 2 transmission aborted
                  errors (errors/s)"
    ::= { perimetaGlobalStatsEntry 1158 }

  globalStatRPXG2B2TransCarrierErrRate OBJECT-TYPE
    SYNTAX       CounterBasedGauge64
    MAX-ACCESS   read-only
    STATUS       current
    DESCRIPTION  "RPXG2 blade 2 transmission carrier
                  errors (errors/s)"
    ::= { perimetaGlobalStatsEntry 1159 }

  globalStatRPXG2B2TransFifoErrRate OBJECT-TYPE
    SYNTAX       CounterBasedGauge64
    MAX-ACCESS   read-only
    STATUS       current
    DESCRIPTION  "RPXG2 blade 2 transmission Fifo errors
                  (errors/s)"
    ::= { perimetaGlobalStatsEntry 1160 }

  globalStatRPXG2B2TransHtbtErrRate OBJECT-TYPE
    SYNTAX       CounterBasedGauge64
    MAX-ACCESS   read-only
    STATUS       current
    DESCRIPTION  "RPXG2 blade 2 transmission heartbeat
                  errors (errors/s)"
    ::= { perimetaGlobalStatsEntry 1161 }

  globalStatRPXG2B2TransWindowErrRate OBJECT-TYPE
    SYNTAX       CounterBasedGauge64
    MAX-ACCESS   read-only
    STATUS       current
    DESCRIPTION  "RPXG2 blade 2 transmission window errors
                  (errors/s)"
    ::= { perimetaGlobalStatsEntry 1162 }

  globalStatRPXG3B2RcvdPacketRate OBJECT-TYPE
    SYNTAX       CounterBasedGauge64
    MAX-ACCESS   read-only
    STATUS       current
    DESCRIPTION  "RPXG3 blade 2 pkts rcvd (pkts/s)"
    ::= { perimetaGlobalStatsEntry 1163 }

  globalStatRPXG3B2TransPacketRate OBJECT-TYPE
    SYNTAX       CounterBasedGauge64
    MAX-ACCESS   read-only
    STATUS       current
    DESCRIPTION  "RPXG3 blade 2 pkts sent (pkts/s)"
    ::= { perimetaGlobalStatsEntry 1164 }

  globalStatRPXG3B2RcvdByteRate OBJECT-TYPE
    SYNTAX       CounterBasedGauge64
    MAX-ACCESS   read-only
    STATUS       current
    DESCRIPTION  "RPXG3 blade 2 bytes rcvd (bytes/s)"
    ::= { perimetaGlobalStatsEntry 1165 }

  globalStatRPXG3B2TransByteRate OBJECT-TYPE
    SYNTAX       CounterBasedGauge64
    MAX-ACCESS   read-only
    STATUS       current
    DESCRIPTION  "RPXG3 blade 2 bytes sent (bytes/s)"
    ::= { perimetaGlobalStatsEntry 1166 }

  globalStatRPXG3B2RcvdErrorRate OBJECT-TYPE
    SYNTAX       CounterBasedGauge64
    MAX-ACCESS   read-only
    STATUS       current
    DESCRIPTION  "RPXG3 blade 2 receive errors (errors/s)"
    ::= { perimetaGlobalStatsEntry 1167 }

  globalStatRPXG3B2TransErrorRate OBJECT-TYPE
    SYNTAX       CounterBasedGauge64
    MAX-ACCESS   read-only
    STATUS       current
    DESCRIPTION  "RPXG3 blade 2 transmission errors
                  (errors/s)"
    ::= { perimetaGlobalStatsEntry 1168 }

  globalStatRPXG3B2RcvdDropPacketRate OBJECT-TYPE
    SYNTAX       CounterBasedGauge64
    MAX-ACCESS   read-only
    STATUS       current
    DESCRIPTION  "RPXG3 blade 2 rcvd pkts dropped (pkts/s)"
    ::= { perimetaGlobalStatsEntry 1169 }

  globalStatRPXG3B2TransDropPacketRate OBJECT-TYPE
    SYNTAX       CounterBasedGauge64
    MAX-ACCESS   read-only
    STATUS       current
    DESCRIPTION  "RPXG3 blade 2 transmission pkts dropped
                  (pkts/s)"
    ::= { perimetaGlobalStatsEntry 1170 }

  globalStatRPXG3B2RcvdMulticastRate OBJECT-TYPE
    SYNTAX       CounterBasedGauge64
    MAX-ACCESS   read-only
    STATUS       current
    DESCRIPTION  "RPXG3 blade 2 multicast pkts rcvd
                  (pkts/s)"
    ::= { perimetaGlobalStatsEntry 1171 }

  globalStatRPXG3B2TransCollisionRate OBJECT-TYPE
    SYNTAX       CounterBasedGauge64
    MAX-ACCESS   read-only
    STATUS       current
    DESCRIPTION  "RPXG3 blade 2 transmission collisions
                  per second"
    ::= { perimetaGlobalStatsEntry 1172 }

  globalStatRPXG3B2RcvdLengthErrRate OBJECT-TYPE
    SYNTAX       CounterBasedGauge64
    MAX-ACCESS   read-only
    STATUS       current
    DESCRIPTION  "RPXG3 blade 2 rcvd length errors
                  (errors/s)"
    ::= { perimetaGlobalStatsEntry 1173 }

  globalStatRPXG3B2RcvdOverrunErrRate OBJECT-TYPE
    SYNTAX       CounterBasedGauge64
    MAX-ACCESS   read-only
    STATUS       current
    DESCRIPTION  "RPXG3 blade 2 rcvd overrun errors
                  (errors/s)"
    ::= { perimetaGlobalStatsEntry 1174 }

  globalStatRPXG3B2RcvdCRCErrRate OBJECT-TYPE
    SYNTAX       CounterBasedGauge64
    MAX-ACCESS   read-only
    STATUS       current
    DESCRIPTION  "RPXG3 blade 2 rcvd CRC errors (errors/s)"
    ::= { perimetaGlobalStatsEntry 1175 }

  globalStatRPXG3B2RcvdFrameErrRate OBJECT-TYPE
    SYNTAX       CounterBasedGauge64
    MAX-ACCESS   read-only
    STATUS       current
    DESCRIPTION  "RPXG3 blade 2 rcvd frame errors
                  (errors/s)"
    ::= { perimetaGlobalStatsEntry 1176 }

  globalStatRPXG3B2RcvdFifoFrameErrRate OBJECT-TYPE
    SYNTAX       CounterBasedGauge64
    MAX-ACCESS   read-only
    STATUS       current
    DESCRIPTION  "RPXG3 blade 2 rcvd Fifo frame errors
                  (errors/s)"
    ::= { perimetaGlobalStatsEntry 1177 }

  globalStatRPXG3B2RcvdMissedFrameErrRate OBJECT-TYPE
    SYNTAX       CounterBasedGauge64
    MAX-ACCESS   read-only
    STATUS       current
    DESCRIPTION  "RPXG3 blade 2 rcvd missed frame errors
                  (errors/s)"
    ::= { perimetaGlobalStatsEntry 1178 }

  globalStatRPXG3B2TransAbortErrRate OBJECT-TYPE
    SYNTAX       CounterBasedGauge64
    MAX-ACCESS   read-only
    STATUS       current
    DESCRIPTION  "RPXG3 blade 2 transmission aborted
                  errors (errors/s)"
    ::= { perimetaGlobalStatsEntry 1179 }

  globalStatRPXG3B2TransCarrierErrRate OBJECT-TYPE
    SYNTAX       CounterBasedGauge64
    MAX-ACCESS   read-only
    STATUS       current
    DESCRIPTION  "RPXG3 blade 2 transmission carrier
                  errors (errors/s)"
    ::= { perimetaGlobalStatsEntry 1180 }

  globalStatRPXG3B2TransFifoErrRate OBJECT-TYPE
    SYNTAX       CounterBasedGauge64
    MAX-ACCESS   read-only
    STATUS       current
    DESCRIPTION  "RPXG3 blade 2 transmission Fifo errors
                  (errors/s)"
    ::= { perimetaGlobalStatsEntry 1181 }

  globalStatRPXG3B2TransHtbtErrRate OBJECT-TYPE
    SYNTAX       CounterBasedGauge64
    MAX-ACCESS   read-only
    STATUS       current
    DESCRIPTION  "RPXG3 blade 2 transmission heartbeat
                  errors (errors/s)"
    ::= { perimetaGlobalStatsEntry 1182 }

  globalStatRPXG3B2TransWindowErrRate OBJECT-TYPE
    SYNTAX       CounterBasedGauge64
    MAX-ACCESS   read-only
    STATUS       current
    DESCRIPTION  "RPXG3 blade 2 transmission window errors
                  (errors/s)"
    ::= { perimetaGlobalStatsEntry 1183 }

  globalStatRPXG4B2RcvdPacketRate OBJECT-TYPE
    SYNTAX       CounterBasedGauge64
    MAX-ACCESS   read-only
    STATUS       current
    DESCRIPTION  "RPXG4 blade 2 pkts rcvd (pkts/s)"
    ::= { perimetaGlobalStatsEntry 1184 }

  globalStatRPXG4B2TransPacketRate OBJECT-TYPE
    SYNTAX       CounterBasedGauge64
    MAX-ACCESS   read-only
    STATUS       current
    DESCRIPTION  "RPXG4 blade 2 pkts sent (pkts/s)"
    ::= { perimetaGlobalStatsEntry 1185 }

  globalStatRPXG4B2RcvdByteRate OBJECT-TYPE
    SYNTAX       CounterBasedGauge64
    MAX-ACCESS   read-only
    STATUS       current
    DESCRIPTION  "RPXG4 blade 2 bytes rcvd (bytes/s)"
    ::= { perimetaGlobalStatsEntry 1186 }

  globalStatRPXG4B2TransByteRate OBJECT-TYPE
    SYNTAX       CounterBasedGauge64
    MAX-ACCESS   read-only
    STATUS       current
    DESCRIPTION  "RPXG4 blade 2 bytes sent (bytes/s)"
    ::= { perimetaGlobalStatsEntry 1187 }

  globalStatRPXG4B2RcvdErrorRate OBJECT-TYPE
    SYNTAX       CounterBasedGauge64
    MAX-ACCESS   read-only
    STATUS       current
    DESCRIPTION  "RPXG4 blade 2 receive errors (errors/s)"
    ::= { perimetaGlobalStatsEntry 1188 }

  globalStatRPXG4B2TransErrorRate OBJECT-TYPE
    SYNTAX       CounterBasedGauge64
    MAX-ACCESS   read-only
    STATUS       current
    DESCRIPTION  "RPXG4 blade 2 transmission errors
                  (errors/s)"
    ::= { perimetaGlobalStatsEntry 1189 }

  globalStatRPXG4B2RcvdDropPacketRate OBJECT-TYPE
    SYNTAX       CounterBasedGauge64
    MAX-ACCESS   read-only
    STATUS       current
    DESCRIPTION  "RPXG4 blade 2 rcvd pkts dropped (pkts/s)"
    ::= { perimetaGlobalStatsEntry 1190 }

  globalStatRPXG4B2TransDropPacketRate OBJECT-TYPE
    SYNTAX       CounterBasedGauge64
    MAX-ACCESS   read-only
    STATUS       current
    DESCRIPTION  "RPXG4 blade 2 transmission pkts dropped
                  (pkts/s)"
    ::= { perimetaGlobalStatsEntry 1191 }

  globalStatRPXG4B2RcvdMulticastRate OBJECT-TYPE
    SYNTAX       CounterBasedGauge64
    MAX-ACCESS   read-only
    STATUS       current
    DESCRIPTION  "RPXG4 blade 2 multicast pkts rcvd
                  (pkts/s)"
    ::= { perimetaGlobalStatsEntry 1192 }

  globalStatRPXG4B2TransCollisionRate OBJECT-TYPE
    SYNTAX       CounterBasedGauge64
    MAX-ACCESS   read-only
    STATUS       current
    DESCRIPTION  "RPXG4 blade 2 transmission collisions
                  per second"
    ::= { perimetaGlobalStatsEntry 1193 }

  globalStatRPXG4B2RcvdLengthErrRate OBJECT-TYPE
    SYNTAX       CounterBasedGauge64
    MAX-ACCESS   read-only
    STATUS       current
    DESCRIPTION  "RPXG4 blade 2 rcvd length errors
                  (errors/s)"
    ::= { perimetaGlobalStatsEntry 1194 }

  globalStatRPXG4B2RcvdOverrunErrRate OBJECT-TYPE
    SYNTAX       CounterBasedGauge64
    MAX-ACCESS   read-only
    STATUS       current
    DESCRIPTION  "RPXG4 blade 2 rcvd overrun errors
                  (errors/s)"
    ::= { perimetaGlobalStatsEntry 1195 }

  globalStatRPXG4B2RcvdCRCErrRate OBJECT-TYPE
    SYNTAX       CounterBasedGauge64
    MAX-ACCESS   read-only
    STATUS       current
    DESCRIPTION  "RPXG4 blade 2 rcvd CRC errors (errors/s)"
    ::= { perimetaGlobalStatsEntry 1196 }

  globalStatRPXG4B2RcvdFrameErrRate OBJECT-TYPE
    SYNTAX       CounterBasedGauge64
    MAX-ACCESS   read-only
    STATUS       current
    DESCRIPTION  "RPXG4 blade 2 rcvd frame errors
                  (errors/s)"
    ::= { perimetaGlobalStatsEntry 1197 }

  globalStatRPXG4B2RcvdFifoFrameErrRate OBJECT-TYPE
    SYNTAX       CounterBasedGauge64
    MAX-ACCESS   read-only
    STATUS       current
    DESCRIPTION  "RPXG4 blade 2 rcvd Fifo frame errors
                  (errors/s)"
    ::= { perimetaGlobalStatsEntry 1198 }

  globalStatRPXG4B2RcvdMissedFrameErrRate OBJECT-TYPE
    SYNTAX       CounterBasedGauge64
    MAX-ACCESS   read-only
    STATUS       current
    DESCRIPTION  "RPXG4 blade 2 rcvd missed frame errors
                  (errors/s)"
    ::= { perimetaGlobalStatsEntry 1199 }

  globalStatRPXG4B2TransAbortErrRate OBJECT-TYPE
    SYNTAX       CounterBasedGauge64
    MAX-ACCESS   read-only
    STATUS       current
    DESCRIPTION  "RPXG4 blade 2 transmission aborted
                  errors (errors/s)"
    ::= { perimetaGlobalStatsEntry 1200 }

  globalStatRPXG4B2TransCarrierErrRate OBJECT-TYPE
    SYNTAX       CounterBasedGauge64
    MAX-ACCESS   read-only
    STATUS       current
    DESCRIPTION  "RPXG4 blade 2 transmission carrier
                  errors (errors/s)"
    ::= { perimetaGlobalStatsEntry 1201 }

  globalStatRPXG4B2TransFifoErrRate OBJECT-TYPE
    SYNTAX       CounterBasedGauge64
    MAX-ACCESS   read-only
    STATUS       current
    DESCRIPTION  "RPXG4 blade 2 transmission Fifo errors
                  (errors/s)"
    ::= { perimetaGlobalStatsEntry 1202 }

  globalStatRPXG4B2TransHtbtErrRate OBJECT-TYPE
    SYNTAX       CounterBasedGauge64
    MAX-ACCESS   read-only
    STATUS       current
    DESCRIPTION  "RPXG4 blade 2 transmission heartbeat
                  errors (errors/s)"
    ::= { perimetaGlobalStatsEntry 1203 }

  globalStatRPXG4B2TransWindowErrRate OBJECT-TYPE
    SYNTAX       CounterBasedGauge64
    MAX-ACCESS   read-only
    STATUS       current
    DESCRIPTION  "RPXG4 blade 2 transmission window errors
                  (errors/s)"
    ::= { perimetaGlobalStatsEntry 1204 }

  globalStatDSPPctPktDrop OBJECT-TYPE
    SYNTAX       CounterBasedGauge64
    UNITS        "/ 10000 %"
    MAX-ACCESS   read-only
    STATUS       current
    DESCRIPTION  "Percentage of total packets dropped by
                  DSPs (in the last period)"
    ::= { perimetaGlobalStatsEntry 1205 }

  globalStatActiveTranscTotal OBJECT-TYPE
    SYNTAX       CounterBasedGauge64
    MAX-ACCESS   read-only
    STATUS       current
    DESCRIPTION  "Active calls transcoding"
    ::= { perimetaGlobalStatsEntry 1206 }

  globalStatActiveTranscGroup1 OBJECT-TYPE
    SYNTAX       CounterBasedGauge64
    MAX-ACCESS   read-only
    STATUS       current
    DESCRIPTION  "Active calls transcoding with a codec in
                  group 1"
    ::= { perimetaGlobalStatsEntry 1207 }

  globalStatSIPTotalTransactions OBJECT-TYPE
    SYNTAX       CounterBasedGauge64
    MAX-ACCESS   read-only
    STATUS       current
    DESCRIPTION  "Total SIP transactions completed or in
                  progress"
    ::= { perimetaGlobalStatsEntry 1208 }

  globalStatPriority7SigPktsRcvd OBJECT-TYPE
    SYNTAX       CounterBasedGauge64
    MAX-ACCESS   read-only
    STATUS       current
    DESCRIPTION  "Total priority 7 signaling packets
                  received (last period)"
    ::= { perimetaGlobalStatsEntry 1209 }

  globalStatPriority7SigPktsRcvdRate OBJECT-TYPE
    SYNTAX       CounterBasedGauge64
    MAX-ACCESS   read-only
    STATUS       current
    DESCRIPTION  "Priority 7 signaling packets received
                  per second"
    ::= { perimetaGlobalStatsEntry 1210 }

  globalStatPriority7SigPktsAccptd OBJECT-TYPE
    SYNTAX       CounterBasedGauge64
    MAX-ACCESS   read-only
    STATUS       current
    DESCRIPTION  "Total priority 7 signaling packets
                  accepted (last period)"
    ::= { perimetaGlobalStatsEntry 1211 }

  globalStatPriority7SigPktsAccptdRate OBJECT-TYPE
    SYNTAX       CounterBasedGauge64
    MAX-ACCESS   read-only
    STATUS       current
    DESCRIPTION  "Priority 7 signaling packets accepted
                  per second"
    ::= { perimetaGlobalStatsEntry 1212 }

  globalStatPriority7SigPktsDropped OBJECT-TYPE
    SYNTAX       CounterBasedGauge64
    MAX-ACCESS   read-only
    STATUS       current
    DESCRIPTION  "Total priority 7 signaling packets
                  dropped (last period)"
    ::= { perimetaGlobalStatsEntry 1213 }

  globalStatPriority7SigPktsDroppedRate OBJECT-TYPE
    SYNTAX       CounterBasedGauge64
    MAX-ACCESS   read-only
    STATUS       current
    DESCRIPTION  "Priority 7 signaling packets dropped per
                  second"
    ::= { perimetaGlobalStatsEntry 1214 }

  globalStatPriority7SigBytesRcvd OBJECT-TYPE
    SYNTAX       CounterBasedGauge64
    MAX-ACCESS   read-only
    STATUS       current
    DESCRIPTION  "Total priority 7 signaling bytes
                  received (last period)"
    ::= { perimetaGlobalStatsEntry 1215 }

  globalStatPriority7SigBytesRcvdRate OBJECT-TYPE
    SYNTAX       CounterBasedGauge64
    MAX-ACCESS   read-only
    STATUS       current
    DESCRIPTION  "Priority 7 signaling bytes received per
                  second"
    ::= { perimetaGlobalStatsEntry 1216 }

  globalStatPriority7SigBytesAccptd OBJECT-TYPE
    SYNTAX       CounterBasedGauge64
    MAX-ACCESS   read-only
    STATUS       current
    DESCRIPTION  "Total priority 7 signaling bytes
                  accepted (last period)"
    ::= { perimetaGlobalStatsEntry 1217 }

  globalStatPriority7SigBytesAccptdRate OBJECT-TYPE
    SYNTAX       CounterBasedGauge64
    MAX-ACCESS   read-only
    STATUS       current
    DESCRIPTION  "Priority 7 signaling bytes accepted per
                  second"
    ::= { perimetaGlobalStatsEntry 1218 }

  globalStatPriority7SigBytesDropped OBJECT-TYPE
    SYNTAX       CounterBasedGauge64
    MAX-ACCESS   read-only
    STATUS       current
    DESCRIPTION  "Total priority 7 signaling bytes dropped
                  (last period)"
    ::= { perimetaGlobalStatsEntry 1219 }

  globalStatPriority7SigBytesDroppedRate OBJECT-TYPE
    SYNTAX       CounterBasedGauge64
    MAX-ACCESS   read-only
    STATUS       current
    DESCRIPTION  "Priority 7 signaling bytes dropped per
                  second"
    ::= { perimetaGlobalStatsEntry 1220 }

  globalStatPriority8SigPktsRcvd OBJECT-TYPE
    SYNTAX       CounterBasedGauge64
    MAX-ACCESS   read-only
    STATUS       current
    DESCRIPTION  "Total priority 8 signaling packets
                  received (last period)"
    ::= { perimetaGlobalStatsEntry 1221 }

  globalStatPriority8SigPktsRcvdRate OBJECT-TYPE
    SYNTAX       CounterBasedGauge64
    MAX-ACCESS   read-only
    STATUS       current
    DESCRIPTION  "Priority 8 signaling packets received
                  per second"
    ::= { perimetaGlobalStatsEntry 1222 }

  globalStatPriority8SigPktsAccptd OBJECT-TYPE
    SYNTAX       CounterBasedGauge64
    MAX-ACCESS   read-only
    STATUS       current
    DESCRIPTION  "Total priority 8 signaling packets
                  accepted (last period)"
    ::= { perimetaGlobalStatsEntry 1223 }

  globalStatPriority8SigPktsAccptdRate OBJECT-TYPE
    SYNTAX       CounterBasedGauge64
    MAX-ACCESS   read-only
    STATUS       current
    DESCRIPTION  "Priority 8 signaling packets accepted
                  per second"
    ::= { perimetaGlobalStatsEntry 1224 }

  globalStatPriority8SigPktsDropped OBJECT-TYPE
    SYNTAX       CounterBasedGauge64
    MAX-ACCESS   read-only
    STATUS       current
    DESCRIPTION  "Total priority 8 signaling packets
                  dropped (last period)"
    ::= { perimetaGlobalStatsEntry 1225 }

  globalStatPriority8SigPktsDroppedRate OBJECT-TYPE
    SYNTAX       CounterBasedGauge64
    MAX-ACCESS   read-only
    STATUS       current
    DESCRIPTION  "Priority 8 signaling packets dropped per
                  second"
    ::= { perimetaGlobalStatsEntry 1226 }

  globalStatPriority8SigBytesRcvd OBJECT-TYPE
    SYNTAX       CounterBasedGauge64
    MAX-ACCESS   read-only
    STATUS       current
    DESCRIPTION  "Total priority 8 signaling bytes
                  received (last period)"
    ::= { perimetaGlobalStatsEntry 1227 }

  globalStatPriority8SigBytesRcvdRate OBJECT-TYPE
    SYNTAX       CounterBasedGauge64
    MAX-ACCESS   read-only
    STATUS       current
    DESCRIPTION  "Priority 8 signaling bytes received per
                  second"
    ::= { perimetaGlobalStatsEntry 1228 }

  globalStatPriority8SigBytesAccptd OBJECT-TYPE
    SYNTAX       CounterBasedGauge64
    MAX-ACCESS   read-only
    STATUS       current
    DESCRIPTION  "Total priority 8 signaling bytes
                  accepted (last period)"
    ::= { perimetaGlobalStatsEntry 1229 }

  globalStatPriority8SigBytesAccptdRate OBJECT-TYPE
    SYNTAX       CounterBasedGauge64
    MAX-ACCESS   read-only
    STATUS       current
    DESCRIPTION  "Priority 8 signaling bytes accepted per
                  second"
    ::= { perimetaGlobalStatsEntry 1230 }

  globalStatPriority8SigBytesDropped OBJECT-TYPE
    SYNTAX       CounterBasedGauge64
    MAX-ACCESS   read-only
    STATUS       current
    DESCRIPTION  "Total priority 8 signaling bytes dropped
                  (last period)"
    ::= { perimetaGlobalStatsEntry 1231 }

  globalStatPriority8SigBytesDroppedRate OBJECT-TYPE
    SYNTAX       CounterBasedGauge64
    MAX-ACCESS   read-only
    STATUS       current
    DESCRIPTION  "Priority 8 signaling bytes dropped per
                  second"
    ::= { perimetaGlobalStatsEntry 1232 }

  globalStatDropClosingUdp OBJECT-TYPE
    SYNTAX       CounterBasedGauge64
    MAX-ACCESS   read-only
    STATUS       current
    DESCRIPTION  "UDP packet received on closing socket"
    ::= { perimetaGlobalStatsEntry 1233 }

  globalStatDropClosingTcp OBJECT-TYPE
    SYNTAX       CounterBasedGauge64
    MAX-ACCESS   read-only
    STATUS       current
    DESCRIPTION  "TCP packet received on closing socket"
    ::= { perimetaGlobalStatsEntry 1234 }

  globalStatDropClosingUdpRate OBJECT-TYPE
    SYNTAX       CounterBasedGauge64
    MAX-ACCESS   read-only
    STATUS       current
    DESCRIPTION  "UDP packet received on closing socket
                  (/s)"
    ::= { perimetaGlobalStatsEntry 1235 }

  globalStatDropClosingTcpRate OBJECT-TYPE
    SYNTAX       CounterBasedGauge64
    MAX-ACCESS   read-only
    STATUS       current
    DESCRIPTION  "TCP packet received on closing socket
                  (/s)"
    ::= { perimetaGlobalStatsEntry 1236 }

  globalStatCodecActiveTranscSILK16 OBJECT-TYPE
    SYNTAX       CounterBasedGauge64
    MAX-ACCESS   read-only
    STATUS       current
    DESCRIPTION  "Active calls transcoding with SILK/16000"
    ::= { perimetaGlobalStatsEntry 1237 }

  globalStatActiveTransrTotal OBJECT-TYPE
    SYNTAX       CounterBasedGauge64
    MAX-ACCESS   read-only
    STATUS       current
    DESCRIPTION  "Active calls transrating"
    ::= { perimetaGlobalStatsEntry 1238 }

  globalStatEmergencyRedirects OBJECT-TYPE
    SYNTAX       CounterBasedGauge64
    MAX-ACCESS   read-only
    STATUS       current
    DESCRIPTION  "Number of SIP INVITE requests responded
                  to with an emergency redirect"
    ::= { perimetaGlobalStatsEntry 1239 }

  globalStatCodecSILKBoards OBJECT-TYPE
    SYNTAX       CounterBasedGauge64
    MAX-ACCESS   read-only
    STATUS       current
    DESCRIPTION  "DSP boards with SILK support enabled"
    ::= { perimetaGlobalStatsEntry 1240 }

  globalStatCodecActiveTranscILBC OBJECT-TYPE
    SYNTAX       CounterBasedGauge64
    MAX-ACCESS   read-only
    STATUS       current
    DESCRIPTION  "Active calls transcoding with iLBC"
    ::= { perimetaGlobalStatsEntry 1241 }

  globalStataSRVCCTransfersOK OBJECT-TYPE
    SYNTAX       CounterBasedGauge64
    MAX-ACCESS   read-only
    STATUS       current
    DESCRIPTION  "Number of successful aSRVCC call
                  handovers"
    ::= { perimetaGlobalStatsEntry 1242 }

  globalStataSRVCCTransfersFailed OBJECT-TYPE
    SYNTAX       CounterBasedGauge64
    MAX-ACCESS   read-only
    STATUS       current
    DESCRIPTION  "Number of failed aSRVCC call handovers"
    ::= { perimetaGlobalStatsEntry 1243 }

  globalStatpreaSRVCCTransfersOK OBJECT-TYPE
    SYNTAX       CounterBasedGauge64
    MAX-ACCESS   read-only
    STATUS       current
    DESCRIPTION  "Number of successful pre-aSRVCC call
                  handovers"
    ::= { perimetaGlobalStatsEntry 1244 }

  globalStatpreaSRVCCTransfersFailed OBJECT-TYPE
    SYNTAX       CounterBasedGauge64
    MAX-ACCESS   read-only
    STATUS       current
    DESCRIPTION  "Number of failed pre-aSRVCC call
                  handovers"
    ::= { perimetaGlobalStatsEntry 1245 }

  globalStatActiveRecordedCalls OBJECT-TYPE
    SYNTAX       CounterBasedGauge64
    MAX-ACCESS   read-only
    STATUS       current
    DESCRIPTION  "Currently active recording calls"
    ::= { perimetaGlobalStatsEntry 1246 }

  globalStatFailedRecordingCallsPercent OBJECT-TYPE
    SYNTAX       CounterBasedGauge64
    UNITS        "/ 10000 %"
    MAX-ACCESS   read-only
    STATUS       current
    DESCRIPTION  "Total percentage of recording call setup
                  attempts failing"
    ::= { perimetaGlobalStatsEntry 1247 }

  globalStatFailedSRSRecordingCalls OBJECT-TYPE
    SYNTAX       CounterBasedGauge64
    UNITS        "/ 10000 %"
    MAX-ACCESS   read-only
    STATUS       current
    DESCRIPTION  "Percentage of recording calls failing
                  due to SRS rejection"
    ::= { perimetaGlobalStatsEntry 1248 }

  globalStatFailedFeatureRecordingCalls OBJECT-TYPE
    SYNTAX       CounterBasedGauge64
    UNITS        "/ 10000 %"
    MAX-ACCESS   read-only
    STATUS       current
    DESCRIPTION  "Percentage of recording calls failing
                  due to feature interactions"
    ::= { perimetaGlobalStatsEntry 1249 }

  globalStatFailedResourceRecordingCalls OBJECT-TYPE
    SYNTAX       CounterBasedGauge64
    UNITS        "/ 10000 %"
    MAX-ACCESS   read-only
    STATUS       current
    DESCRIPTION  "Percentage of recording calls failing
                  due to insufficient resources"
    ::= { perimetaGlobalStatsEntry 1250 }

  globalStatFailedLicenseRecordingCalls OBJECT-TYPE
    SYNTAX       CounterBasedGauge64
    UNITS        "/ 10000 %"
    MAX-ACCESS   read-only
    STATUS       current
    DESCRIPTION  "Percentage of recording calls failing
                  due to license limit"
    ::= { perimetaGlobalStatsEntry 1251 }

  globalStatCodecActiveTranscOPUS OBJECT-TYPE
    SYNTAX       CounterBasedGauge64
    MAX-ACCESS   read-only
    STATUS       current
    DESCRIPTION  "Active calls transcoding with OPUS"
    ::= { perimetaGlobalStatsEntry 1252 }

  globalStatTotalRecordedCalls OBJECT-TYPE
    SYNTAX       CounterBasedGauge64
    MAX-ACCESS   read-only
    STATUS       current
    DESCRIPTION  "Total recorded calls"
    ::= { perimetaGlobalStatsEntry 1253 }

  globalStatTotalAttemptedRecordedCalls OBJECT-TYPE
    SYNTAX       CounterBasedGauge64
    MAX-ACCESS   read-only
    STATUS       current
    DESCRIPTION  "Total number of attempted recorded calls"
    ::= { perimetaGlobalStatsEntry 1254 }

  globalStatActivePrecIWCalls OBJECT-TYPE
    SYNTAX       CounterBasedGauge64
    MAX-ACCESS   read-only
    STATUS       current
    DESCRIPTION  "Currently active preconditions
                  interworking calls"
    ::= { perimetaGlobalStatsEntry 1255 }

  alarmStatTotalAlarms OBJECT-TYPE
    SYNTAX       CounterBasedGauge64
    MAX-ACCESS   read-only
    STATUS       current
    DESCRIPTION  "Total Active Alarms"
    ::= { perimetaGlobalStatsEntry 1256 }

  alarmStatCriticalAlarms OBJECT-TYPE
    SYNTAX       CounterBasedGauge64
    MAX-ACCESS   read-only
    STATUS       current
    DESCRIPTION  "Total Active Critical Alarms"
    ::= { perimetaGlobalStatsEntry 1257 }

  alarmStatMajorAlarms OBJECT-TYPE
    SYNTAX       CounterBasedGauge64
    MAX-ACCESS   read-only
    STATUS       current
    DESCRIPTION  "Total Active Major Alarms"
    ::= { perimetaGlobalStatsEntry 1258 }

  alarmStatMinorAlarms OBJECT-TYPE
    SYNTAX       CounterBasedGauge64
    MAX-ACCESS   read-only
    STATUS       current
    DESCRIPTION  "Total Active Minor Alarms"
    ::= { perimetaGlobalStatsEntry 1259 }

  alarmStatInfoAlarms OBJECT-TYPE
    SYNTAX       CounterBasedGauge64
    MAX-ACCESS   read-only
    STATUS       current
    DESCRIPTION  "Total Active Info Alarms"
    ::= { perimetaGlobalStatsEntry 1260 }

  globalStatActivePNSubscribers OBJECT-TYPE
    SYNTAX       CounterBasedGauge64
    MAX-ACCESS   read-only
    STATUS       current
    DESCRIPTION  "Number of registered push-notification
                  subscribers"
    ::= { perimetaGlobalStatsEntry 1261 }

  globalStatISUPInterworkingCalls OBJECT-TYPE
    SYNTAX       CounterBasedGauge64
    MAX-ACCESS   read-only
    STATUS       current
    DESCRIPTION  "Current ISUP interworking calls"
    ::= { perimetaGlobalStatsEntry 1262 }

  globalStatPushNtfnReqSentCount OBJECT-TYPE
    SYNTAX       CounterBasedGauge64
    MAX-ACCESS   read-only
    STATUS       current
    DESCRIPTION  "Number of push notification requests
                  sent (in the last period)"
    ::= { perimetaGlobalStatsEntry 1263 }

  globalStatPushNtfnReqSentRate OBJECT-TYPE
    SYNTAX       CounterBasedGauge64
    MAX-ACCESS   read-only
    STATUS       current
    DESCRIPTION  "Rate of push notification requests sent
                  (msgs/s)"
    ::= { perimetaGlobalStatsEntry 1264 }

  globalStatPushNtfnOKRspRcvdCount OBJECT-TYPE
    SYNTAX       CounterBasedGauge64
    MAX-ACCESS   read-only
    STATUS       current
    DESCRIPTION  "Number of successful push notification
                  responses received (in the last period)"
    ::= { perimetaGlobalStatsEntry 1265 }

  globalStatPushNtfnOKRspRcvdRate OBJECT-TYPE
    SYNTAX       CounterBasedGauge64
    MAX-ACCESS   read-only
    STATUS       current
    DESCRIPTION  "Rate of successful push notification
                  responses received (msgs/s)"
    ::= { perimetaGlobalStatsEntry 1266 }

  globalStatPushNtfnFailedRspRcvdCount OBJECT-TYPE
    SYNTAX       CounterBasedGauge64
    MAX-ACCESS   read-only
    STATUS       current
    DESCRIPTION  "Number of failed push notification
                  responses received (in the last period)"
    ::= { perimetaGlobalStatsEntry 1267 }

  globalStatPushNtfnFailedRspRcvdRate OBJECT-TYPE
    SYNTAX       CounterBasedGauge64
    MAX-ACCESS   read-only
    STATUS       current
    DESCRIPTION  "Rate of failed push notification
                  responses received (msgs/s)"
    ::= { perimetaGlobalStatsEntry 1268 }

  globalStatPushNtfnTimeoutCount OBJECT-TYPE
    SYNTAX       CounterBasedGauge64
    MAX-ACCESS   read-only
    STATUS       current
    DESCRIPTION  "Number of push notification request
                  timeouts (in the last period)"
    ::= { perimetaGlobalStatsEntry 1269 }

  globalStatPushNtfnTimeoutRate OBJECT-TYPE
    SYNTAX       CounterBasedGauge64
    MAX-ACCESS   read-only
    STATUS       current
    DESCRIPTION  "Rate of push notification timeouts
                  (timeouts/s)"
    ::= { perimetaGlobalStatsEntry 1270 }

  globalStatPushNtfnConnectionErrorCount OBJECT-TYPE
    SYNTAX       CounterBasedGauge64
    MAX-ACCESS   read-only
    STATUS       current
    DESCRIPTION  "Number of connection errors to push
                  notification microservices (in the last
                  period)"
    ::= { perimetaGlobalStatsEntry 1271 }

  globalStatPushNtfnConnectionErrorRate OBJECT-TYPE
    SYNTAX       CounterBasedGauge64
    MAX-ACCESS   read-only
    STATUS       current
    DESCRIPTION  "Rate of connection errors to push
                  notification microservices (errors/s)"
    ::= { perimetaGlobalStatsEntry 1272 }

  globalStatPushNtfnNumConns OBJECT-TYPE
    SYNTAX       CounterBasedGauge64
    MAX-ACCESS   read-only
    STATUS       current
    DESCRIPTION  "Number of concurrent connections to push
                  notification microservices"
    ::= { perimetaGlobalStatsEntry 1273 }

  globalStatPushNtfnNumTrans OBJECT-TYPE
    SYNTAX       CounterBasedGauge64
    MAX-ACCESS   read-only
    STATUS       current
    DESCRIPTION  "Number of outstanding transactions with
                  push notification services"
    ::= { perimetaGlobalStatsEntry 1274 }

  globalStatPushNtfnAverageRTT OBJECT-TYPE
    SYNTAX       CounterBasedGauge64
    MAX-ACCESS   read-only
    STATUS       current
    DESCRIPTION  "Average round-trip-time (ms) to push
                  notification services over the last 10
                  seconds"
    ::= { perimetaGlobalStatsEntry 1275 }

  globalStatPriorityCallAttemptFailureRate OBJECT-TYPE
    SYNTAX       CounterBasedGauge64
    MAX-ACCESS   read-only
    STATUS       current
    DESCRIPTION  "Failed Priority call attempts per second"
    ::= { perimetaGlobalStatsEntry 1280 }

  globalStatSIPCongestionQPri00PktsAccepted OBJECT-TYPE
    SYNTAX       CounterBasedGauge64
    MAX-ACCESS   read-only
    STATUS       current
    DESCRIPTION  "Priority 0 SIP packets accepted by the
                  congestion queues (last period)"
    ::= { perimetaGlobalStatsEntry 1281 }

  globalStatSIPCongestionQPri00PktsDropped OBJECT-TYPE
    SYNTAX       CounterBasedGauge64
    MAX-ACCESS   read-only
    STATUS       current
    DESCRIPTION  "Priority 0 SIP packets rejected by the
                  congestion queues (last period)"
    ::= { perimetaGlobalStatsEntry 1282 }

  globalStatSIPCongestionQPri01PktsAccepted OBJECT-TYPE
    SYNTAX       CounterBasedGauge64
    MAX-ACCESS   read-only
    STATUS       current
    DESCRIPTION  "Priority 1 SIP packets accepted by the
                  congestion queues (last period)"
    ::= { perimetaGlobalStatsEntry 1283 }

  globalStatSIPCongestionQPri01PktsDropped OBJECT-TYPE
    SYNTAX       CounterBasedGauge64
    MAX-ACCESS   read-only
    STATUS       current
    DESCRIPTION  "Priority 1 SIP packets rejected by the
                  congestion queues (last period)"
    ::= { perimetaGlobalStatsEntry 1284 }

  globalStatSIPCongestionQPri02PktsAccepted OBJECT-TYPE
    SYNTAX       CounterBasedGauge64
    MAX-ACCESS   read-only
    STATUS       current
    DESCRIPTION  "Priority 2 SIP packets accepted by the
                  congestion queues (last period)"
    ::= { perimetaGlobalStatsEntry 1285 }

  globalStatSIPCongestionQPri02PktsDropped OBJECT-TYPE
    SYNTAX       CounterBasedGauge64
    MAX-ACCESS   read-only
    STATUS       current
    DESCRIPTION  "Priority 2 SIP packets rejected by the
                  congestion queues (last period)"
    ::= { perimetaGlobalStatsEntry 1286 }

  globalStatSIPCongestionQPri03PktsAccepted OBJECT-TYPE
    SYNTAX       CounterBasedGauge64
    MAX-ACCESS   read-only
    STATUS       current
    DESCRIPTION  "Priority 3 SIP packets accepted by the
                  congestion queues (last period)"
    ::= { perimetaGlobalStatsEntry 1287 }

  globalStatSIPCongestionQPri03PktsDropped OBJECT-TYPE
    SYNTAX       CounterBasedGauge64
    MAX-ACCESS   read-only
    STATUS       current
    DESCRIPTION  "Priority 3 SIP packets rejected by the
                  congestion queues (last period)"
    ::= { perimetaGlobalStatsEntry 1288 }

  globalStatSIPCongestionQPri04PktsAccepted OBJECT-TYPE
    SYNTAX       CounterBasedGauge64
    MAX-ACCESS   read-only
    STATUS       current
    DESCRIPTION  "Priority 4 SIP packets accepted by the
                  congestion queues (last period)"
    ::= { perimetaGlobalStatsEntry 1289 }

  globalStatSIPCongestionQPri04PktsDropped OBJECT-TYPE
    SYNTAX       CounterBasedGauge64
    MAX-ACCESS   read-only
    STATUS       current
    DESCRIPTION  "Priority 4 SIP packets rejected by the
                  congestion queues (last period)"
    ::= { perimetaGlobalStatsEntry 1290 }

  globalStatSIPCongestionQPri05PktsAccepted OBJECT-TYPE
    SYNTAX       CounterBasedGauge64
    MAX-ACCESS   read-only
    STATUS       current
    DESCRIPTION  "Priority 5 SIP packets accepted by the
                  congestion queues (last period)"
    ::= { perimetaGlobalStatsEntry 1291 }

  globalStatSIPCongestionQPri05PktsDropped OBJECT-TYPE
    SYNTAX       CounterBasedGauge64
    MAX-ACCESS   read-only
    STATUS       current
    DESCRIPTION  "Priority 5 SIP packets rejected by the
                  congestion queues (last period)"
    ::= { perimetaGlobalStatsEntry 1292 }

  globalStatSIPCongestionQPri06PktsAccepted OBJECT-TYPE
    SYNTAX       CounterBasedGauge64
    MAX-ACCESS   read-only
    STATUS       current
    DESCRIPTION  "Priority 6 SIP packets accepted by the
                  congestion queues (last period)"
    ::= { perimetaGlobalStatsEntry 1293 }

  globalStatSIPCongestionQPri06PktsDropped OBJECT-TYPE
    SYNTAX       CounterBasedGauge64
    MAX-ACCESS   read-only
    STATUS       current
    DESCRIPTION  "Priority 6 SIP packets rejected by the
                  congestion queues (last period)"
    ::= { perimetaGlobalStatsEntry 1294 }

  globalStatSIPCongestionQPri07PktsAccepted OBJECT-TYPE
    SYNTAX       CounterBasedGauge64
    MAX-ACCESS   read-only
    STATUS       current
    DESCRIPTION  "Priority 7 SIP packets accepted by the
                  congestion queues (last period)"
    ::= { perimetaGlobalStatsEntry 1295 }

  globalStatSIPCongestionQPri07PktsDropped OBJECT-TYPE
    SYNTAX       CounterBasedGauge64
    MAX-ACCESS   read-only
    STATUS       current
    DESCRIPTION  "Priority 7 SIP packets rejected by the
                  congestion queues (last period)"
    ::= { perimetaGlobalStatsEntry 1296 }

  globalStatSIPCongestionQPri08PktsAccepted OBJECT-TYPE
    SYNTAX       CounterBasedGauge64
    MAX-ACCESS   read-only
    STATUS       current
    DESCRIPTION  "Priority 8 SIP packets accepted by the
                  congestion queues (last period)"
    ::= { perimetaGlobalStatsEntry 1297 }

  globalStatSIPCongestionQPri08PktsDropped OBJECT-TYPE
    SYNTAX       CounterBasedGauge64
    MAX-ACCESS   read-only
    STATUS       current
    DESCRIPTION  "Priority 8 SIP packets rejected by the
                  congestion queues (last period)"
    ::= { perimetaGlobalStatsEntry 1298 }

  globalStatSIPCongestionQPri09PktsAccepted OBJECT-TYPE
    SYNTAX       CounterBasedGauge64
    MAX-ACCESS   read-only
    STATUS       current
    DESCRIPTION  "Priority 9 SIP packets accepted by the
                  congestion queues (last period)"
    ::= { perimetaGlobalStatsEntry 1299 }

  globalStatSIPCongestionQPri09PktsDropped OBJECT-TYPE
    SYNTAX       CounterBasedGauge64
    MAX-ACCESS   read-only
    STATUS       current
    DESCRIPTION  "Priority 9 SIP packets rejected by the
                  congestion queues (last period)"
    ::= { perimetaGlobalStatsEntry 1300 }

  globalStatSIPCongestionQPri10PktsAccepted OBJECT-TYPE
    SYNTAX       CounterBasedGauge64
    MAX-ACCESS   read-only
    STATUS       current
    DESCRIPTION  "Priority 10 SIP packets accepted by the
                  congestion queues (last period)"
    ::= { perimetaGlobalStatsEntry 1301 }

  globalStatSIPCongestionQPri10PktsDropped OBJECT-TYPE
    SYNTAX       CounterBasedGauge64
    MAX-ACCESS   read-only
    STATUS       current
    DESCRIPTION  "Priority 10 SIP packets rejected by the
                  congestion queues (last period)"
    ::= { perimetaGlobalStatsEntry 1302 }

  globalStatSIPCongestionQPri11PktsAccepted OBJECT-TYPE
    SYNTAX       CounterBasedGauge64
    MAX-ACCESS   read-only
    STATUS       current
    DESCRIPTION  "Priority 11 SIP packets accepted by the
                  congestion queues (last period)"
    ::= { perimetaGlobalStatsEntry 1303 }

  globalStatSIPCongestionQPri11PktsDropped OBJECT-TYPE
    SYNTAX       CounterBasedGauge64
    MAX-ACCESS   read-only
    STATUS       current
    DESCRIPTION  "Priority 11 SIP packets rejected by the
                  congestion queues (last period)"
    ::= { perimetaGlobalStatsEntry 1304 }

  globalStatSIPCongestionQPri12PktsAccepted OBJECT-TYPE
    SYNTAX       CounterBasedGauge64
    MAX-ACCESS   read-only
    STATUS       current
    DESCRIPTION  "Priority 12 SIP packets accepted by the
                  congestion queues (last period)"
    ::= { perimetaGlobalStatsEntry 1305 }

  globalStatSIPCongestionQPri12PktsDropped OBJECT-TYPE
    SYNTAX       CounterBasedGauge64
    MAX-ACCESS   read-only
    STATUS       current
    DESCRIPTION  "Priority 12 SIP packets rejected by the
                  congestion queues (last period)"
    ::= { perimetaGlobalStatsEntry 1306 }

  globalStatSIPCongestionQPri13PktsAccepted OBJECT-TYPE
    SYNTAX       CounterBasedGauge64
    MAX-ACCESS   read-only
    STATUS       current
    DESCRIPTION  "Priority 13 SIP packets accepted by the
                  congestion queues (last period)"
    ::= { perimetaGlobalStatsEntry 1307 }

  globalStatSIPCongestionQPri13PktsDropped OBJECT-TYPE
    SYNTAX       CounterBasedGauge64
    MAX-ACCESS   read-only
    STATUS       current
    DESCRIPTION  "Priority 13 SIP packets rejected by the
                  congestion queues (last period)"
    ::= { perimetaGlobalStatsEntry 1308 }

  globalStatSIPCongestionQPri14PktsAccepted OBJECT-TYPE
    SYNTAX       CounterBasedGauge64
    MAX-ACCESS   read-only
    STATUS       current
    DESCRIPTION  "Priority 14 SIP packets accepted by the
                  congestion queues (last period)"
    ::= { perimetaGlobalStatsEntry 1309 }

  globalStatSIPCongestionQPri14PktsDropped OBJECT-TYPE
    SYNTAX       CounterBasedGauge64
    MAX-ACCESS   read-only
    STATUS       current
    DESCRIPTION  "Priority 14 SIP packets rejected by the
                  congestion queues (last period)"
    ::= { perimetaGlobalStatsEntry 1310 }

  globalStatSIPCongestionQPri15PktsAccepted OBJECT-TYPE
    SYNTAX       CounterBasedGauge64
    MAX-ACCESS   read-only
    STATUS       current
    DESCRIPTION  "Priority 15 SIP packets accepted by the
                  congestion queues (last period)"
    ::= { perimetaGlobalStatsEntry 1311 }

  globalStatSIPCongestionQPri15PktsDropped OBJECT-TYPE
    SYNTAX       CounterBasedGauge64
    MAX-ACCESS   read-only
    STATUS       current
    DESCRIPTION  "Priority 15 SIP packets rejected by the
                  congestion queues (last period)"
    ::= { perimetaGlobalStatsEntry 1312 }

  globalStatSigningSucceededCount OBJECT-TYPE
    SYNTAX       CounterBasedGauge64
    MAX-ACCESS   read-only
    STATUS       current
    DESCRIPTION  "Number of call attempts with successful
                  signing (in the last period)"
    ::= { perimetaGlobalStatsEntry 1313 }

  globalStatSigningSucceededRate OBJECT-TYPE
    SYNTAX       CounterBasedGauge64
    MAX-ACCESS   read-only
    STATUS       current
    DESCRIPTION  "Rate of call attempts with successful
                  signing (calls/s)"
    ::= { perimetaGlobalStatsEntry 1314 }

  globalStatSigningRejectedCount OBJECT-TYPE
    SYNTAX       CounterBasedGauge64
    MAX-ACCESS   read-only
    STATUS       current
    DESCRIPTION  "Number of call attempts with signing
                  request rejected (in the last period)"
    ::= { perimetaGlobalStatsEntry 1315 }

  globalStatSigningRejectedRate OBJECT-TYPE
    SYNTAX       CounterBasedGauge64
    MAX-ACCESS   read-only
    STATUS       current
    DESCRIPTION  "Rate of call attempts with signing
                  request rejected (calls/s)"
    ::= { perimetaGlobalStatsEntry 1316 }

  globalStatSigningTimeoutCount OBJECT-TYPE
    SYNTAX       CounterBasedGauge64
    MAX-ACCESS   read-only
    STATUS       current
    DESCRIPTION  "Number of call attempts with signing
                  request timed out (in the last period)"
    ::= { perimetaGlobalStatsEntry 1317 }

  globalStatSigningTimeoutRate OBJECT-TYPE
    SYNTAX       CounterBasedGauge64
    MAX-ACCESS   read-only
    STATUS       current
    DESCRIPTION  "Rate of call attempts with signing
                  request timed out (calls/s)"
    ::= { perimetaGlobalStatsEntry 1318 }

  globalStatSigningUnavailableCount OBJECT-TYPE
    SYNTAX       CounterBasedGauge64
    MAX-ACCESS   read-only
    STATUS       current
    DESCRIPTION  "Number of call attempts with signing
                  unavailable (in the last period)"
    ::= { perimetaGlobalStatsEntry 1319 }

  globalStatSigningUnavailableRate OBJECT-TYPE
    SYNTAX       CounterBasedGauge64
    MAX-ACCESS   read-only
    STATUS       current
    DESCRIPTION  "Rate of call attempts with signing
                  unavailable (calls/s)"
    ::= { perimetaGlobalStatsEntry 1320 }

  globalStatFailedRecordedCallsSetup OBJECT-TYPE
    SYNTAX       CounterBasedGauge64
    MAX-ACCESS   read-only
    STATUS       current
    DESCRIPTION  "Number of recorded calls failing due to
                  recording call setup failure (in the
                  last period)"
    ::= { perimetaGlobalStatsEntry 1321 }

  globalStatFailedRecordedCallsDrop OBJECT-TYPE
    SYNTAX       CounterBasedGauge64
    MAX-ACCESS   read-only
    STATUS       current
    DESCRIPTION  "Number of recorded calls failing due to
                  recording call drop (in the last period)"
    ::= { perimetaGlobalStatsEntry 1322 }

  globalStatFailedRecordedCallsSetupPercent OBJECT-TYPE
    SYNTAX       CounterBasedGauge64
    UNITS        "/ 10000 %"
    MAX-ACCESS   read-only
    STATUS       current
    DESCRIPTION  "Percentage of recorded calls failing due
                  to recording call setup failure (in the
                  last period)"
    ::= { perimetaGlobalStatsEntry 1323 }

  globalStatFailedRecordedCallsDropPercent OBJECT-TYPE
    SYNTAX       CounterBasedGauge64
    UNITS        "/ 10000 %"
    MAX-ACCESS   read-only
    STATUS       current
    DESCRIPTION  "Percentage of recorded calls failing due
                  to recording call drop (in the last
                  period)"
    ::= { perimetaGlobalStatsEntry 1324 }

  globalStatNoPermitCount OBJECT-TYPE
    SYNTAX       CounterBasedGauge64
    MAX-ACCESS   read-only
    STATUS       current
    DESCRIPTION  "Number of packets dropped on restricted
                  service interfaces (in the last period)"
    ::= { perimetaGlobalStatsEntry 1325 }

  globalStatNoPermitRate OBJECT-TYPE
    SYNTAX       CounterBasedGauge64
    MAX-ACCESS   read-only
    STATUS       current
    DESCRIPTION  "Rate of packets dropped on restricted
                  service interfaces (pkts/s)"
    ::= { perimetaGlobalStatsEntry 1326 }

-- /**********************************************************/
-- /* Information about Perimeta Adjacencies.                */
-- /**********************************************************/

  perimetaAdjacencies OBJECT IDENTIFIER ::= { perimeta 3 }

  perimetaAdjacencyNumber OBJECT-TYPE
    SYNTAX       Unsigned32
    MAX-ACCESS   read-only
    STATUS       current
    DESCRIPTION  "This is the number of adjacencies configured on Perimeta"
    ::= { perimetaAdjacencies 1 }

  perimetaAdjacencyStatsTable OBJECT-TYPE
    SYNTAX      SEQUENCE OF PerimetaAdjacencyStatsEntry
    MAX-ACCESS  not-accessible
    STATUS      current
    DESCRIPTION "This table contains statistics from Perimeta at
                 per-adjacency scope, indexed by adjacency name."
    ::= { perimetaAdjacencies 2 }

  perimetaAdjacencyStatsEntry OBJECT-TYPE
    SYNTAX      PerimetaAdjacencyStatsEntry
    MAX-ACCESS  not-accessible
    STATUS      current
    DESCRIPTION "The entry in the Perimeta adjacency stats table
                 contains all the per-adjacency statistics,
                 indexed on adjacency name."
    INDEX      { adjStatAdjacencyName, adjStatSummaryPeriod }
    ::= { perimetaAdjacencyStatsTable 1 }

  PerimetaAdjacencyStatsEntry ::= SEQUENCE
  {
    adjStatAdjacencyName                          DisplayString,
    adjStatSummaryPeriod                          INTEGER,
    adjStatAccountName                            DisplayString,
    adjStatSrcActiveCalls                         CounterBasedGauge64,
    adjStatDstActiveCalls                         CounterBasedGauge64,
    adjStatSrcActivatingCalls                     CounterBasedGauge64,
    adjStatDstActivatingCalls                     CounterBasedGauge64,
    adjStatSrcDeactivatingCalls                   CounterBasedGauge64,
    adjStatDstDectivatingCalls                    CounterBasedGauge64,
    adjStatSrcActEmergCalls                       CounterBasedGauge64,
    adjStatDstActEmergCalls                       CounterBasedGauge64,
    adjStatSrcActiveIPSecCalls                    CounterBasedGauge64,
    adjStatDstActiveIPSecCalls                    CounterBasedGauge64,
    adjStatSrcActSRTPIntCalls                     CounterBasedGauge64,
    adjStatDstActSRTPIntCalls                     CounterBasedGauge64,
    adjStatSrcActiveRxCalls                       CounterBasedGauge64,
    adjStatDstActiveRxCalls                       CounterBasedGauge64,
    adjStatSrcActTrigTcdngCs                      CounterBasedGauge64,
    adjStatDstActTrigTcdngCs                      CounterBasedGauge64,
    adjStatSrcActUsedTcdngCs                      CounterBasedGauge64,
    adjStatDstActUsedTcdngCs                      CounterBasedGauge64,
    adjStatSrcActiveH323Clls                      CounterBasedGauge64,
    adjStatDstActiveH323Clls                      CounterBasedGauge64,
    adjStatActiveSubscribers                      CounterBasedGauge64,
    adjStatSrcAllCallAttemptsRate                 CounterBasedGauge64,
    adjStatDstAllCallAttemptsRate                 CounterBasedGauge64,
    adjStatSrcFldCallAttemptsRate                 CounterBasedGauge64,
    adjStatDstFldCallAttemptsRate                 CounterBasedGauge64,
    adjStatSrcFldRxCallAttmptsRate                CounterBasedGauge64,
    adjStatDstFldRxCallAttmptsRate                CounterBasedGauge64,
    adjStatSrcRxRnegAttmptsRate                   CounterBasedGauge64,
    adjStatDstRxRnegAttmptsRate                   CounterBasedGauge64,
    adjStatSrcFldRxRnegAttmptsRate                CounterBasedGauge64,
    adjStatDstFldRxRnegAttmptsRate                CounterBasedGauge64,
    adjStatSrcIPSecCallSetupRate                  CounterBasedGauge64,
    adjStatDstIPSecCallSetupRate                  CounterBasedGauge64,
    adjStatSrcTrnscdngTrigCallRate                CounterBasedGauge64,
    adjStatDstTrnscdngTrigCallRate                CounterBasedGauge64,
    adjStatSrcTrnscdngUsedCallRate                CounterBasedGauge64,
    adjStatDstTrnscdngUsedCallRate                CounterBasedGauge64,
    adjStatSrcH323CallRate                        CounterBasedGauge64,
    adjStatDstH323CallRate                        CounterBasedGauge64,
    adjStatSrcTotalSetupFailureRate               CounterBasedGauge64,
    adjStatDstTotalSetupFailureRate               CounterBasedGauge64,
    adjStatSrcNumAnlysFailureRate                 CounterBasedGauge64,
    adjStatDstNumAnlysFailureRate                 CounterBasedGauge64,
    adjStatSrcRoutingFailureRate                  CounterBasedGauge64,
    adjStatDstRoutingFailureRate                  CounterBasedGauge64,
    adjStatSrcCapacityControlFailureRate          CounterBasedGauge64,
    adjStatDstCapacityControlFailureRate          CounterBasedGauge64,
    adjStatSrcUnsupCodecFailureRate               CounterBasedGauge64,
    adjStatDstUnsupCodecFailureRate               CounterBasedGauge64,
    adjStatSrcActiveCallFailureRate               CounterBasedGauge64,
    adjStatDstActiveCallFailureRate               CounterBasedGauge64,
    adjStatSrcFailuresAnyReason                   CounterBasedGauge64,
    adjStatDstFailuresAnyReason                   CounterBasedGauge64,
    adjStatSrcFailuresNumberAnalysis              CounterBasedGauge64,
    adjStatDstFailuresNumberAnalysis              CounterBasedGauge64,
    adjStatSrcFailuresRouting                     CounterBasedGauge64,
    adjStatDstFailuresRouting                     CounterBasedGauge64,
    adjStatSrcFailuresCapacityControl             CounterBasedGauge64,
    adjStatDstFailuresCapacityControl             CounterBasedGauge64,
    adjStatSrcFailuresUnsupCodecs                 CounterBasedGauge64,
    adjStatDstFailuresUnsupCodecs                 CounterBasedGauge64,
    adjStatSrcFailuresAfterSetup                  CounterBasedGauge64,
    adjStatDstFailuresAfterSetup                  CounterBasedGauge64,
    adjStatSrcCapCtrlRejectedAnyReasonLastPeriod  CounterBasedGauge64,
    adjStatDstCapCtrlRejectedAnyReasonLastPeriod  CounterBasedGauge64,
    adjStatSrcCapCtrlRejectedBandwidthLimitLastPeriod CounterBasedGauge64,
    adjStatDstCapCtrlRejectedBandwidthLimitLastPeriod CounterBasedGauge64,
    adjStatSrcCapCtrlRejectedTotalConcurrentLastPeriod CounterBasedGauge64,
    adjStatDstCapCtrlRejectedTotalConcurrentLastPeriod CounterBasedGauge64,
    adjStatRTPPacketsReceivedLastPeriod           CounterBasedGauge64,
    adjStatRTPPacketsSentLastPeriod               CounterBasedGauge64,
    adjStatRTPPacketsDroppedLastPeriod            CounterBasedGauge64,
    adjStatRTPPacketsLostLastPeriod               CounterBasedGauge64,
    adjStatRTPAvgRoundTripDelayLast5Min           CounterBasedGauge64,
    adjStatRTPAvgRemoteJitterLast5Min             CounterBasedGauge64,
    adjStatSrcInbDTMFCalls                        CounterBasedGauge64,
    adjStatDstInbDTMFCalls                        CounterBasedGauge64,
    adjStatSrcInbDTMFCallRate                     CounterBasedGauge64,
    adjStatDstInbDTMFCallRate                     CounterBasedGauge64,
    adjStatRTPBytesSent                           CounterBasedGauge64,
    adjStatRTPBytesReceived                       CounterBasedGauge64,
    adjStatRTPBandwidthSent                       CounterBasedGauge64,
    adjStatRTPBandwidthReceived                   CounterBasedGauge64,
    adjStatRTPBandwidthSentPercent                CounterBasedGauge64,
    adjStatRTPBandwidthReceivedPercent            CounterBasedGauge64,
    adjStatMaxPacketDrop                          CounterBasedGauge64,
    adjStatAveragePacketDrop                      CounterBasedGauge64,
    adjStatMaxPacketLoss                          CounterBasedGauge64,
    adjStatAveragePacketLoss                      CounterBasedGauge64,
    adjStatMaxRemoteJitter                        CounterBasedGauge64,
    adjStatAverageMaxRemoteJitter                 CounterBasedGauge64,
    adjStatMaxAverageRoundTripDelay               CounterBasedGauge64,
    adjStatAverageRoundTripDelay                  CounterBasedGauge64,
    adjStatCodecUsageOther                        CounterBasedGauge64,
    adjStatCodecUsageG711U                        CounterBasedGauge64,
    adjStatCodecUsageG711A                        CounterBasedGauge64,
    adjStatCodecUsageG722                         CounterBasedGauge64,
    adjStatCodecUsageG7231                        CounterBasedGauge64,
    adjStatCodecUsageG726                         CounterBasedGauge64,
    adjStatCodecUsageG729                         CounterBasedGauge64,
    adjStatCodecUsageT38                          CounterBasedGauge64,
    adjStatCodecUsageAMRNB                        CounterBasedGauge64,
    adjStatCodecUsageAMRWB                        CounterBasedGauge64,
    adjStatCodecUsageClearmode                    CounterBasedGauge64,
    adjStatCodecUsageGSMFR                        CounterBasedGauge64,
    adjStatCodecUsageGSMEFR                       CounterBasedGauge64,
    adjStatCodecUsageGSMHR                        CounterBasedGauge64,
    adjStatCodecUsageEVRC                         CounterBasedGauge64,
    adjStatCodecUsageiLBC                         CounterBasedGauge64,
    adjStatCodecUsageSILK                         CounterBasedGauge64,
    adjStatNumCallsHwm                            CounterBasedGauge64,
    adjStatMedBwHwm                               CounterBasedGauge64,
    adjStatMedStreamsHwm                          CounterBasedGauge64,
    adjStatNumRegsHwm                             CounterBasedGauge64,
    adjStatCallBurstRateHwm                       CounterBasedGauge64,
    adjStatCallSustainRateHwm                     CounterBasedGauge64,
    adjStatInCallBurstRateHwm                     CounterBasedGauge64,
    adjStatInCallSustainRateHwm                   CounterBasedGauge64,
    adjStatOOCBurstRateHwm                        CounterBasedGauge64,
    adjStatOOCSustainRateHwm                      CounterBasedGauge64,
    adjStatRegsBurstRateHwm                       CounterBasedGauge64,
    adjStatRegsSustainRateHwm                     CounterBasedGauge64,
    adjStatNumCallsPerc                           CounterBasedGauge64,
    adjStatMedBwPerc                              CounterBasedGauge64,
    adjStatMedStrPerc                             CounterBasedGauge64,
    adjStatNumRegsPerc                            CounterBasedGauge64,
    adjStatCallBurstRatePerc                      CounterBasedGauge64,
    adjStatCallSustainRatePerc                    CounterBasedGauge64,
    adjStatInCallBurstRatePerc                    CounterBasedGauge64,
    adjStatInCallSustainRatePerc                  CounterBasedGauge64,
    adjStatOOCBurstRatePerc                       CounterBasedGauge64,
    adjStatOOCSustainRatePerc                     CounterBasedGauge64,
    adjStatRegsBurstRatePerc                      CounterBasedGauge64,
    adjStatRegsSustainRatePerc                    CounterBasedGauge64,
    adjStatSrcNumCallsHwm                         CounterBasedGauge64,
    adjStatSrcMedBwHwm                            CounterBasedGauge64,
    adjStatSrcMedStreamsHwm                       CounterBasedGauge64,
    adjStatSrcNumRegsHwm                          CounterBasedGauge64,
    adjStatSrcCallBurstRateHwm                    CounterBasedGauge64,
    adjStatSrcCallSustainRateHwm                  CounterBasedGauge64,
    adjStatSrcInCallBurstRateHwm                  CounterBasedGauge64,
    adjStatSrcInCallSustainRateHwm                CounterBasedGauge64,
    adjStatSrcOOCBurstRateHwm                     CounterBasedGauge64,
    adjStatSrcOOCSustainRateHwm                   CounterBasedGauge64,
    adjStatSrcRegsBurstRateHwm                    CounterBasedGauge64,
    adjStatSrcRegsSustainRateHwm                  CounterBasedGauge64,
    adjStatSrcNumCallsPerc                        CounterBasedGauge64,
    adjStatSrcMedBwPerc                           CounterBasedGauge64,
    adjStatSrcMedStrPerc                          CounterBasedGauge64,
    adjStatSrcNumRegsPerc                         CounterBasedGauge64,
    adjStatSrcCallBurstRatePerc                   CounterBasedGauge64,
    adjStatSrcCallSustainRatePerc                 CounterBasedGauge64,
    adjStatSrcInCallBurstRatePerc                 CounterBasedGauge64,
    adjStatSrcInCallSustainRatePerc               CounterBasedGauge64,
    adjStatSrcOOCBurstRatePerc                    CounterBasedGauge64,
    adjStatSrcOOCSustainRatePerc                  CounterBasedGauge64,
    adjStatSrcRegsBurstRatePerc                   CounterBasedGauge64,
    adjStatSrcRegsSustainRatePerc                 CounterBasedGauge64,
    adjStatDstNumCallsHwm                         CounterBasedGauge64,
    adjStatDstMedBwHwm                            CounterBasedGauge64,
    adjStatDstMedStreamsHwm                       CounterBasedGauge64,
    adjStatDstNumRegsHwm                          CounterBasedGauge64,
    adjStatDstCallBurstRateHwm                    CounterBasedGauge64,
    adjStatDstCallSustainRateHwm                  CounterBasedGauge64,
    adjStatDstInCallBurstRateHwm                  CounterBasedGauge64,
    adjStatDstInCallSustainRateHwm                CounterBasedGauge64,
    adjStatDstOOCBurstRateHwm                     CounterBasedGauge64,
    adjStatDstOOCSustainRateHwm                   CounterBasedGauge64,
    adjStatDstRegsBurstRateHwm                    CounterBasedGauge64,
    adjStatDstRegsSustainRateHwm                  CounterBasedGauge64,
    adjStatDstNumCallsPerc                        CounterBasedGauge64,
    adjStatDstMedBwPerc                           CounterBasedGauge64,
    adjStatDstMedStrPerc                          CounterBasedGauge64,
    adjStatDstNumRegsPerc                         CounterBasedGauge64,
    adjStatDstCallBurstRatePerc                   CounterBasedGauge64,
    adjStatDstCallSustainRatePerc                 CounterBasedGauge64,
    adjStatDstInCallBurstRatePerc                 CounterBasedGauge64,
    adjStatDstInCallSustainRatePerc               CounterBasedGauge64,
    adjStatDstOOCBurstRatePerc                    CounterBasedGauge64,
    adjStatDstOOCSustainRatePerc                  CounterBasedGauge64,
    adjStatDstRegsBurstRatePerc                   CounterBasedGauge64,
    adjStatDstRegsSustainRatePerc                 CounterBasedGauge64,
    adjStatNumCallsMLimit                         CounterBasedGauge64,
    adjStatMedBwMLimit                            CounterBasedGauge64,
    adjStatMedStrMLimit                           CounterBasedGauge64,
    adjStatNumRegsMLimit                          CounterBasedGauge64,
    adjStatCallBurstRateMLimit                    CounterBasedGauge64,
    adjStatCallSustainRateMLimit                  CounterBasedGauge64,
    adjStatInCallBurstRateMLimit                  CounterBasedGauge64,
    adjStatInCallSustainRateMLimit                CounterBasedGauge64,
    adjStatOOCBurstRateMLimit                     CounterBasedGauge64,
    adjStatOOCSustainRateMLimit                   CounterBasedGauge64,
    adjStatRegsBurstRateMLimit                    CounterBasedGauge64,
    adjStatRegsSustainRateMLimit                  CounterBasedGauge64,
    adjStatSrcNumCallsMLimit                      CounterBasedGauge64,
    adjStatSrcMedBwMLimit                         CounterBasedGauge64,
    adjStatSrcMedStrMLimit                        CounterBasedGauge64,
    adjStatSrcNumRegsMLimit                       CounterBasedGauge64,
    adjStatSrcCallBurstRateMLimit                 CounterBasedGauge64,
    adjStatSrcCallSustainRateMLimit               CounterBasedGauge64,
    adjStatSrcInCallBurstRateMLimit               CounterBasedGauge64,
    adjStatSrcInCallSustainRateMLimit             CounterBasedGauge64,
    adjStatSrcOOCBurstRateMLimit                  CounterBasedGauge64,
    adjStatSrcOOCSustainRateMLimit                CounterBasedGauge64,
    adjStatSrcRegsBurstRateMLimit                 CounterBasedGauge64,
    adjStatSrcRegsSustainRateMLimit               CounterBasedGauge64,
    adjStatDstNumCallsMLimit                      CounterBasedGauge64,
    adjStatDstMedBwMLimit                         CounterBasedGauge64,
    adjStatDstMedStrMLimit                        CounterBasedGauge64,
    adjStatDstNumRegsMLimit                       CounterBasedGauge64,
    adjStatDstCallBurstRateMLimit                 CounterBasedGauge64,
    adjStatDstCallSustainRateMLimit               CounterBasedGauge64,
    adjStatDstInCallBurstRateMLimit               CounterBasedGauge64,
    adjStatDstInCallSustainRateMLimit             CounterBasedGauge64,
    adjStatDstOOCBurstRateMLimit                  CounterBasedGauge64,
    adjStatDstOOCSustainRateMLimit                CounterBasedGauge64,
    adjStatDstRegsBurstRateMLimit                 CounterBasedGauge64,
    adjStatDstRegsSustainRateMLimit               CounterBasedGauge64,
    adjStatRTPAvgRfactorLast5Min                  CounterBasedGauge64,
    adjStatRTPAvgMOScqeLast5Min                   CounterBasedGauge64,
    adjStatSrcMSRPSIWCallsCurrent                 CounterBasedGauge64,
    adjStatSrcMSRPSPtCallsCurrent                 CounterBasedGauge64,
    adjStatSrcMSRPSIWCallRate                     CounterBasedGauge64,
    adjStatSrcMSRPSPtCallRate                     CounterBasedGauge64,
    adjStatDstMSRPSIWCallsCurrent                 CounterBasedGauge64,
    adjStatDstMSRPSPtCallsCurrent                 CounterBasedGauge64,
    adjStatDstMSRPSIWCallRate                     CounterBasedGauge64,
    adjStatDstMSRPSPtCallRate                     CounterBasedGauge64,
    adjStatSrcSignalFailureRate                   CounterBasedGauge64,
    adjStatDstSignalFailureRate                   CounterBasedGauge64,
    adjStatSrcFailuresSignaling                   CounterBasedGauge64,
    adjStatDstFailuresSignaling                   CounterBasedGauge64,
    adjStatEmergencyRedirects                     CounterBasedGauge64,
    adjStatCodecUsageOPUS                         CounterBasedGauge64,
    adjStatNumCallsHwmNMP                         CounterBasedGauge64,
    adjStatMedBwHwmNMP                            CounterBasedGauge64,
    adjStatMedStreamsHwmNMP                       CounterBasedGauge64,
    adjStatNumRegsHwmNMP                          CounterBasedGauge64,
    adjStatCallBurstRateHwmNMP                    CounterBasedGauge64,
    adjStatCallSustainRateHwmNMP                  CounterBasedGauge64,
    adjStatInCallBurstRateHwmNMP                  CounterBasedGauge64,
    adjStatInCallSustainRateHwmNMP                CounterBasedGauge64,
    adjStatOOCBurstRateHwmNMP                     CounterBasedGauge64,
    adjStatOOCSustainRateHwmNMP                   CounterBasedGauge64,
    adjStatRegsBurstRateHwmNMP                    CounterBasedGauge64,
    adjStatRegsSustainRateHwmNMP                  CounterBasedGauge64,
    adjStatSrcNumCallsHwmNMP                      CounterBasedGauge64,
    adjStatSrcMedBwHwmNMP                         CounterBasedGauge64,
    adjStatSrcMedStreamsHwmNMP                    CounterBasedGauge64,
    adjStatSrcNumRegsHwmNMP                       CounterBasedGauge64,
    adjStatSrcCallBurstRateHwmNMP                 CounterBasedGauge64,
    adjStatSrcCallSustainRateHwmNMP               CounterBasedGauge64,
    adjStatSrcInCallBurstRateHwmNMP               CounterBasedGauge64,
    adjStatSrcInCallSustainRateHwmNMP             CounterBasedGauge64,
    adjStatSrcOOCBurstRateHwmNMP                  CounterBasedGauge64,
    adjStatSrcOOCSustainRateHwmNMP                CounterBasedGauge64,
    adjStatSrcRegsBurstRateHwmNMP                 CounterBasedGauge64,
    adjStatSrcRegsSustainRateHwmNMP               CounterBasedGauge64,
    adjStatDstNumCallsHwmNMP                      CounterBasedGauge64,
    adjStatDstMedBwHwmNMP                         CounterBasedGauge64,
    adjStatDstMedStreamsHwmNMP                    CounterBasedGauge64,
    adjStatDstNumRegsHwmNMP                       CounterBasedGauge64,
    adjStatDstCallBurstRateHwmNMP                 CounterBasedGauge64,
    adjStatDstCallSustainRateHwmNMP               CounterBasedGauge64,
    adjStatDstInCallBurstRateHwmNMP               CounterBasedGauge64,
    adjStatDstInCallSustainRateHwmNMP             CounterBasedGauge64,
    adjStatDstOOCBurstRateHwmNMP                  CounterBasedGauge64,
    adjStatDstOOCSustainRateHwmNMP                CounterBasedGauge64,
    adjStatDstRegsBurstRateHwmNMP                 CounterBasedGauge64,
    adjStatDstRegsSustainRateHwmNMP               CounterBasedGauge64,
    adjStatDstTotalCallDuration                   CounterBasedGauge64,
    adjStatSrcTotalCallDuration                   CounterBasedGauge64,
    adjStatOKEmergencyCallNotifiesLastPeriod      CounterBasedGauge64,
    adjStatFailedEmergencyCallNotifiesLastPeriod  CounterBasedGauge64,
    adjStatOKEmergencyCallNotifiesRate            CounterBasedGauge64,
    adjStatFailedEmergencyCallNotifiesRate        CounterBasedGauge64,
    adjStatEmergencyCallNotifiesSentLastPeriod    CounterBasedGauge64,
    adjStatEmergencyCallNotifiesSentRate          CounterBasedGauge64
  }

  adjStatAdjacencyName OBJECT-TYPE
    SYNTAX      DisplayString (SIZE(1..32))
    MAX-ACCESS  not-accessible
    STATUS      current
    DESCRIPTION "The name of the adjacency. This is the index field
                 for adjacency statistics."
    ::= { perimetaAdjacencyStatsEntry 1 }

  adjStatSummaryPeriod OBJECT-TYPE
    SYNTAX       INTEGER {
                   summaryPeriod1CurrentClctnIntv(1)
                 }
    MAX-ACCESS   not-accessible
    STATUS       current
    DESCRIPTION  "The period over which the statistics were collected.
                  This is an index field."
    ::= { perimetaAdjacencyStatsEntry 2 }

  adjStatAccountName OBJECT-TYPE
    SYNTAX      DisplayString (SIZE(1..32))
    MAX-ACCESS  not-accessible
    STATUS      current
    DESCRIPTION "The name of the account configured for this adjacency."
    ::= { perimetaAdjacencyStatsEntry 3 }

  adjStatSrcActiveCalls OBJECT-TYPE
    SYNTAX       CounterBasedGauge64
    MAX-ACCESS   read-only
    STATUS       current
    DESCRIPTION  "Currently active calls incoming to this
                  adjacency"
    ::= { perimetaAdjacencyStatsEntry 11 }

  adjStatDstActiveCalls OBJECT-TYPE
    SYNTAX       CounterBasedGauge64
    MAX-ACCESS   read-only
    STATUS       current
    DESCRIPTION  "Currently active calls outgoing from
                  this adjacency"
    ::= { perimetaAdjacencyStatsEntry 12 }

  adjStatSrcActivatingCalls OBJECT-TYPE
    SYNTAX       CounterBasedGauge64
    MAX-ACCESS   read-only
    STATUS       current
    DESCRIPTION  "Currently activating calls incoming to
                  this adjacency"
    ::= { perimetaAdjacencyStatsEntry 13 }

  adjStatDstActivatingCalls OBJECT-TYPE
    SYNTAX       CounterBasedGauge64
    MAX-ACCESS   read-only
    STATUS       current
    DESCRIPTION  "Currently activating calls outgoing from
                  this adjacency"
    ::= { perimetaAdjacencyStatsEntry 14 }

  adjStatSrcDeactivatingCalls OBJECT-TYPE
    SYNTAX       CounterBasedGauge64
    MAX-ACCESS   read-only
    STATUS       current
    DESCRIPTION  "Currently deactivating calls incoming to
                  this adjacency"
    ::= { perimetaAdjacencyStatsEntry 15 }

  adjStatDstDectivatingCalls OBJECT-TYPE
    SYNTAX       CounterBasedGauge64
    MAX-ACCESS   read-only
    STATUS       current
    DESCRIPTION  "Currently deactivating calls outgoing
                  from this adjacency"
    ::= { perimetaAdjacencyStatsEntry 16 }

  adjStatSrcActEmergCalls OBJECT-TYPE
    SYNTAX       CounterBasedGauge64
    MAX-ACCESS   read-only
    STATUS       current
    DESCRIPTION  "Currently active priority calls incoming
                  to this adjacency"
    ::= { perimetaAdjacencyStatsEntry 17 }

  adjStatDstActEmergCalls OBJECT-TYPE
    SYNTAX       CounterBasedGauge64
    MAX-ACCESS   read-only
    STATUS       current
    DESCRIPTION  "Currently active priority calls outgoing
                  from this adjacency"
    ::= { perimetaAdjacencyStatsEntry 18 }

  adjStatSrcActiveIPSecCalls OBJECT-TYPE
    SYNTAX       CounterBasedGauge64
    MAX-ACCESS   read-only
    STATUS       current
    DESCRIPTION  "Currently active IPSec calls incoming to
                  this adjacency"
    ::= { perimetaAdjacencyStatsEntry 19 }

  adjStatDstActiveIPSecCalls OBJECT-TYPE
    SYNTAX       CounterBasedGauge64
    MAX-ACCESS   read-only
    STATUS       current
    DESCRIPTION  "Currently active IPSec calls outgoing
                  from this adjacency"
    ::= { perimetaAdjacencyStatsEntry 20 }

  adjStatSrcActSRTPIntCalls OBJECT-TYPE
    SYNTAX       CounterBasedGauge64
    MAX-ACCESS   read-only
    STATUS       current
    DESCRIPTION  "Currently active SRTP Interworking calls
                  incoming to this adjacency"
    ::= { perimetaAdjacencyStatsEntry 21 }

  adjStatDstActSRTPIntCalls OBJECT-TYPE
    SYNTAX       CounterBasedGauge64
    MAX-ACCESS   read-only
    STATUS       current
    DESCRIPTION  "Currently active SRTP Interworking calls
                  outgoing from this adjacency"
    ::= { perimetaAdjacencyStatsEntry 22 }

  adjStatSrcActiveRxCalls OBJECT-TYPE
    SYNTAX       CounterBasedGauge64
    MAX-ACCESS   read-only
    STATUS       current
    DESCRIPTION  "Currently active Rx calls incoming to
                  this adjacency"
    ::= { perimetaAdjacencyStatsEntry 23 }

  adjStatDstActiveRxCalls OBJECT-TYPE
    SYNTAX       CounterBasedGauge64
    MAX-ACCESS   read-only
    STATUS       current
    DESCRIPTION  "Currently active Rx calls outgoing from
                  this adjacency"
    ::= { perimetaAdjacencyStatsEntry 24 }

  adjStatSrcActTrigTcdngCs OBJECT-TYPE
    SYNTAX       CounterBasedGauge64
    MAX-ACCESS   read-only
    STATUS       current
    DESCRIPTION  "Active calls incoming to this adjacency
                  that have triggered transcoding"
    ::= { perimetaAdjacencyStatsEntry 25 }

  adjStatDstActTrigTcdngCs OBJECT-TYPE
    SYNTAX       CounterBasedGauge64
    MAX-ACCESS   read-only
    STATUS       current
    DESCRIPTION  "Active calls outgoing from this
                  adjacency that have triggered
                  transcoding"
    ::= { perimetaAdjacencyStatsEntry 26 }

  adjStatSrcActUsedTcdngCs OBJECT-TYPE
    SYNTAX       CounterBasedGauge64
    MAX-ACCESS   read-only
    STATUS       current
    DESCRIPTION  "Active calls incoming to this adjacency
                  that have used transcoding"
    ::= { perimetaAdjacencyStatsEntry 27 }

  adjStatDstActUsedTcdngCs OBJECT-TYPE
    SYNTAX       CounterBasedGauge64
    MAX-ACCESS   read-only
    STATUS       current
    DESCRIPTION  "Active calls outgoing from this
                  adjacency that have used transcoding"
    ::= { perimetaAdjacencyStatsEntry 28 }

  adjStatSrcActiveH323Clls OBJECT-TYPE
    SYNTAX       CounterBasedGauge64
    MAX-ACCESS   read-only
    STATUS       current
    DESCRIPTION  "Currently active H323 calls incoming to
                  this adjacency"
    ::= { perimetaAdjacencyStatsEntry 29 }

  adjStatDstActiveH323Clls OBJECT-TYPE
    SYNTAX       CounterBasedGauge64
    MAX-ACCESS   read-only
    STATUS       current
    DESCRIPTION  "Currently active H323 calls outgoing
                  from this adjacency"
    ::= { perimetaAdjacencyStatsEntry 30 }

  adjStatActiveSubscribers OBJECT-TYPE
    SYNTAX       CounterBasedGauge64
    MAX-ACCESS   read-only
    STATUS       current
    DESCRIPTION  "Current number of subscribers registered
                  through this adjacency"
    ::= { perimetaAdjacencyStatsEntry 59 }

  adjStatSrcAllCallAttemptsRate OBJECT-TYPE
    SYNTAX       CounterBasedGauge64
    MAX-ACCESS   read-only
    STATUS       current
    DESCRIPTION  "Rate of all incoming call attempts to
                  this adjacency"
    ::= { perimetaAdjacencyStatsEntry 60 }

  adjStatDstAllCallAttemptsRate OBJECT-TYPE
    SYNTAX       CounterBasedGauge64
    MAX-ACCESS   read-only
    STATUS       current
    DESCRIPTION  "Rate of all outgoing call attempts from
                  this adjacency"
    ::= { perimetaAdjacencyStatsEntry 61 }

  adjStatSrcFldCallAttemptsRate OBJECT-TYPE
    SYNTAX       CounterBasedGauge64
    MAX-ACCESS   read-only
    STATUS       current
    DESCRIPTION  "Rate of failed incoming call attempts to
                  this adjacency"
    ::= { perimetaAdjacencyStatsEntry 62 }

  adjStatDstFldCallAttemptsRate OBJECT-TYPE
    SYNTAX       CounterBasedGauge64
    MAX-ACCESS   read-only
    STATUS       current
    DESCRIPTION  "Rate of failed outgoing call attempts
                  from this adjacency"
    ::= { perimetaAdjacencyStatsEntry 63 }

  adjStatSrcFldRxCallAttmptsRate OBJECT-TYPE
    SYNTAX       CounterBasedGauge64
    MAX-ACCESS   read-only
    STATUS       current
    DESCRIPTION  "Rate of failed incoming Rx call attempts
                  to this adjacency"
    ::= { perimetaAdjacencyStatsEntry 64 }

  adjStatDstFldRxCallAttmptsRate OBJECT-TYPE
    SYNTAX       CounterBasedGauge64
    MAX-ACCESS   read-only
    STATUS       current
    DESCRIPTION  "Rate of failed outgoing Rx call attempts
                  from this adjacency"
    ::= { perimetaAdjacencyStatsEntry 65 }

  adjStatSrcRxRnegAttmptsRate OBJECT-TYPE
    SYNTAX       CounterBasedGauge64
    MAX-ACCESS   read-only
    STATUS       current
    DESCRIPTION  "Rate of incoming Rx renegotiation
                  attempts to this adjacency"
    ::= { perimetaAdjacencyStatsEntry 66 }

  adjStatDstRxRnegAttmptsRate OBJECT-TYPE
    SYNTAX       CounterBasedGauge64
    MAX-ACCESS   read-only
    STATUS       current
    DESCRIPTION  "Rate of outgoing Rx renegotiation
                  attempts from this adjacency"
    ::= { perimetaAdjacencyStatsEntry 67 }

  adjStatSrcFldRxRnegAttmptsRate OBJECT-TYPE
    SYNTAX       CounterBasedGauge64
    MAX-ACCESS   read-only
    STATUS       current
    DESCRIPTION  "Rate of failed incoming Rx renegotiation
                  attempts to this adjacency"
    ::= { perimetaAdjacencyStatsEntry 68 }

  adjStatDstFldRxRnegAttmptsRate OBJECT-TYPE
    SYNTAX       CounterBasedGauge64
    MAX-ACCESS   read-only
    STATUS       current
    DESCRIPTION  "Rate of failed outgoing Rx renegotiation
                  attempts from this adjacency"
    ::= { perimetaAdjacencyStatsEntry 69 }

  adjStatSrcIPSecCallSetupRate OBJECT-TYPE
    SYNTAX       CounterBasedGauge64
    MAX-ACCESS   read-only
    STATUS       current
    DESCRIPTION  "Rate of successful incoming IPSec calls
                  setup to this adjacency"
    ::= { perimetaAdjacencyStatsEntry 70 }

  adjStatDstIPSecCallSetupRate OBJECT-TYPE
    SYNTAX       CounterBasedGauge64
    MAX-ACCESS   read-only
    STATUS       current
    DESCRIPTION  "Rate of successful outgoing IPSec calls
                  setup from this adjacency"
    ::= { perimetaAdjacencyStatsEntry 71 }

  adjStatSrcTrnscdngTrigCallRate OBJECT-TYPE
    SYNTAX       CounterBasedGauge64
    MAX-ACCESS   read-only
    STATUS       current
    DESCRIPTION  "Rate of incoming calls to this adjacency
                  that have triggered transcoding"
    ::= { perimetaAdjacencyStatsEntry 72 }

  adjStatDstTrnscdngTrigCallRate OBJECT-TYPE
    SYNTAX       CounterBasedGauge64
    MAX-ACCESS   read-only
    STATUS       current
    DESCRIPTION  "Rate of outgoing calls from this
                  adjacency that have triggered
                  transcoding"
    ::= { perimetaAdjacencyStatsEntry 73 }

  adjStatSrcTrnscdngUsedCallRate OBJECT-TYPE
    SYNTAX       CounterBasedGauge64
    MAX-ACCESS   read-only
    STATUS       current
    DESCRIPTION  "Rate of incoming transcoded calls to
                  this adjacency"
    ::= { perimetaAdjacencyStatsEntry 74 }

  adjStatDstTrnscdngUsedCallRate OBJECT-TYPE
    SYNTAX       CounterBasedGauge64
    MAX-ACCESS   read-only
    STATUS       current
    DESCRIPTION  "Rate of outgoing transcoded calls from
                  this adjacency"
    ::= { perimetaAdjacencyStatsEntry 75 }

  adjStatSrcH323CallRate OBJECT-TYPE
    SYNTAX       CounterBasedGauge64
    MAX-ACCESS   read-only
    STATUS       current
    DESCRIPTION  "Rate of incoming H323 calls setup to
                  this adjacency"
    ::= { perimetaAdjacencyStatsEntry 76 }

  adjStatDstH323CallRate OBJECT-TYPE
    SYNTAX       CounterBasedGauge64
    MAX-ACCESS   read-only
    STATUS       current
    DESCRIPTION  "Rate of outgoing H323 calls setup from
                  this adjacency"
    ::= { perimetaAdjacencyStatsEntry 77 }

  adjStatSrcTotalSetupFailureRate OBJECT-TYPE
    SYNTAX       CounterBasedGauge64
    MAX-ACCESS   read-only
    STATUS       current
    DESCRIPTION  "Rate of incoming calls to this adjacency
                  failing to be setup for any reason"
    ::= { perimetaAdjacencyStatsEntry 83 }

  adjStatDstTotalSetupFailureRate OBJECT-TYPE
    SYNTAX       CounterBasedGauge64
    MAX-ACCESS   read-only
    STATUS       current
    DESCRIPTION  "Rate of outgoing calls from this
                  adjacency failing to be setup for any
                  reason"
    ::= { perimetaAdjacencyStatsEntry 84 }

  adjStatSrcNumAnlysFailureRate OBJECT-TYPE
    SYNTAX       CounterBasedGauge64
    MAX-ACCESS   read-only
    STATUS       current
    DESCRIPTION  "Rate of incoming calls to this adjacency
                  failing to be setup due to Number
                  Analysis"
    ::= { perimetaAdjacencyStatsEntry 85 }

  adjStatDstNumAnlysFailureRate OBJECT-TYPE
    SYNTAX       CounterBasedGauge64
    MAX-ACCESS   read-only
    STATUS       current
    DESCRIPTION  "Rate of outgoing calls from this
                  adjacency failing to be setup due to
                  Number Analysis"
    ::= { perimetaAdjacencyStatsEntry 86 }

  adjStatSrcRoutingFailureRate OBJECT-TYPE
    SYNTAX       CounterBasedGauge64
    MAX-ACCESS   read-only
    STATUS       current
    DESCRIPTION  "Rate of incoming calls to this adjacency
                  failing to be setup due to Routing"
    ::= { perimetaAdjacencyStatsEntry 87 }

  adjStatDstRoutingFailureRate OBJECT-TYPE
    SYNTAX       CounterBasedGauge64
    MAX-ACCESS   read-only
    STATUS       current
    DESCRIPTION  "Rate of outgoing calls from this
                  adjacency failing to be setup due to
                  Routing"
    ::= { perimetaAdjacencyStatsEntry 88 }

  adjStatSrcCapacityControlFailureRate OBJECT-TYPE
    SYNTAX       CounterBasedGauge64
    MAX-ACCESS   read-only
    STATUS       current
    DESCRIPTION  "Rate of incoming calls to this adjacency
                  failing to be setup due to Capacity
                  Control"
    ::= { perimetaAdjacencyStatsEntry 89 }

  adjStatDstCapacityControlFailureRate OBJECT-TYPE
    SYNTAX       CounterBasedGauge64
    MAX-ACCESS   read-only
    STATUS       current
    DESCRIPTION  "Rate of outgoing calls from this
                  adjacency failing to be setup due to
                  Capacity Control"
    ::= { perimetaAdjacencyStatsEntry 90 }

  adjStatSrcUnsupCodecFailureRate OBJECT-TYPE
    SYNTAX       CounterBasedGauge64
    MAX-ACCESS   read-only
    STATUS       current
    DESCRIPTION  "Rate of incoming calls to this adjacency
                  failing to be setup due to Unsupported
                  Codecs"
    ::= { perimetaAdjacencyStatsEntry 91 }

  adjStatDstUnsupCodecFailureRate OBJECT-TYPE
    SYNTAX       CounterBasedGauge64
    MAX-ACCESS   read-only
    STATUS       current
    DESCRIPTION  "Rate of outgoing calls from this
                  adjacency failing to be setup due to
                  Unsupported Codecs"
    ::= { perimetaAdjacencyStatsEntry 92 }

  adjStatSrcActiveCallFailureRate OBJECT-TYPE
    SYNTAX       CounterBasedGauge64
    MAX-ACCESS   read-only
    STATUS       current
    DESCRIPTION  "Rate of active incoming calls to this
                  adjacency failing"
    ::= { perimetaAdjacencyStatsEntry 93 }

  adjStatDstActiveCallFailureRate OBJECT-TYPE
    SYNTAX       CounterBasedGauge64
    MAX-ACCESS   read-only
    STATUS       current
    DESCRIPTION  "Rate of active outgoing calls from this
                  adjacency failing"
    ::= { perimetaAdjacencyStatsEntry 94 }

  adjStatSrcFailuresAnyReason OBJECT-TYPE
    SYNTAX       CounterBasedGauge64
    UNITS        "/ 10000 %"
    MAX-ACCESS   read-only
    STATUS       current
    DESCRIPTION  "Percentage of incoming calls to this
                  adjacency failing to be setup for any
                  reason (compared to attempts)"
    ::= { perimetaAdjacencyStatsEntry 95 }

  adjStatDstFailuresAnyReason OBJECT-TYPE
    SYNTAX       CounterBasedGauge64
    UNITS        "/ 10000 %"
    MAX-ACCESS   read-only
    STATUS       current
    DESCRIPTION  "Percentage of outgoing calls from this
                  adjacency failing to be setup for any
                  reason (compared to attempts)"
    ::= { perimetaAdjacencyStatsEntry 96 }

  adjStatSrcFailuresNumberAnalysis OBJECT-TYPE
    SYNTAX       CounterBasedGauge64
    UNITS        "/ 10000 %"
    MAX-ACCESS   read-only
    STATUS       current
    DESCRIPTION  "Percentage of incoming calls to this
                  adjacency failing to be setup due to
                  Number Analysis (compared to attempts)"
    ::= { perimetaAdjacencyStatsEntry 97 }

  adjStatDstFailuresNumberAnalysis OBJECT-TYPE
    SYNTAX       CounterBasedGauge64
    UNITS        "/ 10000 %"
    MAX-ACCESS   read-only
    STATUS       current
    DESCRIPTION  "Percentage of outgoing calls from this
                  adjacency failing to be setup due to
                  Number Analysis (compared to attempts)"
    ::= { perimetaAdjacencyStatsEntry 98 }

  adjStatSrcFailuresRouting OBJECT-TYPE
    SYNTAX       CounterBasedGauge64
    UNITS        "/ 10000 %"
    MAX-ACCESS   read-only
    STATUS       current
    DESCRIPTION  "Percentage of incoming calls to this
                  adjacency failing to be setup due to
                  Routing (compared to attempts)"
    ::= { perimetaAdjacencyStatsEntry 99 }

  adjStatDstFailuresRouting OBJECT-TYPE
    SYNTAX       CounterBasedGauge64
    UNITS        "/ 10000 %"
    MAX-ACCESS   read-only
    STATUS       current
    DESCRIPTION  "Percentage of outgoing calls from this
                  adjacency failing to be setup due to
                  Routing (compared to attempts)"
    ::= { perimetaAdjacencyStatsEntry 100 }

  adjStatSrcFailuresCapacityControl OBJECT-TYPE
    SYNTAX       CounterBasedGauge64
    UNITS        "/ 10000 %"
    MAX-ACCESS   read-only
    STATUS       current
    DESCRIPTION  "Percentage of incoming calls to this
                  adjacency failing to be setup due to
                  Capacity Control (compared to attempts)"
    ::= { perimetaAdjacencyStatsEntry 101 }

  adjStatDstFailuresCapacityControl OBJECT-TYPE
    SYNTAX       CounterBasedGauge64
    UNITS        "/ 10000 %"
    MAX-ACCESS   read-only
    STATUS       current
    DESCRIPTION  "Percentage of outgoing calls from this
                  adjacency failing to be setup due to
                  Capacity Control (compared to attempts)"
    ::= { perimetaAdjacencyStatsEntry 102 }

  adjStatSrcFailuresUnsupCodecs OBJECT-TYPE
    SYNTAX       CounterBasedGauge64
    UNITS        "/ 10000 %"
    MAX-ACCESS   read-only
    STATUS       current
    DESCRIPTION  "Percentage of incoming calls to this
                  adjacency failing to be setup due to
                  Unsupported Codecs (compared to
                  attempts)"
    ::= { perimetaAdjacencyStatsEntry 103 }

  adjStatDstFailuresUnsupCodecs OBJECT-TYPE
    SYNTAX       CounterBasedGauge64
    UNITS        "/ 10000 %"
    MAX-ACCESS   read-only
    STATUS       current
    DESCRIPTION  "Percentage of outgoing calls from this
                  adjacency failing to be setup due to
                  Unsupported Codecs (compared to
                  attempts)"
    ::= { perimetaAdjacencyStatsEntry 104 }

  adjStatSrcFailuresAfterSetup OBJECT-TYPE
    SYNTAX       CounterBasedGauge64
    UNITS        "/ 10000 %"
    MAX-ACCESS   read-only
    STATUS       current
    DESCRIPTION  "Percentage of incoming calls to this
                  adjacency failing after successful setup
                  (compared to attempts)"
    ::= { perimetaAdjacencyStatsEntry 105 }

  adjStatDstFailuresAfterSetup OBJECT-TYPE
    SYNTAX       CounterBasedGauge64
    UNITS        "/ 10000 %"
    MAX-ACCESS   read-only
    STATUS       current
    DESCRIPTION  "Percentage of outgoing calls from this
                  adjacency failing after successful setup
                  (compared to attempts)"
    ::= { perimetaAdjacencyStatsEntry 106 }

  adjStatSrcCapCtrlRejectedAnyReasonLastPeriod OBJECT-TYPE
    SYNTAX       CounterBasedGauge64
    MAX-ACCESS   read-only
    STATUS       current
    DESCRIPTION  "The total number of incoming calls to
                  this adjacency rejected by Capacity
                  Control for any reason over the last
                  period"
    ::= { perimetaAdjacencyStatsEntry 117 }

  adjStatDstCapCtrlRejectedAnyReasonLastPeriod OBJECT-TYPE
    SYNTAX       CounterBasedGauge64
    MAX-ACCESS   read-only
    STATUS       current
    DESCRIPTION  "The total number of outgoing calls from
                  this adjacency rejected by Capacity
                  Control for any reason over the last
                  period"
    ::= { perimetaAdjacencyStatsEntry 118 }

  adjStatSrcCapCtrlRejectedBandwidthLimitLastPeriod OBJECT-TYPE
    SYNTAX       CounterBasedGauge64
    MAX-ACCESS   read-only
    STATUS       current
    DESCRIPTION  "The total number of incoming calls to
                  this adjacency rejected by Capacity
                  Control due to bandwidth limits over the
                  last period"
    ::= { perimetaAdjacencyStatsEntry 119 }

  adjStatDstCapCtrlRejectedBandwidthLimitLastPeriod OBJECT-TYPE
    SYNTAX       CounterBasedGauge64
    MAX-ACCESS   read-only
    STATUS       current
    DESCRIPTION  "The total number of outgoing calls from
                  this adjacency rejected by Capacity
                  Control due to bandwidth limits over the
                  last period"
    ::= { perimetaAdjacencyStatsEntry 120 }

  adjStatSrcCapCtrlRejectedTotalConcurrentLastPeriod OBJECT-TYPE
    SYNTAX       CounterBasedGauge64
    MAX-ACCESS   read-only
    STATUS       current
    DESCRIPTION  "The total number of incoming calls to
                  this adjacency rejected by Capacity
                  Control due to the total concurrent
                  calls limit over the last period"
    ::= { perimetaAdjacencyStatsEntry 121 }

  adjStatDstCapCtrlRejectedTotalConcurrentLastPeriod OBJECT-TYPE
    SYNTAX       CounterBasedGauge64
    MAX-ACCESS   read-only
    STATUS       current
    DESCRIPTION  "The total number of outgoing calls from
                  this adjacency rejected by Capacity
                  Control due to the total concurrent
                  calls limit over the last period"
    ::= { perimetaAdjacencyStatsEntry 122 }

  adjStatRTPPacketsReceivedLastPeriod OBJECT-TYPE
    SYNTAX       CounterBasedGauge64
    MAX-ACCESS   read-only
    STATUS       current
    DESCRIPTION  "Count of RTP packets received on this
                  adjacency over the last period"
    ::= { perimetaAdjacencyStatsEntry 123 }

  adjStatRTPPacketsSentLastPeriod OBJECT-TYPE
    SYNTAX       CounterBasedGauge64
    MAX-ACCESS   read-only
    STATUS       current
    DESCRIPTION  "Count of RTP packets sent from this
                  adjacency over the last period"
    ::= { perimetaAdjacencyStatsEntry 124 }

  adjStatRTPPacketsDroppedLastPeriod OBJECT-TYPE
    SYNTAX       CounterBasedGauge64
    MAX-ACCESS   read-only
    STATUS       current
    DESCRIPTION  "Count of RTP packets dropped by Perimeta
                  due to congestion on this adjacency over
                  the last period"
    ::= { perimetaAdjacencyStatsEntry 125 }

  adjStatRTPPacketsLostLastPeriod OBJECT-TYPE
    SYNTAX       CounterBasedGauge64
    MAX-ACCESS   read-only
    STATUS       current
    DESCRIPTION  "Count of RTP packets reported as lost on
                  this adjacency over the last period"
    ::= { perimetaAdjacencyStatsEntry 126 }

  adjStatRTPAvgRoundTripDelayLast5Min OBJECT-TYPE
    SYNTAX       CounterBasedGauge64
    MAX-ACCESS   read-only
    STATUS       current
    DESCRIPTION  "Moving average with averaging period 5
                  minutes of the round-trip delay for RTP
                  packets on this adjacency"
    ::= { perimetaAdjacencyStatsEntry 127 }

  adjStatRTPAvgRemoteJitterLast5Min OBJECT-TYPE
    SYNTAX       CounterBasedGauge64
    MAX-ACCESS   read-only
    STATUS       current
    DESCRIPTION  "Moving average with averaging period 5
                  minutes of the jitter on the media
                  streams reported by remote devices on
                  this adjacency"
    ::= { perimetaAdjacencyStatsEntry 128 }

  adjStatSrcInbDTMFCalls OBJECT-TYPE
    SYNTAX       CounterBasedGauge64
    MAX-ACCESS   read-only
    STATUS       current
    DESCRIPTION  "Currently active calls with inband DTMF
                  detection incoming to this adjacency"
    ::= { perimetaAdjacencyStatsEntry 133 }

  adjStatDstInbDTMFCalls OBJECT-TYPE
    SYNTAX       CounterBasedGauge64
    MAX-ACCESS   read-only
    STATUS       current
    DESCRIPTION  "Currently active calls with inband DTMF
                  detection outgoing from this adjacency"
    ::= { perimetaAdjacencyStatsEntry 134 }

  adjStatSrcInbDTMFCallRate OBJECT-TYPE
    SYNTAX       CounterBasedGauge64
    MAX-ACCESS   read-only
    STATUS       current
    DESCRIPTION  "Rate of incoming calls with inband DTMF
                  detection setup to this adjacency"
    ::= { perimetaAdjacencyStatsEntry 135 }

  adjStatDstInbDTMFCallRate OBJECT-TYPE
    SYNTAX       CounterBasedGauge64
    MAX-ACCESS   read-only
    STATUS       current
    DESCRIPTION  "Rate of outgoing calls with inband DTMF
                  detection setup from this adjacency"
    ::= { perimetaAdjacencyStatsEntry 136 }

  adjStatRTPBytesSent OBJECT-TYPE
    SYNTAX       CounterBasedGauge64
    MAX-ACCESS   read-only
    STATUS       current
    DESCRIPTION  "Count of RTP bytes sent over the last
                  period"
    ::= { perimetaAdjacencyStatsEntry 139 }

  adjStatRTPBytesReceived OBJECT-TYPE
    SYNTAX       CounterBasedGauge64
    MAX-ACCESS   read-only
    STATUS       current
    DESCRIPTION  "Count of RTP bytes received over the
                  last period"
    ::= { perimetaAdjacencyStatsEntry 140 }

  adjStatRTPBandwidthSent OBJECT-TYPE
    SYNTAX       CounterBasedGauge64
    MAX-ACCESS   read-only
    STATUS       current
    DESCRIPTION  "Bandwidth of RTP sent over the last
                  period"
    ::= { perimetaAdjacencyStatsEntry 141 }

  adjStatRTPBandwidthReceived OBJECT-TYPE
    SYNTAX       CounterBasedGauge64
    MAX-ACCESS   read-only
    STATUS       current
    DESCRIPTION  "Bandwidth of RTP received over the last
                  period"
    ::= { perimetaAdjacencyStatsEntry 142 }

  adjStatRTPBandwidthSentPercent OBJECT-TYPE
    SYNTAX       CounterBasedGauge64
    UNITS        "/ 10000 %"
    MAX-ACCESS   read-only
    STATUS       current
    DESCRIPTION  "Bandwidth of RTP sent over the last
                  period as a percent of global RTP
                  bandwidth sent"
    ::= { perimetaAdjacencyStatsEntry 143 }

  adjStatRTPBandwidthReceivedPercent OBJECT-TYPE
    SYNTAX       CounterBasedGauge64
    UNITS        "/ 10000 %"
    MAX-ACCESS   read-only
    STATUS       current
    DESCRIPTION  "Bandwidth of RTP received over the last
                  period as a percent of global RTP
                  bandwidth received"
    ::= { perimetaAdjacencyStatsEntry 144 }

  adjStatMaxPacketDrop OBJECT-TYPE
    SYNTAX       CounterBasedGauge64
    UNITS        "/ 10000000 %"
    MAX-ACCESS   read-only
    STATUS       current
    DESCRIPTION  "The max percentage of packets dropped in
                  any call"
    ::= { perimetaAdjacencyStatsEntry 145 }

  adjStatAveragePacketDrop OBJECT-TYPE
    SYNTAX       CounterBasedGauge64
    UNITS        "/ 10000000 %"
    MAX-ACCESS   read-only
    STATUS       current
    DESCRIPTION  "The average percentage of packets
                  dropped in calls"
    ::= { perimetaAdjacencyStatsEntry 146 }

  adjStatMaxPacketLoss OBJECT-TYPE
    SYNTAX       CounterBasedGauge64
    UNITS        "/ 10000000 %"
    MAX-ACCESS   read-only
    STATUS       current
    DESCRIPTION  "The max percentage of packets lost by
                  the endpoint in any call"
    ::= { perimetaAdjacencyStatsEntry 147 }

  adjStatAveragePacketLoss OBJECT-TYPE
    SYNTAX       CounterBasedGauge64
    UNITS        "/ 10000000 %"
    MAX-ACCESS   read-only
    STATUS       current
    DESCRIPTION  "The average percentage of packets lost
                  by the endpoint in calls"
    ::= { perimetaAdjacencyStatsEntry 148 }

  adjStatMaxRemoteJitter OBJECT-TYPE
    SYNTAX       CounterBasedGauge64
    UNITS        "/ 100"
    MAX-ACCESS   read-only
    STATUS       current
    DESCRIPTION  "The max remote jitter in any call"
    ::= { perimetaAdjacencyStatsEntry 149 }

  adjStatAverageMaxRemoteJitter OBJECT-TYPE
    SYNTAX       CounterBasedGauge64
    UNITS        "/ 100"
    MAX-ACCESS   read-only
    STATUS       current
    DESCRIPTION  "The average max remote jitter of calls"
    ::= { perimetaAdjacencyStatsEntry 150 }

  adjStatMaxAverageRoundTripDelay OBJECT-TYPE
    SYNTAX       CounterBasedGauge64
    UNITS        "/ 100"
    MAX-ACCESS   read-only
    STATUS       current
    DESCRIPTION  "The max average round trip delay in any
                  call"
    ::= { perimetaAdjacencyStatsEntry 151 }

  adjStatAverageRoundTripDelay OBJECT-TYPE
    SYNTAX       CounterBasedGauge64
    UNITS        "/ 100"
    MAX-ACCESS   read-only
    STATUS       current
    DESCRIPTION  "The average round trip delay in calls"
    ::= { perimetaAdjacencyStatsEntry 152 }

  adjStatCodecUsageOther OBJECT-TYPE
    SYNTAX       CounterBasedGauge64
    MAX-ACCESS   read-only
    STATUS       current
    DESCRIPTION  "The number of streams using codecs that
                  do not fall under another stat"
    ::= { perimetaAdjacencyStatsEntry 153 }

  adjStatCodecUsageG711U OBJECT-TYPE
    SYNTAX       CounterBasedGauge64
    MAX-ACCESS   read-only
    STATUS       current
    DESCRIPTION  "The number of streams using G711U"
    ::= { perimetaAdjacencyStatsEntry 154 }

  adjStatCodecUsageG711A OBJECT-TYPE
    SYNTAX       CounterBasedGauge64
    MAX-ACCESS   read-only
    STATUS       current
    DESCRIPTION  "The number of streams using G711A"
    ::= { perimetaAdjacencyStatsEntry 155 }

  adjStatCodecUsageG722 OBJECT-TYPE
    SYNTAX       CounterBasedGauge64
    MAX-ACCESS   read-only
    STATUS       current
    DESCRIPTION  "The number of streams using G722"
    ::= { perimetaAdjacencyStatsEntry 156 }

  adjStatCodecUsageG7231 OBJECT-TYPE
    SYNTAX       CounterBasedGauge64
    MAX-ACCESS   read-only
    STATUS       current
    DESCRIPTION  "The number of streams using G723(1)"
    ::= { perimetaAdjacencyStatsEntry 157 }

  adjStatCodecUsageG726 OBJECT-TYPE
    SYNTAX       CounterBasedGauge64
    MAX-ACCESS   read-only
    STATUS       current
    DESCRIPTION  "The number of streams using G726"
    ::= { perimetaAdjacencyStatsEntry 158 }

  adjStatCodecUsageG729 OBJECT-TYPE
    SYNTAX       CounterBasedGauge64
    MAX-ACCESS   read-only
    STATUS       current
    DESCRIPTION  "The number of streams using G729"
    ::= { perimetaAdjacencyStatsEntry 159 }

  adjStatCodecUsageT38 OBJECT-TYPE
    SYNTAX       CounterBasedGauge64
    MAX-ACCESS   read-only
    STATUS       current
    DESCRIPTION  "The number of streams using T38"
    ::= { perimetaAdjacencyStatsEntry 160 }

  adjStatCodecUsageAMRNB OBJECT-TYPE
    SYNTAX       CounterBasedGauge64
    MAX-ACCESS   read-only
    STATUS       current
    DESCRIPTION  "The number of streams using AMR(-NB)"
    ::= { perimetaAdjacencyStatsEntry 161 }

  adjStatCodecUsageAMRWB OBJECT-TYPE
    SYNTAX       CounterBasedGauge64
    MAX-ACCESS   read-only
    STATUS       current
    DESCRIPTION  "The number of streams using AMR-WB"
    ::= { perimetaAdjacencyStatsEntry 162 }

  adjStatCodecUsageClearmode OBJECT-TYPE
    SYNTAX       CounterBasedGauge64
    MAX-ACCESS   read-only
    STATUS       current
    DESCRIPTION  "The number of streams using Clearmode"
    ::= { perimetaAdjacencyStatsEntry 163 }

  adjStatCodecUsageGSMFR OBJECT-TYPE
    SYNTAX       CounterBasedGauge64
    MAX-ACCESS   read-only
    STATUS       current
    DESCRIPTION  "The number of streams using GSM(-FR)"
    ::= { perimetaAdjacencyStatsEntry 164 }

  adjStatCodecUsageGSMEFR OBJECT-TYPE
    SYNTAX       CounterBasedGauge64
    MAX-ACCESS   read-only
    STATUS       current
    DESCRIPTION  "The number of streams using GSM-EFR"
    ::= { perimetaAdjacencyStatsEntry 165 }

  adjStatCodecUsageGSMHR OBJECT-TYPE
    SYNTAX       CounterBasedGauge64
    MAX-ACCESS   read-only
    STATUS       current
    DESCRIPTION  "The number of streams using GSM-HR"
    ::= { perimetaAdjacencyStatsEntry 166 }

  adjStatCodecUsageEVRC OBJECT-TYPE
    SYNTAX       CounterBasedGauge64
    MAX-ACCESS   read-only
    STATUS       current
    DESCRIPTION  "The number of streams using EVRC"
    ::= { perimetaAdjacencyStatsEntry 167 }

  adjStatCodecUsageiLBC OBJECT-TYPE
    SYNTAX       CounterBasedGauge64
    MAX-ACCESS   read-only
    STATUS       current
    DESCRIPTION  "The number of streams using iLBC"
    ::= { perimetaAdjacencyStatsEntry 169 }

  adjStatCodecUsageSILK OBJECT-TYPE
    SYNTAX       CounterBasedGauge64
    MAX-ACCESS   read-only
    STATUS       current
    DESCRIPTION  "The number of streams using SILK"
    ::= { perimetaAdjacencyStatsEntry 170 }

  adjStatNumCallsHwm OBJECT-TYPE
    SYNTAX       CounterBasedGauge64
    MAX-ACCESS   read-only
    STATUS       current
    DESCRIPTION  "High water mark of active calls within
                  adjacency"
    ::= { perimetaAdjacencyStatsEntry 195 }

  adjStatMedBwHwm OBJECT-TYPE
    SYNTAX       CounterBasedGauge64
    MAX-ACCESS   read-only
    STATUS       current
    DESCRIPTION  "High water mark of media bandwidth
                  within adjacency"
    ::= { perimetaAdjacencyStatsEntry 196 }

  adjStatMedStreamsHwm OBJECT-TYPE
    SYNTAX       CounterBasedGauge64
    MAX-ACCESS   read-only
    STATUS       current
    DESCRIPTION  "High water mark of media streams within
                  adjacency"
    ::= { perimetaAdjacencyStatsEntry 197 }

  adjStatNumRegsHwm OBJECT-TYPE
    SYNTAX       CounterBasedGauge64
    MAX-ACCESS   read-only
    STATUS       current
    DESCRIPTION  "High water mark of concurrent
                  registrations within adjacency"
    ::= { perimetaAdjacencyStatsEntry 198 }

  adjStatCallBurstRateHwm OBJECT-TYPE
    SYNTAX       CounterBasedGauge64
    MAX-ACCESS   read-only
    STATUS       current
    DESCRIPTION  "High water mark of burst rate of call
                  setup within adjacency"
    ::= { perimetaAdjacencyStatsEntry 199 }

  adjStatCallSustainRateHwm OBJECT-TYPE
    SYNTAX       CounterBasedGauge64
    MAX-ACCESS   read-only
    STATUS       current
    DESCRIPTION  "High water mark of sustained rate of
                  call setup within adjacency"
    ::= { perimetaAdjacencyStatsEntry 200 }

  adjStatInCallBurstRateHwm OBJECT-TYPE
    SYNTAX       CounterBasedGauge64
    MAX-ACCESS   read-only
    STATUS       current
    DESCRIPTION  "High water mark of burst rate of in-call
                  messages within adjacency"
    ::= { perimetaAdjacencyStatsEntry 201 }

  adjStatInCallSustainRateHwm OBJECT-TYPE
    SYNTAX       CounterBasedGauge64
    MAX-ACCESS   read-only
    STATUS       current
    DESCRIPTION  "High water mark of sustained rate of
                  in-call messages within adjacency"
    ::= { perimetaAdjacencyStatsEntry 202 }

  adjStatOOCBurstRateHwm OBJECT-TYPE
    SYNTAX       CounterBasedGauge64
    MAX-ACCESS   read-only
    STATUS       current
    DESCRIPTION  "High water mark of burst rate of
                  out-of-call messages within adjacency"
    ::= { perimetaAdjacencyStatsEntry 203 }

  adjStatOOCSustainRateHwm OBJECT-TYPE
    SYNTAX       CounterBasedGauge64
    MAX-ACCESS   read-only
    STATUS       current
    DESCRIPTION  "High water mark of sustained rate of
                  out-of-call messages within the
                  adjacency"
    ::= { perimetaAdjacencyStatsEntry 204 }

  adjStatRegsBurstRateHwm OBJECT-TYPE
    SYNTAX       CounterBasedGauge64
    MAX-ACCESS   read-only
    STATUS       current
    DESCRIPTION  "High water mark of burst rate of
                  registration within adjacency"
    ::= { perimetaAdjacencyStatsEntry 205 }

  adjStatRegsSustainRateHwm OBJECT-TYPE
    SYNTAX       CounterBasedGauge64
    MAX-ACCESS   read-only
    STATUS       current
    DESCRIPTION  "High water mark of sustained rate of
                  registration within adjacency"
    ::= { perimetaAdjacencyStatsEntry 206 }

  adjStatNumCallsPerc OBJECT-TYPE
    SYNTAX       CounterBasedGauge64
    UNITS        "/ 10000 %"
    MAX-ACCESS   read-only
    STATUS       current
    DESCRIPTION  "% of currently active calls versus call
                  limit within adjacency"
    ::= { perimetaAdjacencyStatsEntry 207 }

  adjStatMedBwPerc OBJECT-TYPE
    SYNTAX       CounterBasedGauge64
    UNITS        "/ 10000 %"
    MAX-ACCESS   read-only
    STATUS       current
    DESCRIPTION  "% of media bandwidth versus bandwidth
                  limit within adjacency"
    ::= { perimetaAdjacencyStatsEntry 208 }

  adjStatMedStrPerc OBJECT-TYPE
    SYNTAX       CounterBasedGauge64
    UNITS        "/ 10000 %"
    MAX-ACCESS   read-only
    STATUS       current
    DESCRIPTION  "% of media streams versus limit within
                  adjacency"
    ::= { perimetaAdjacencyStatsEntry 209 }

  adjStatNumRegsPerc OBJECT-TYPE
    SYNTAX       CounterBasedGauge64
    UNITS        "/ 10000 %"
    MAX-ACCESS   read-only
    STATUS       current
    DESCRIPTION  "% of registrations versus limit within
                  adjacency"
    ::= { perimetaAdjacencyStatsEntry 210 }

  adjStatCallBurstRatePerc OBJECT-TYPE
    SYNTAX       CounterBasedGauge64
    UNITS        "/ 10000 %"
    MAX-ACCESS   read-only
    STATUS       current
    DESCRIPTION  "% of burst call rate versus limit within
                  adjacency"
    ::= { perimetaAdjacencyStatsEntry 211 }

  adjStatCallSustainRatePerc OBJECT-TYPE
    SYNTAX       CounterBasedGauge64
    UNITS        "/ 10000 %"
    MAX-ACCESS   read-only
    STATUS       current
    DESCRIPTION  "% of sustained call rate versus limit
                  within adjacency"
    ::= { perimetaAdjacencyStatsEntry 212 }

  adjStatInCallBurstRatePerc OBJECT-TYPE
    SYNTAX       CounterBasedGauge64
    UNITS        "/ 10000 %"
    MAX-ACCESS   read-only
    STATUS       current
    DESCRIPTION  "% of burst in-call message rate versus
                  limit within adjacency"
    ::= { perimetaAdjacencyStatsEntry 213 }

  adjStatInCallSustainRatePerc OBJECT-TYPE
    SYNTAX       CounterBasedGauge64
    UNITS        "/ 10000 %"
    MAX-ACCESS   read-only
    STATUS       current
    DESCRIPTION  "% of sustained in-call message rate
                  versus limit within adjacency"
    ::= { perimetaAdjacencyStatsEntry 214 }

  adjStatOOCBurstRatePerc OBJECT-TYPE
    SYNTAX       CounterBasedGauge64
    UNITS        "/ 10000 %"
    MAX-ACCESS   read-only
    STATUS       current
    DESCRIPTION  "% of burst out-of-call message rate
                  versus limit within adjacency"
    ::= { perimetaAdjacencyStatsEntry 215 }

  adjStatOOCSustainRatePerc OBJECT-TYPE
    SYNTAX       CounterBasedGauge64
    UNITS        "/ 10000 %"
    MAX-ACCESS   read-only
    STATUS       current
    DESCRIPTION  "% of sustained out-of-call message rate
                  versus limit within adjacency"
    ::= { perimetaAdjacencyStatsEntry 216 }

  adjStatRegsBurstRatePerc OBJECT-TYPE
    SYNTAX       CounterBasedGauge64
    UNITS        "/ 10000 %"
    MAX-ACCESS   read-only
    STATUS       current
    DESCRIPTION  "% of burst registration rate versus
                  limit within adjacency"
    ::= { perimetaAdjacencyStatsEntry 217 }

  adjStatRegsSustainRatePerc OBJECT-TYPE
    SYNTAX       CounterBasedGauge64
    UNITS        "/ 10000 %"
    MAX-ACCESS   read-only
    STATUS       current
    DESCRIPTION  "% of sustained registration rate versus
                  limit within adjacency"
    ::= { perimetaAdjacencyStatsEntry 218 }

  adjStatSrcNumCallsHwm OBJECT-TYPE
    SYNTAX       CounterBasedGauge64
    MAX-ACCESS   read-only
    STATUS       current
    DESCRIPTION  "High water mark of calls within source
                  adjacency"
    ::= { perimetaAdjacencyStatsEntry 243 }

  adjStatSrcMedBwHwm OBJECT-TYPE
    SYNTAX       CounterBasedGauge64
    MAX-ACCESS   read-only
    STATUS       current
    DESCRIPTION  "High water mark of media bandwidth
                  within source adjacency"
    ::= { perimetaAdjacencyStatsEntry 244 }

  adjStatSrcMedStreamsHwm OBJECT-TYPE
    SYNTAX       CounterBasedGauge64
    MAX-ACCESS   read-only
    STATUS       current
    DESCRIPTION  "High water mark of media streams within
                  source adjacency"
    ::= { perimetaAdjacencyStatsEntry 245 }

  adjStatSrcNumRegsHwm OBJECT-TYPE
    SYNTAX       CounterBasedGauge64
    MAX-ACCESS   read-only
    STATUS       current
    DESCRIPTION  "High water mark of concurrent
                  registrations within source adjacency"
    ::= { perimetaAdjacencyStatsEntry 246 }

  adjStatSrcCallBurstRateHwm OBJECT-TYPE
    SYNTAX       CounterBasedGauge64
    MAX-ACCESS   read-only
    STATUS       current
    DESCRIPTION  "High water mark of burst rate of call
                  setup within source adjacency"
    ::= { perimetaAdjacencyStatsEntry 247 }

  adjStatSrcCallSustainRateHwm OBJECT-TYPE
    SYNTAX       CounterBasedGauge64
    MAX-ACCESS   read-only
    STATUS       current
    DESCRIPTION  "High water mark of sustained rate of
                  call setup within source adjacency"
    ::= { perimetaAdjacencyStatsEntry 248 }

  adjStatSrcInCallBurstRateHwm OBJECT-TYPE
    SYNTAX       CounterBasedGauge64
    MAX-ACCESS   read-only
    STATUS       current
    DESCRIPTION  "High water mark of burst rate of in-call
                  messages within source adjacency"
    ::= { perimetaAdjacencyStatsEntry 249 }

  adjStatSrcInCallSustainRateHwm OBJECT-TYPE
    SYNTAX       CounterBasedGauge64
    MAX-ACCESS   read-only
    STATUS       current
    DESCRIPTION  "High water mark of sustained rate of
                  in-call messages within source adjacency"
    ::= { perimetaAdjacencyStatsEntry 250 }

  adjStatSrcOOCBurstRateHwm OBJECT-TYPE
    SYNTAX       CounterBasedGauge64
    MAX-ACCESS   read-only
    STATUS       current
    DESCRIPTION  "High water mark of burst rate of
                  out-of-call messages within source
                  adjacency"
    ::= { perimetaAdjacencyStatsEntry 251 }

  adjStatSrcOOCSustainRateHwm OBJECT-TYPE
    SYNTAX       CounterBasedGauge64
    MAX-ACCESS   read-only
    STATUS       current
    DESCRIPTION  "High water mark of sustained rate of
                  out-of-call messages within the source
                  adjacency"
    ::= { perimetaAdjacencyStatsEntry 252 }

  adjStatSrcRegsBurstRateHwm OBJECT-TYPE
    SYNTAX       CounterBasedGauge64
    MAX-ACCESS   read-only
    STATUS       current
    DESCRIPTION  "High water mark of burst rate of
                  registration within source adjacency"
    ::= { perimetaAdjacencyStatsEntry 253 }

  adjStatSrcRegsSustainRateHwm OBJECT-TYPE
    SYNTAX       CounterBasedGauge64
    MAX-ACCESS   read-only
    STATUS       current
    DESCRIPTION  "High water mark of sustained rate of
                  registration within source adjacency"
    ::= { perimetaAdjacencyStatsEntry 254 }

  adjStatSrcNumCallsPerc OBJECT-TYPE
    SYNTAX       CounterBasedGauge64
    UNITS        "/ 10000 %"
    MAX-ACCESS   read-only
    STATUS       current
    DESCRIPTION  "% of currently active calls versus call
                  limit within source adjacency"
    ::= { perimetaAdjacencyStatsEntry 255 }

  adjStatSrcMedBwPerc OBJECT-TYPE
    SYNTAX       CounterBasedGauge64
    UNITS        "/ 10000 %"
    MAX-ACCESS   read-only
    STATUS       current
    DESCRIPTION  "% of media bandwidth versus bandwidth
                  limit within source adjacency"
    ::= { perimetaAdjacencyStatsEntry 256 }

  adjStatSrcMedStrPerc OBJECT-TYPE
    SYNTAX       CounterBasedGauge64
    UNITS        "/ 10000 %"
    MAX-ACCESS   read-only
    STATUS       current
    DESCRIPTION  "% of media streams versus limit within
                  source adjacency"
    ::= { perimetaAdjacencyStatsEntry 257 }

  adjStatSrcNumRegsPerc OBJECT-TYPE
    SYNTAX       CounterBasedGauge64
    UNITS        "/ 10000 %"
    MAX-ACCESS   read-only
    STATUS       current
    DESCRIPTION  "% of registrations versus limit within
                  source adjacency"
    ::= { perimetaAdjacencyStatsEntry 258 }

  adjStatSrcCallBurstRatePerc OBJECT-TYPE
    SYNTAX       CounterBasedGauge64
    UNITS        "/ 10000 %"
    MAX-ACCESS   read-only
    STATUS       current
    DESCRIPTION  "% of burst call rate versus limit within
                  source adjacency"
    ::= { perimetaAdjacencyStatsEntry 259 }

  adjStatSrcCallSustainRatePerc OBJECT-TYPE
    SYNTAX       CounterBasedGauge64
    UNITS        "/ 10000 %"
    MAX-ACCESS   read-only
    STATUS       current
    DESCRIPTION  "% of sustained call rate versus limit
                  within source adjacency"
    ::= { perimetaAdjacencyStatsEntry 260 }

  adjStatSrcInCallBurstRatePerc OBJECT-TYPE
    SYNTAX       CounterBasedGauge64
    UNITS        "/ 10000 %"
    MAX-ACCESS   read-only
    STATUS       current
    DESCRIPTION  "% of burst in-call message rate versus
                  limit within source adjacency"
    ::= { perimetaAdjacencyStatsEntry 261 }

  adjStatSrcInCallSustainRatePerc OBJECT-TYPE
    SYNTAX       CounterBasedGauge64
    UNITS        "/ 10000 %"
    MAX-ACCESS   read-only
    STATUS       current
    DESCRIPTION  "% of sustained in-call message rate
                  versus limit within source adjacency"
    ::= { perimetaAdjacencyStatsEntry 262 }

  adjStatSrcOOCBurstRatePerc OBJECT-TYPE
    SYNTAX       CounterBasedGauge64
    UNITS        "/ 10000 %"
    MAX-ACCESS   read-only
    STATUS       current
    DESCRIPTION  "% of burst out-of-call message rate
                  versus limit within source adjacency"
    ::= { perimetaAdjacencyStatsEntry 263 }

  adjStatSrcOOCSustainRatePerc OBJECT-TYPE
    SYNTAX       CounterBasedGauge64
    UNITS        "/ 10000 %"
    MAX-ACCESS   read-only
    STATUS       current
    DESCRIPTION  "% of sustained out-of-call message rate
                  versus limit within source adjacency"
    ::= { perimetaAdjacencyStatsEntry 264 }

  adjStatSrcRegsBurstRatePerc OBJECT-TYPE
    SYNTAX       CounterBasedGauge64
    UNITS        "/ 10000 %"
    MAX-ACCESS   read-only
    STATUS       current
    DESCRIPTION  "% of burst registration rate versus
                  limit within source adjacency"
    ::= { perimetaAdjacencyStatsEntry 265 }

  adjStatSrcRegsSustainRatePerc OBJECT-TYPE
    SYNTAX       CounterBasedGauge64
    UNITS        "/ 10000 %"
    MAX-ACCESS   read-only
    STATUS       current
    DESCRIPTION  "% of sustained registration rate versus
                  limit within source adjacency"
    ::= { perimetaAdjacencyStatsEntry 266 }

  adjStatDstNumCallsHwm OBJECT-TYPE
    SYNTAX       CounterBasedGauge64
    MAX-ACCESS   read-only
    STATUS       current
    DESCRIPTION  "High water mark of calls within
                  destination adjacency"
    ::= { perimetaAdjacencyStatsEntry 291 }

  adjStatDstMedBwHwm OBJECT-TYPE
    SYNTAX       CounterBasedGauge64
    MAX-ACCESS   read-only
    STATUS       current
    DESCRIPTION  "High water mark of media bandwidth
                  within destination adjacency"
    ::= { perimetaAdjacencyStatsEntry 292 }

  adjStatDstMedStreamsHwm OBJECT-TYPE
    SYNTAX       CounterBasedGauge64
    MAX-ACCESS   read-only
    STATUS       current
    DESCRIPTION  "High water mark of media streams within
                  destination adjacency"
    ::= { perimetaAdjacencyStatsEntry 293 }

  adjStatDstNumRegsHwm OBJECT-TYPE
    SYNTAX       CounterBasedGauge64
    MAX-ACCESS   read-only
    STATUS       current
    DESCRIPTION  "High water mark of concurrent
                  registrations within destination
                  adjacency"
    ::= { perimetaAdjacencyStatsEntry 294 }

  adjStatDstCallBurstRateHwm OBJECT-TYPE
    SYNTAX       CounterBasedGauge64
    MAX-ACCESS   read-only
    STATUS       current
    DESCRIPTION  "High water mark of burst rate of call
                  setup within destination adjacency"
    ::= { perimetaAdjacencyStatsEntry 295 }

  adjStatDstCallSustainRateHwm OBJECT-TYPE
    SYNTAX       CounterBasedGauge64
    MAX-ACCESS   read-only
    STATUS       current
    DESCRIPTION  "High water mark of sustained rate of
                  call setup within destination adjacency"
    ::= { perimetaAdjacencyStatsEntry 296 }

  adjStatDstInCallBurstRateHwm OBJECT-TYPE
    SYNTAX       CounterBasedGauge64
    MAX-ACCESS   read-only
    STATUS       current
    DESCRIPTION  "High water mark of burst rate of in-call
                  messages within destination adjacency"
    ::= { perimetaAdjacencyStatsEntry 297 }

  adjStatDstInCallSustainRateHwm OBJECT-TYPE
    SYNTAX       CounterBasedGauge64
    MAX-ACCESS   read-only
    STATUS       current
    DESCRIPTION  "High water mark of sustained rate of
                  in-call messages within destination
                  adjacency"
    ::= { perimetaAdjacencyStatsEntry 298 }

  adjStatDstOOCBurstRateHwm OBJECT-TYPE
    SYNTAX       CounterBasedGauge64
    MAX-ACCESS   read-only
    STATUS       current
    DESCRIPTION  "High water mark of burst rate of
                  out-of-call messages within destination
                  adjacency"
    ::= { perimetaAdjacencyStatsEntry 299 }

  adjStatDstOOCSustainRateHwm OBJECT-TYPE
    SYNTAX       CounterBasedGauge64
    MAX-ACCESS   read-only
    STATUS       current
    DESCRIPTION  "High water mark of sustained rate of
                  out-of-call messages within the
                  destination adjacency"
    ::= { perimetaAdjacencyStatsEntry 300 }

  adjStatDstRegsBurstRateHwm OBJECT-TYPE
    SYNTAX       CounterBasedGauge64
    MAX-ACCESS   read-only
    STATUS       current
    DESCRIPTION  "High water mark of burst rate of
                  registration within destination
                  adjacency"
    ::= { perimetaAdjacencyStatsEntry 301 }

  adjStatDstRegsSustainRateHwm OBJECT-TYPE
    SYNTAX       CounterBasedGauge64
    MAX-ACCESS   read-only
    STATUS       current
    DESCRIPTION  "High water mark of sustained rate of
                  registration within destination
                  adjacency"
    ::= { perimetaAdjacencyStatsEntry 302 }

  adjStatDstNumCallsPerc OBJECT-TYPE
    SYNTAX       CounterBasedGauge64
    UNITS        "/ 10000 %"
    MAX-ACCESS   read-only
    STATUS       current
    DESCRIPTION  "% of currently active calls versus call
                  limit within destination adjacency"
    ::= { perimetaAdjacencyStatsEntry 303 }

  adjStatDstMedBwPerc OBJECT-TYPE
    SYNTAX       CounterBasedGauge64
    UNITS        "/ 10000 %"
    MAX-ACCESS   read-only
    STATUS       current
    DESCRIPTION  "% of media bandwidth versus bandwidth
                  limit within destination adjacency"
    ::= { perimetaAdjacencyStatsEntry 304 }

  adjStatDstMedStrPerc OBJECT-TYPE
    SYNTAX       CounterBasedGauge64
    UNITS        "/ 10000 %"
    MAX-ACCESS   read-only
    STATUS       current
    DESCRIPTION  "% of media streams versus limit within
                  destination adjacency"
    ::= { perimetaAdjacencyStatsEntry 305 }

  adjStatDstNumRegsPerc OBJECT-TYPE
    SYNTAX       CounterBasedGauge64
    UNITS        "/ 10000 %"
    MAX-ACCESS   read-only
    STATUS       current
    DESCRIPTION  "% of registrations versus limit within
                  destination adjacency"
    ::= { perimetaAdjacencyStatsEntry 306 }

  adjStatDstCallBurstRatePerc OBJECT-TYPE
    SYNTAX       CounterBasedGauge64
    UNITS        "/ 10000 %"
    MAX-ACCESS   read-only
    STATUS       current
    DESCRIPTION  "% of burst call rate versus limit within
                  destination adjacency"
    ::= { perimetaAdjacencyStatsEntry 307 }

  adjStatDstCallSustainRatePerc OBJECT-TYPE
    SYNTAX       CounterBasedGauge64
    UNITS        "/ 10000 %"
    MAX-ACCESS   read-only
    STATUS       current
    DESCRIPTION  "% of sustained call rate versus limit
                  within destination adjacency"
    ::= { perimetaAdjacencyStatsEntry 308 }

  adjStatDstInCallBurstRatePerc OBJECT-TYPE
    SYNTAX       CounterBasedGauge64
    UNITS        "/ 10000 %"
    MAX-ACCESS   read-only
    STATUS       current
    DESCRIPTION  "% of burst in-call message rate versus
                  limit within destination adjacency"
    ::= { perimetaAdjacencyStatsEntry 309 }

  adjStatDstInCallSustainRatePerc OBJECT-TYPE
    SYNTAX       CounterBasedGauge64
    UNITS        "/ 10000 %"
    MAX-ACCESS   read-only
    STATUS       current
    DESCRIPTION  "% of sustained in-call message rate
                  versus limit within destination
                  adjacency"
    ::= { perimetaAdjacencyStatsEntry 310 }

  adjStatDstOOCBurstRatePerc OBJECT-TYPE
    SYNTAX       CounterBasedGauge64
    UNITS        "/ 10000 %"
    MAX-ACCESS   read-only
    STATUS       current
    DESCRIPTION  "% of burst out-of-call message rate
                  versus limit within destination
                  adjacency"
    ::= { perimetaAdjacencyStatsEntry 311 }

  adjStatDstOOCSustainRatePerc OBJECT-TYPE
    SYNTAX       CounterBasedGauge64
    UNITS        "/ 10000 %"
    MAX-ACCESS   read-only
    STATUS       current
    DESCRIPTION  "% of sustained out-of-call message rate
                  versus limit within destination
                  adjacency"
    ::= { perimetaAdjacencyStatsEntry 312 }

  adjStatDstRegsBurstRatePerc OBJECT-TYPE
    SYNTAX       CounterBasedGauge64
    UNITS        "/ 10000 %"
    MAX-ACCESS   read-only
    STATUS       current
    DESCRIPTION  "% of burst registration rate versus
                  limit within destination adjacency"
    ::= { perimetaAdjacencyStatsEntry 313 }

  adjStatDstRegsSustainRatePerc OBJECT-TYPE
    SYNTAX       CounterBasedGauge64
    UNITS        "/ 10000 %"
    MAX-ACCESS   read-only
    STATUS       current
    DESCRIPTION  "% of sustained registration rate versus
                  limit within destination adjacency"
    ::= { perimetaAdjacencyStatsEntry 314 }

  adjStatNumCallsMLimit OBJECT-TYPE
    SYNTAX       CounterBasedGauge64
    MAX-ACCESS   read-only
    STATUS       current
    DESCRIPTION  "Active call limit within adjacency"
    ::= { perimetaAdjacencyStatsEntry 315 }

  adjStatMedBwMLimit OBJECT-TYPE
    SYNTAX       CounterBasedGauge64
    MAX-ACCESS   read-only
    STATUS       current
    DESCRIPTION  "Media bandwidth limit within adjacency"
    ::= { perimetaAdjacencyStatsEntry 316 }

  adjStatMedStrMLimit OBJECT-TYPE
    SYNTAX       CounterBasedGauge64
    MAX-ACCESS   read-only
    STATUS       current
    DESCRIPTION  "Media streams limit within adjacency"
    ::= { perimetaAdjacencyStatsEntry 317 }

  adjStatNumRegsMLimit OBJECT-TYPE
    SYNTAX       CounterBasedGauge64
    MAX-ACCESS   read-only
    STATUS       current
    DESCRIPTION  "Registrations limit within adjacency"
    ::= { perimetaAdjacencyStatsEntry 318 }

  adjStatCallBurstRateMLimit OBJECT-TYPE
    SYNTAX       CounterBasedGauge64
    MAX-ACCESS   read-only
    STATUS       current
    DESCRIPTION  "Burst call rate limit (per min) within
                  adjacency"
    ::= { perimetaAdjacencyStatsEntry 319 }

  adjStatCallSustainRateMLimit OBJECT-TYPE
    SYNTAX       CounterBasedGauge64
    MAX-ACCESS   read-only
    STATUS       current
    DESCRIPTION  "Sustained call rate limit (per min)
                  within adjacency"
    ::= { perimetaAdjacencyStatsEntry 320 }

  adjStatInCallBurstRateMLimit OBJECT-TYPE
    SYNTAX       CounterBasedGauge64
    MAX-ACCESS   read-only
    STATUS       current
    DESCRIPTION  "Burst in-call message rate limit (per
                  min) within adjacency"
    ::= { perimetaAdjacencyStatsEntry 321 }

  adjStatInCallSustainRateMLimit OBJECT-TYPE
    SYNTAX       CounterBasedGauge64
    MAX-ACCESS   read-only
    STATUS       current
    DESCRIPTION  "Sustained in-call message rate limit
                  (per min) within adjacency"
    ::= { perimetaAdjacencyStatsEntry 322 }

  adjStatOOCBurstRateMLimit OBJECT-TYPE
    SYNTAX       CounterBasedGauge64
    MAX-ACCESS   read-only
    STATUS       current
    DESCRIPTION  "Burst out-of-call message rate limit
                  (per min) within adjacency"
    ::= { perimetaAdjacencyStatsEntry 323 }

  adjStatOOCSustainRateMLimit OBJECT-TYPE
    SYNTAX       CounterBasedGauge64
    MAX-ACCESS   read-only
    STATUS       current
    DESCRIPTION  "Sustained out-of-call message rate limit
                  (per min) within adjacency"
    ::= { perimetaAdjacencyStatsEntry 324 }

  adjStatRegsBurstRateMLimit OBJECT-TYPE
    SYNTAX       CounterBasedGauge64
    MAX-ACCESS   read-only
    STATUS       current
    DESCRIPTION  "Burst registration rate limit (per min)
                  within adjacency"
    ::= { perimetaAdjacencyStatsEntry 325 }

  adjStatRegsSustainRateMLimit OBJECT-TYPE
    SYNTAX       CounterBasedGauge64
    MAX-ACCESS   read-only
    STATUS       current
    DESCRIPTION  "Sustained registration rate limit (per
                  min) within adjacency"
    ::= { perimetaAdjacencyStatsEntry 326 }

  adjStatSrcNumCallsMLimit OBJECT-TYPE
    SYNTAX       CounterBasedGauge64
    MAX-ACCESS   read-only
    STATUS       current
    DESCRIPTION  "Active call limit within source
                  adjacency"
    ::= { perimetaAdjacencyStatsEntry 327 }

  adjStatSrcMedBwMLimit OBJECT-TYPE
    SYNTAX       CounterBasedGauge64
    MAX-ACCESS   read-only
    STATUS       current
    DESCRIPTION  "Media bandwidth limit within source
                  adjacency"
    ::= { perimetaAdjacencyStatsEntry 328 }

  adjStatSrcMedStrMLimit OBJECT-TYPE
    SYNTAX       CounterBasedGauge64
    MAX-ACCESS   read-only
    STATUS       current
    DESCRIPTION  "Media streams limit within source
                  adjacency"
    ::= { perimetaAdjacencyStatsEntry 329 }

  adjStatSrcNumRegsMLimit OBJECT-TYPE
    SYNTAX       CounterBasedGauge64
    MAX-ACCESS   read-only
    STATUS       current
    DESCRIPTION  "Registrations limit within source
                  adjacency"
    ::= { perimetaAdjacencyStatsEntry 330 }

  adjStatSrcCallBurstRateMLimit OBJECT-TYPE
    SYNTAX       CounterBasedGauge64
    MAX-ACCESS   read-only
    STATUS       current
    DESCRIPTION  "Burst call rate limit (per min) within
                  source adjacency"
    ::= { perimetaAdjacencyStatsEntry 331 }

  adjStatSrcCallSustainRateMLimit OBJECT-TYPE
    SYNTAX       CounterBasedGauge64
    MAX-ACCESS   read-only
    STATUS       current
    DESCRIPTION  "Sustained call rate limit (per min)
                  within source adjacency"
    ::= { perimetaAdjacencyStatsEntry 332 }

  adjStatSrcInCallBurstRateMLimit OBJECT-TYPE
    SYNTAX       CounterBasedGauge64
    MAX-ACCESS   read-only
    STATUS       current
    DESCRIPTION  "Burst in-call message rate limit (per
                  min) within source adjacency"
    ::= { perimetaAdjacencyStatsEntry 333 }

  adjStatSrcInCallSustainRateMLimit OBJECT-TYPE
    SYNTAX       CounterBasedGauge64
    MAX-ACCESS   read-only
    STATUS       current
    DESCRIPTION  "Sustained in-call message rate limit
                  (per min) within source adjacency"
    ::= { perimetaAdjacencyStatsEntry 334 }

  adjStatSrcOOCBurstRateMLimit OBJECT-TYPE
    SYNTAX       CounterBasedGauge64
    MAX-ACCESS   read-only
    STATUS       current
    DESCRIPTION  "Burst out-of-call message rate limit
                  (per min) within source adjacency"
    ::= { perimetaAdjacencyStatsEntry 335 }

  adjStatSrcOOCSustainRateMLimit OBJECT-TYPE
    SYNTAX       CounterBasedGauge64
    MAX-ACCESS   read-only
    STATUS       current
    DESCRIPTION  "Sustained out-of-call message rate limit
                  (per min) within source adjacency"
    ::= { perimetaAdjacencyStatsEntry 336 }

  adjStatSrcRegsBurstRateMLimit OBJECT-TYPE
    SYNTAX       CounterBasedGauge64
    MAX-ACCESS   read-only
    STATUS       current
    DESCRIPTION  "Burst registration rate limit (per min)
                  within source adjacency"
    ::= { perimetaAdjacencyStatsEntry 337 }

  adjStatSrcRegsSustainRateMLimit OBJECT-TYPE
    SYNTAX       CounterBasedGauge64
    MAX-ACCESS   read-only
    STATUS       current
    DESCRIPTION  "Sustained registration rate limit (per
                  min) within source adjacency"
    ::= { perimetaAdjacencyStatsEntry 338 }

  adjStatDstNumCallsMLimit OBJECT-TYPE
    SYNTAX       CounterBasedGauge64
    MAX-ACCESS   read-only
    STATUS       current
    DESCRIPTION  "Active call limit within destination
                  adjacency"
    ::= { perimetaAdjacencyStatsEntry 339 }

  adjStatDstMedBwMLimit OBJECT-TYPE
    SYNTAX       CounterBasedGauge64
    MAX-ACCESS   read-only
    STATUS       current
    DESCRIPTION  "Media bandwidth limit within destination
                  adjacency"
    ::= { perimetaAdjacencyStatsEntry 340 }

  adjStatDstMedStrMLimit OBJECT-TYPE
    SYNTAX       CounterBasedGauge64
    MAX-ACCESS   read-only
    STATUS       current
    DESCRIPTION  "Media streams limit within destination
                  adjacency"
    ::= { perimetaAdjacencyStatsEntry 341 }

  adjStatDstNumRegsMLimit OBJECT-TYPE
    SYNTAX       CounterBasedGauge64
    MAX-ACCESS   read-only
    STATUS       current
    DESCRIPTION  "Registrations limit within destination
                  adjacency"
    ::= { perimetaAdjacencyStatsEntry 342 }

  adjStatDstCallBurstRateMLimit OBJECT-TYPE
    SYNTAX       CounterBasedGauge64
    MAX-ACCESS   read-only
    STATUS       current
    DESCRIPTION  "Burst call rate limit (per min) within
                  destination adjacency"
    ::= { perimetaAdjacencyStatsEntry 343 }

  adjStatDstCallSustainRateMLimit OBJECT-TYPE
    SYNTAX       CounterBasedGauge64
    MAX-ACCESS   read-only
    STATUS       current
    DESCRIPTION  "Sustained call rate limit (per min)
                  within destination adjacency"
    ::= { perimetaAdjacencyStatsEntry 344 }

  adjStatDstInCallBurstRateMLimit OBJECT-TYPE
    SYNTAX       CounterBasedGauge64
    MAX-ACCESS   read-only
    STATUS       current
    DESCRIPTION  "Burst in-call message rate limit (per
                  min) within destination adjacency"
    ::= { perimetaAdjacencyStatsEntry 345 }

  adjStatDstInCallSustainRateMLimit OBJECT-TYPE
    SYNTAX       CounterBasedGauge64
    MAX-ACCESS   read-only
    STATUS       current
    DESCRIPTION  "Sustained in-call message rate limit
                  (per min) within destination adjacency"
    ::= { perimetaAdjacencyStatsEntry 346 }

  adjStatDstOOCBurstRateMLimit OBJECT-TYPE
    SYNTAX       CounterBasedGauge64
    MAX-ACCESS   read-only
    STATUS       current
    DESCRIPTION  "Burst out-of-call message rate limit
                  (per min) within destination adjacency"
    ::= { perimetaAdjacencyStatsEntry 347 }

  adjStatDstOOCSustainRateMLimit OBJECT-TYPE
    SYNTAX       CounterBasedGauge64
    MAX-ACCESS   read-only
    STATUS       current
    DESCRIPTION  "Sustained out-of-call message rate limit
                  (per min) within destination adjacency"
    ::= { perimetaAdjacencyStatsEntry 348 }

  adjStatDstRegsBurstRateMLimit OBJECT-TYPE
    SYNTAX       CounterBasedGauge64
    MAX-ACCESS   read-only
    STATUS       current
    DESCRIPTION  "Burst registration rate limit (per min)
                  within destination adjacency"
    ::= { perimetaAdjacencyStatsEntry 349 }

  adjStatDstRegsSustainRateMLimit OBJECT-TYPE
    SYNTAX       CounterBasedGauge64
    MAX-ACCESS   read-only
    STATUS       current
    DESCRIPTION  "Sustained registration rate limit (per
                  min) within destination adjacency"
    ::= { perimetaAdjacencyStatsEntry 350 }

  adjStatRTPAvgRfactorLast5Min OBJECT-TYPE
    SYNTAX       CounterBasedGauge64
    MAX-ACCESS   read-only
    STATUS       current
    DESCRIPTION  "Moving average with averaging period 5
                  minutes of the R-factor for media
                  streams on this adjacency"
    ::= { perimetaAdjacencyStatsEntry 351 }

  adjStatRTPAvgMOScqeLast5Min OBJECT-TYPE
    SYNTAX       CounterBasedGauge64
    UNITS        "/ 10"
    MAX-ACCESS   read-only
    STATUS       current
    DESCRIPTION  "Moving average with averaging period 5
                  minutes of the MOScqe for media streams
                  on this adjacency"
    ::= { perimetaAdjacencyStatsEntry 352 }

  adjStatSrcMSRPSIWCallsCurrent OBJECT-TYPE
    SYNTAX       CounterBasedGauge64
    MAX-ACCESS   read-only
    STATUS       current
    DESCRIPTION  "Current number of MSRPS interworking
                  calls on this source adjacency"
    ::= { perimetaAdjacencyStatsEntry 353 }

  adjStatSrcMSRPSPtCallsCurrent OBJECT-TYPE
    SYNTAX       CounterBasedGauge64
    MAX-ACCESS   read-only
    STATUS       current
    DESCRIPTION  "Current number of MSRPS passthrough
                  calls on this source adjacency"
    ::= { perimetaAdjacencyStatsEntry 354 }

  adjStatSrcMSRPSIWCallRate OBJECT-TYPE
    SYNTAX       CounterBasedGauge64
    MAX-ACCESS   read-only
    STATUS       current
    DESCRIPTION  "MSRPS interworking calls/second rate on
                  this source adjacency"
    ::= { perimetaAdjacencyStatsEntry 357 }

  adjStatSrcMSRPSPtCallRate OBJECT-TYPE
    SYNTAX       CounterBasedGauge64
    MAX-ACCESS   read-only
    STATUS       current
    DESCRIPTION  "MSRPS passthrough calls/second rate on
                  this source adjacency"
    ::= { perimetaAdjacencyStatsEntry 358 }

  adjStatDstMSRPSIWCallsCurrent OBJECT-TYPE
    SYNTAX       CounterBasedGauge64
    MAX-ACCESS   read-only
    STATUS       current
    DESCRIPTION  "Current number of MSRPS interworking
                  calls on this destination adjacency"
    ::= { perimetaAdjacencyStatsEntry 359 }

  adjStatDstMSRPSPtCallsCurrent OBJECT-TYPE
    SYNTAX       CounterBasedGauge64
    MAX-ACCESS   read-only
    STATUS       current
    DESCRIPTION  "Current number of MSRPS passthrough
                  calls on this destination adjacency"
    ::= { perimetaAdjacencyStatsEntry 360 }

  adjStatDstMSRPSIWCallRate OBJECT-TYPE
    SYNTAX       CounterBasedGauge64
    MAX-ACCESS   read-only
    STATUS       current
    DESCRIPTION  "MSRPS interworking calls/second rate on
                  this destination adjacency"
    ::= { perimetaAdjacencyStatsEntry 363 }

  adjStatDstMSRPSPtCallRate OBJECT-TYPE
    SYNTAX       CounterBasedGauge64
    MAX-ACCESS   read-only
    STATUS       current
    DESCRIPTION  "MSRPS passthrough calls/second rate on
                  this destination adjacency"
    ::= { perimetaAdjacencyStatsEntry 364 }

  adjStatSrcSignalFailureRate OBJECT-TYPE
    SYNTAX       CounterBasedGauge64
    MAX-ACCESS   read-only
    STATUS       current
    DESCRIPTION  "Rate of incoming calls to this adjacency
                  failing due to Signal Failure"
    ::= { perimetaAdjacencyStatsEntry 367 }

  adjStatDstSignalFailureRate OBJECT-TYPE
    SYNTAX       CounterBasedGauge64
    MAX-ACCESS   read-only
    STATUS       current
    DESCRIPTION  "Rate of outgoing calls from this
                  adjacency failing due to Signal Failure"
    ::= { perimetaAdjacencyStatsEntry 368 }

  adjStatSrcFailuresSignaling OBJECT-TYPE
    SYNTAX       CounterBasedGauge64
    UNITS        "/ 10000 %"
    MAX-ACCESS   read-only
    STATUS       current
    DESCRIPTION  "Percentage of incoming calls to this
                  adjacency failing due to Signaling
                  Failure (compared to attempts)"
    ::= { perimetaAdjacencyStatsEntry 369 }

  adjStatDstFailuresSignaling OBJECT-TYPE
    SYNTAX       CounterBasedGauge64
    UNITS        "/ 10000 %"
    MAX-ACCESS   read-only
    STATUS       current
    DESCRIPTION  "Percentage of outgoing calls from this
                  adjacency failing due to Signaling
                  Failure (compared to attempts)"
    ::= { perimetaAdjacencyStatsEntry 370 }

  adjStatEmergencyRedirects OBJECT-TYPE
    SYNTAX       CounterBasedGauge64
    MAX-ACCESS   read-only
    STATUS       current
    DESCRIPTION  "Number of IMS emergency redirects
                  carried out on this adjacency"
    ::= { perimetaAdjacencyStatsEntry 387 }

  adjStatCodecUsageOPUS OBJECT-TYPE
    SYNTAX       CounterBasedGauge64
    MAX-ACCESS   read-only
    STATUS       current
    DESCRIPTION  "The number of streams using OPUS"
    ::= { perimetaAdjacencyStatsEntry 388 }

  adjStatNumCallsHwmNMP OBJECT-TYPE
    SYNTAX       CounterBasedGauge64
    MAX-ACCESS   read-only
    STATUS       current
    DESCRIPTION  "High water mark of active calls within
                  adjacency during this statistics
                  collection interval"
    ::= { perimetaAdjacencyStatsEntry 389 }

  adjStatMedBwHwmNMP OBJECT-TYPE
    SYNTAX       CounterBasedGauge64
    MAX-ACCESS   read-only
    STATUS       current
    DESCRIPTION  "High water mark of media bandwidth
                  within adjacency during this statistics
                  collection interval"
    ::= { perimetaAdjacencyStatsEntry 390 }

  adjStatMedStreamsHwmNMP OBJECT-TYPE
    SYNTAX       CounterBasedGauge64
    MAX-ACCESS   read-only
    STATUS       current
    DESCRIPTION  "High water mark of media streams within
                  adjacency during this statistics
                  collection interval"
    ::= { perimetaAdjacencyStatsEntry 391 }

  adjStatNumRegsHwmNMP OBJECT-TYPE
    SYNTAX       CounterBasedGauge64
    MAX-ACCESS   read-only
    STATUS       current
    DESCRIPTION  "High water mark of concurrent
                  registrations within adjacency during
                  this statistics collection interval"
    ::= { perimetaAdjacencyStatsEntry 392 }

  adjStatCallBurstRateHwmNMP OBJECT-TYPE
    SYNTAX       CounterBasedGauge64
    MAX-ACCESS   read-only
    STATUS       current
    DESCRIPTION  "High water mark of burst rate of call
                  setup within adjacency during this
                  statistics collection interval"
    ::= { perimetaAdjacencyStatsEntry 393 }

  adjStatCallSustainRateHwmNMP OBJECT-TYPE
    SYNTAX       CounterBasedGauge64
    MAX-ACCESS   read-only
    STATUS       current
    DESCRIPTION  "High water mark of sustained rate of
                  call setup within adjacency during this
                  statistics collection interval"
    ::= { perimetaAdjacencyStatsEntry 394 }

  adjStatInCallBurstRateHwmNMP OBJECT-TYPE
    SYNTAX       CounterBasedGauge64
    MAX-ACCESS   read-only
    STATUS       current
    DESCRIPTION  "High water mark of burst rate of in-call
                  messages within adjacency during this
                  statistics collection interval"
    ::= { perimetaAdjacencyStatsEntry 395 }

  adjStatInCallSustainRateHwmNMP OBJECT-TYPE
    SYNTAX       CounterBasedGauge64
    MAX-ACCESS   read-only
    STATUS       current
    DESCRIPTION  "High water mark of sustained rate of
                  in-call messages within adjacency during
                  this statistics collection interval"
    ::= { perimetaAdjacencyStatsEntry 396 }

  adjStatOOCBurstRateHwmNMP OBJECT-TYPE
    SYNTAX       CounterBasedGauge64
    MAX-ACCESS   read-only
    STATUS       current
    DESCRIPTION  "High water mark of burst rate of
                  out-of-call messages within adjacency
                  during this statistics collection
                  interval"
    ::= { perimetaAdjacencyStatsEntry 397 }

  adjStatOOCSustainRateHwmNMP OBJECT-TYPE
    SYNTAX       CounterBasedGauge64
    MAX-ACCESS   read-only
    STATUS       current
    DESCRIPTION  "High water mark of sustained rate of
                  out-of-call messages within the
                  adjacency during this statistics
                  collection interval"
    ::= { perimetaAdjacencyStatsEntry 398 }

  adjStatRegsBurstRateHwmNMP OBJECT-TYPE
    SYNTAX       CounterBasedGauge64
    MAX-ACCESS   read-only
    STATUS       current
    DESCRIPTION  "High water mark of burst rate of
                  registration within adjacency during
                  this statistics collection interval"
    ::= { perimetaAdjacencyStatsEntry 399 }

  adjStatRegsSustainRateHwmNMP OBJECT-TYPE
    SYNTAX       CounterBasedGauge64
    MAX-ACCESS   read-only
    STATUS       current
    DESCRIPTION  "High water mark of sustained rate of
                  registration within adjacency during
                  this statistics collection interval"
    ::= { perimetaAdjacencyStatsEntry 400 }

  adjStatSrcNumCallsHwmNMP OBJECT-TYPE
    SYNTAX       CounterBasedGauge64
    MAX-ACCESS   read-only
    STATUS       current
    DESCRIPTION  "High water mark of active calls within
                  source adjacency during this statistics
                  collection interval"
    ::= { perimetaAdjacencyStatsEntry 401 }

  adjStatSrcMedBwHwmNMP OBJECT-TYPE
    SYNTAX       CounterBasedGauge64
    MAX-ACCESS   read-only
    STATUS       current
    DESCRIPTION  "High water mark of media bandwidth
                  within source adjacency during this
                  statistics collection interval"
    ::= { perimetaAdjacencyStatsEntry 402 }

  adjStatSrcMedStreamsHwmNMP OBJECT-TYPE
    SYNTAX       CounterBasedGauge64
    MAX-ACCESS   read-only
    STATUS       current
    DESCRIPTION  "High water mark of media streams within
                  source adjacency during this statistics
                  collection interval"
    ::= { perimetaAdjacencyStatsEntry 403 }

  adjStatSrcNumRegsHwmNMP OBJECT-TYPE
    SYNTAX       CounterBasedGauge64
    MAX-ACCESS   read-only
    STATUS       current
    DESCRIPTION  "High water mark of concurrent
                  registrations within source adjacency
                  during this statistics collection
                  interval"
    ::= { perimetaAdjacencyStatsEntry 404 }

  adjStatSrcCallBurstRateHwmNMP OBJECT-TYPE
    SYNTAX       CounterBasedGauge64
    MAX-ACCESS   read-only
    STATUS       current
    DESCRIPTION  "High water mark of burst rate of call
                  setup within source adjacency during
                  this statistics collection interval"
    ::= { perimetaAdjacencyStatsEntry 405 }

  adjStatSrcCallSustainRateHwmNMP OBJECT-TYPE
    SYNTAX       CounterBasedGauge64
    MAX-ACCESS   read-only
    STATUS       current
    DESCRIPTION  "High water mark of sustained rate of
                  call setup within source adjacency
                  during this statistics collection
                  interval"
    ::= { perimetaAdjacencyStatsEntry 406 }

  adjStatSrcInCallBurstRateHwmNMP OBJECT-TYPE
    SYNTAX       CounterBasedGauge64
    MAX-ACCESS   read-only
    STATUS       current
    DESCRIPTION  "High water mark of burst rate of in-call
                  messages within source adjacency during
                  this statistics collection interval"
    ::= { perimetaAdjacencyStatsEntry 407 }

  adjStatSrcInCallSustainRateHwmNMP OBJECT-TYPE
    SYNTAX       CounterBasedGauge64
    MAX-ACCESS   read-only
    STATUS       current
    DESCRIPTION  "High water mark of sustained rate of
                  in-call messages within source adjacency
                  during this statistics collection
                  interval"
    ::= { perimetaAdjacencyStatsEntry 408 }

  adjStatSrcOOCBurstRateHwmNMP OBJECT-TYPE
    SYNTAX       CounterBasedGauge64
    MAX-ACCESS   read-only
    STATUS       current
    DESCRIPTION  "High water mark of burst rate of
                  out-of-call messages within source
                  adjacency during this statistics
                  collection interval"
    ::= { perimetaAdjacencyStatsEntry 409 }

  adjStatSrcOOCSustainRateHwmNMP OBJECT-TYPE
    SYNTAX       CounterBasedGauge64
    MAX-ACCESS   read-only
    STATUS       current
    DESCRIPTION  "High water mark of sustained rate of
                  out-of-call messages within the source
                  adjacency during this statistics
                  collection interval"
    ::= { perimetaAdjacencyStatsEntry 410 }

  adjStatSrcRegsBurstRateHwmNMP OBJECT-TYPE
    SYNTAX       CounterBasedGauge64
    MAX-ACCESS   read-only
    STATUS       current
    DESCRIPTION  "High water mark of burst rate of
                  registration within source adjacency
                  during this statistics collection
                  interval"
    ::= { perimetaAdjacencyStatsEntry 411 }

  adjStatSrcRegsSustainRateHwmNMP OBJECT-TYPE
    SYNTAX       CounterBasedGauge64
    MAX-ACCESS   read-only
    STATUS       current
    DESCRIPTION  "High water mark of sustained rate of
                  registration within source adjacency
                  during this statistics collection
                  interval"
    ::= { perimetaAdjacencyStatsEntry 412 }

  adjStatDstNumCallsHwmNMP OBJECT-TYPE
    SYNTAX       CounterBasedGauge64
    MAX-ACCESS   read-only
    STATUS       current
    DESCRIPTION  "High water mark of active calls within
                  destination adjacency during this
                  statistics collection interval"
    ::= { perimetaAdjacencyStatsEntry 413 }

  adjStatDstMedBwHwmNMP OBJECT-TYPE
    SYNTAX       CounterBasedGauge64
    MAX-ACCESS   read-only
    STATUS       current
    DESCRIPTION  "High water mark of media bandwidth
                  within destination adjacency during this
                  statistics collection interval"
    ::= { perimetaAdjacencyStatsEntry 414 }

  adjStatDstMedStreamsHwmNMP OBJECT-TYPE
    SYNTAX       CounterBasedGauge64
    MAX-ACCESS   read-only
    STATUS       current
    DESCRIPTION  "High water mark of media streams within
                  destination adjacency during this
                  statistics collection interval"
    ::= { perimetaAdjacencyStatsEntry 415 }

  adjStatDstNumRegsHwmNMP OBJECT-TYPE
    SYNTAX       CounterBasedGauge64
    MAX-ACCESS   read-only
    STATUS       current
    DESCRIPTION  "High water mark of concurrent
                  registrations within destination
                  adjacency during this statistics
                  collection interval"
    ::= { perimetaAdjacencyStatsEntry 416 }

  adjStatDstCallBurstRateHwmNMP OBJECT-TYPE
    SYNTAX       CounterBasedGauge64
    MAX-ACCESS   read-only
    STATUS       current
    DESCRIPTION  "High water mark of burst rate of call
                  setup within destination adjacency
                  during this statistics collection
                  interval"
    ::= { perimetaAdjacencyStatsEntry 417 }

  adjStatDstCallSustainRateHwmNMP OBJECT-TYPE
    SYNTAX       CounterBasedGauge64
    MAX-ACCESS   read-only
    STATUS       current
    DESCRIPTION  "High water mark of sustained rate of
                  call setup within destination adjacency
                  during this statistics collection
                  interval"
    ::= { perimetaAdjacencyStatsEntry 418 }

  adjStatDstInCallBurstRateHwmNMP OBJECT-TYPE
    SYNTAX       CounterBasedGauge64
    MAX-ACCESS   read-only
    STATUS       current
    DESCRIPTION  "High water mark of burst rate of in-call
                  messages within destination adjacency
                  during this statistics collection
                  interval"
    ::= { perimetaAdjacencyStatsEntry 419 }

  adjStatDstInCallSustainRateHwmNMP OBJECT-TYPE
    SYNTAX       CounterBasedGauge64
    MAX-ACCESS   read-only
    STATUS       current
    DESCRIPTION  "High water mark of sustained rate of
                  in-call messages within destination
                  adjacency during this statistics
                  collection interval"
    ::= { perimetaAdjacencyStatsEntry 420 }

  adjStatDstOOCBurstRateHwmNMP OBJECT-TYPE
    SYNTAX       CounterBasedGauge64
    MAX-ACCESS   read-only
    STATUS       current
    DESCRIPTION  "High water mark of burst rate of
                  out-of-call messages within destination
                  adjacency during this statistics
                  collection interval"
    ::= { perimetaAdjacencyStatsEntry 421 }

  adjStatDstOOCSustainRateHwmNMP OBJECT-TYPE
    SYNTAX       CounterBasedGauge64
    MAX-ACCESS   read-only
    STATUS       current
    DESCRIPTION  "High water mark of sustained rate of
                  out-of-call messages within the
                  destination adjacency during this
                  statistics collection interval"
    ::= { perimetaAdjacencyStatsEntry 422 }

  adjStatDstRegsBurstRateHwmNMP OBJECT-TYPE
    SYNTAX       CounterBasedGauge64
    MAX-ACCESS   read-only
    STATUS       current
    DESCRIPTION  "High water mark of burst rate of
                  registration within destination
                  adjacency during this statistics
                  collection interval"
    ::= { perimetaAdjacencyStatsEntry 423 }

  adjStatDstRegsSustainRateHwmNMP OBJECT-TYPE
    SYNTAX       CounterBasedGauge64
    MAX-ACCESS   read-only
    STATUS       current
    DESCRIPTION  "High water mark of sustained rate of
                  registration within destination
                  adjacency during this statistics
                  collection interval"
    ::= { perimetaAdjacencyStatsEntry 424 }

  adjStatDstTotalCallDuration OBJECT-TYPE
    SYNTAX       CounterBasedGauge64
    MAX-ACCESS   read-only
    STATUS       current
    DESCRIPTION  "Total duration of calls outbound from
                  this adjacency terminating during this
                  statistics collection interval (s)"
    ::= { perimetaAdjacencyStatsEntry 427 }

  adjStatSrcTotalCallDuration OBJECT-TYPE
    SYNTAX       CounterBasedGauge64
    MAX-ACCESS   read-only
    STATUS       current
    DESCRIPTION  "Total duration of calls inbound to this
                  adjacency terminating during this
                  statistics collection interval (s)"
    ::= { perimetaAdjacencyStatsEntry 428 }

  adjStatOKEmergencyCallNotifiesLastPeriod OBJECT-TYPE
    SYNTAX       CounterBasedGauge64
    MAX-ACCESS   read-only
    STATUS       current
    DESCRIPTION  "The number of emergency call
                  notification successful responses
                  received by this adjacency over the last
                  period"
    ::= { perimetaAdjacencyStatsEntry 431 }

  adjStatFailedEmergencyCallNotifiesLastPeriod OBJECT-TYPE
    SYNTAX       CounterBasedGauge64
    MAX-ACCESS   read-only
    STATUS       current
    DESCRIPTION  "The number of emergency call
                  notification failure responses received
                  by this adjacency over the last period"
    ::= { perimetaAdjacencyStatsEntry 432 }

  adjStatOKEmergencyCallNotifiesRate OBJECT-TYPE
    SYNTAX       CounterBasedGauge64
    MAX-ACCESS   read-only
    STATUS       current
    DESCRIPTION  "Rate of successful emergency call
                  notification responses received by this
                  adjacency (msgs/s)"
    ::= { perimetaAdjacencyStatsEntry 433 }

  adjStatFailedEmergencyCallNotifiesRate OBJECT-TYPE
    SYNTAX       CounterBasedGauge64
    MAX-ACCESS   read-only
    STATUS       current
    DESCRIPTION  "Rate of failed emergency call
                  notification responses received by this
                  adjacency (msgs/s)"
    ::= { perimetaAdjacencyStatsEntry 434 }

  adjStatEmergencyCallNotifiesSentLastPeriod OBJECT-TYPE
    SYNTAX       CounterBasedGauge64
    MAX-ACCESS   read-only
    STATUS       current
    DESCRIPTION  "The number of emergency call
                  notifications sent by this adjacency
                  over the last period"
    ::= { perimetaAdjacencyStatsEntry 436 }

  adjStatEmergencyCallNotifiesSentRate OBJECT-TYPE
    SYNTAX       CounterBasedGauge64
    MAX-ACCESS   read-only
    STATUS       current
    DESCRIPTION  "Rate of emergency call notifications
                  sent by this adjacency (msgs/s)"
    ::= { perimetaAdjacencyStatsEntry 437 }

-- /**********************************************************/
-- /* Information about Perimeta Accounts.                   */
-- /**********************************************************/

  perimetaAccounts OBJECT IDENTIFIER ::= { perimeta 4 }

  perimetaAccountNumber OBJECT-TYPE
    SYNTAX       Unsigned32
    MAX-ACCESS   read-only
    STATUS       current
    DESCRIPTION  "This is the number of accounts configured on Perimeta"
    ::= { perimetaAccounts 1 }

  perimetaAccountStatsTable OBJECT-TYPE
    SYNTAX      SEQUENCE OF PerimetaAccountStatsEntry
    MAX-ACCESS  not-accessible
    STATUS      current
    DESCRIPTION "This table contains statistics from Perimeta at
                 per-account scope, indexed by account name."
    ::= { perimetaAccounts 2 }

  perimetaAccountStatsEntry OBJECT-TYPE
    SYNTAX      PerimetaAccountStatsEntry
    MAX-ACCESS  not-accessible
    STATUS      current
    DESCRIPTION "The entry in the Perimeta account stats table
                 contains all the per-account statistics,
                 indexed on account name."
    INDEX      { accStatAccountName, accStatSummaryPeriod }
    ::= { perimetaAccountStatsTable 1 }

  PerimetaAccountStatsEntry ::= SEQUENCE
  {
    accStatAccountName                          DisplayString,
    accStatSummaryPeriod                        INTEGER,
    accStatNumCallsHwm                            CounterBasedGauge64,
    accStatMedBwHwm                               CounterBasedGauge64,
    accStatMedStreamsHwm                          CounterBasedGauge64,
    accStatNumRegsHwm                             CounterBasedGauge64,
    accStatCallBurstRateHwm                       CounterBasedGauge64,
    accStatCallSustainRateHwm                     CounterBasedGauge64,
    accStatInCallBurstRateHwm                     CounterBasedGauge64,
    accStatInCallSustainRateHwm                   CounterBasedGauge64,
    accStatOOCBurstRateHwm                        CounterBasedGauge64,
    accStatOOCSustainRateHwm                      CounterBasedGauge64,
    accStatRegsRateHwm                            CounterBasedGauge64,
    accStatRegsSustainRateHwm                     CounterBasedGauge64,
    accStatNumCallsPerc                           CounterBasedGauge64,
    accStatMedBwPerc                              CounterBasedGauge64,
    accStatMedStrPerc                             CounterBasedGauge64,
    accStatNumRegsPerc                            CounterBasedGauge64,
    accStatCallBurstRatePerc                      CounterBasedGauge64,
    accStatCallSustainRatePerc                    CounterBasedGauge64,
    accStatInCallBurstRatePerc                    CounterBasedGauge64,
    accStatInCallSustainRatePerc                  CounterBasedGauge64,
    accStatOOCBurstRatePerc                       CounterBasedGauge64,
    accStatOOCSustainRatePerc                     CounterBasedGauge64,
    accStatRegsBurstRatePerc                      CounterBasedGauge64,
    accStatRegsSustainRatePerc                    CounterBasedGauge64,
    accStatSrcNumCallsHwm                         CounterBasedGauge64,
    accStatSrcMedBwHwm                            CounterBasedGauge64,
    accStatSrcMedStreamsHwm                       CounterBasedGauge64,
    accStatSrcNumRegsHwm                          CounterBasedGauge64,
    accStatSrcCallBurstRateHwm                    CounterBasedGauge64,
    accStatSrcCallSustainRateHwm                  CounterBasedGauge64,
    accStatSrcInCallBurstRateHwm                  CounterBasedGauge64,
    accStatSrcInCallSustainRateHwm                CounterBasedGauge64,
    accStatSrcOOCBurstRateHwm                     CounterBasedGauge64,
    accStatSrcOOCSustainRateHwm                   CounterBasedGauge64,
    accStatSrcRegsRateHwm                         CounterBasedGauge64,
    accStatSrcRegsSustainRateHwm                  CounterBasedGauge64,
    accStatSrcNumCallsPerc                        CounterBasedGauge64,
    accStatSrcMedBwPerc                           CounterBasedGauge64,
    accStatSrcMedStrPerc                          CounterBasedGauge64,
    accStatSrcNumRegsPerc                         CounterBasedGauge64,
    accStatSrcCallBurstRatePerc                   CounterBasedGauge64,
    accStatSrcCallSustainRatePerc                 CounterBasedGauge64,
    accStatSrcInCallBurstRatePerc                 CounterBasedGauge64,
    accStatSrcInCallSustainRatePerc               CounterBasedGauge64,
    accStatSrcOOCBurstRatePerc                    CounterBasedGauge64,
    accStatSrcOOCSustainRatePerc                  CounterBasedGauge64,
    accStatSrcRegsBurstRatePerc                   CounterBasedGauge64,
    accStatSrcRegsSustainRatePerc                 CounterBasedGauge64,
    accStatDstNumCallsHwm                         CounterBasedGauge64,
    accStatDstMedBwHwm                            CounterBasedGauge64,
    accStatDstMedStreamsHwm                       CounterBasedGauge64,
    accStatDstNumRegsHwm                          CounterBasedGauge64,
    accStatDstCallBurstRateHwm                    CounterBasedGauge64,
    accStatDstCallSustainRateHwm                  CounterBasedGauge64,
    accStatDstInCallBurstRateHwm                  CounterBasedGauge64,
    accStatDstInCallSustainRateHwm                CounterBasedGauge64,
    accStatDstOOCBurstRateHwm                     CounterBasedGauge64,
    accStatDstOOCSustainRateHwm                   CounterBasedGauge64,
    accStatDstRegsRateHwm                         CounterBasedGauge64,
    accStatDstRegsSustainRateHwm                  CounterBasedGauge64,
    accStatDstNumCallsPerc                        CounterBasedGauge64,
    accStatDstMedBwPerc                           CounterBasedGauge64,
    accStatDstMedStrPerc                          CounterBasedGauge64,
    accStatDstNumRegsPerc                         CounterBasedGauge64,
    accStatDstCallBurstRatePerc                   CounterBasedGauge64,
    accStatDstCallSustainRatePerc                 CounterBasedGauge64,
    accStatDstInCallBurstRatePerc                 CounterBasedGauge64,
    accStatDstInCallSustainRatePerc               CounterBasedGauge64,
    accStatDstOOCBurstRatePerc                    CounterBasedGauge64,
    accStatDstOOCSustainRatePerc                  CounterBasedGauge64,
    accStatDstRegsBurstRatePerc                   CounterBasedGauge64,
    accStatDstRegsSustainRatePerc                 CounterBasedGauge64,
    accStatNumCallsMLimit                         CounterBasedGauge64,
    accStatMedBwMLimit                            CounterBasedGauge64,
    accStatMedStrMLimit                           CounterBasedGauge64,
    accStatNumRegsMLimit                          CounterBasedGauge64,
    accStatCallBurstRateMLimit                    CounterBasedGauge64,
    accStatCallSustainRateMLimit                  CounterBasedGauge64,
    accStatInCallBurstRateMLimit                  CounterBasedGauge64,
    accStatInCallSustainRateMLimit                CounterBasedGauge64,
    accStatOOCBurstRateMLimit                     CounterBasedGauge64,
    accStatOOCSustainRateMLimit                   CounterBasedGauge64,
    accStatRegsBurstRateMLimit                    CounterBasedGauge64,
    accStatRegsSustainRateMLimit                  CounterBasedGauge64,
    accStatSrcNumCallsMLimit                      CounterBasedGauge64,
    accStatSrcMedBwMLimit                         CounterBasedGauge64,
    accStatSrcMedStrMLimit                        CounterBasedGauge64,
    accStatSrcNumRegsMLimit                       CounterBasedGauge64,
    accStatSrcCallBurstRateMLimit                 CounterBasedGauge64,
    accStatSrcCallSustainRateMLimit               CounterBasedGauge64,
    accStatSrcInCallBurstRateMLimit               CounterBasedGauge64,
    accStatSrcInCallSustainRateMLimit             CounterBasedGauge64,
    accStatSrcOOCBurstRateMLimit                  CounterBasedGauge64,
    accStatSrcOOCSustainRateMLimit                CounterBasedGauge64,
    accStatSrcRegsBurstRateMLimit                 CounterBasedGauge64,
    accStatSrcRegsSustainRateMLimit               CounterBasedGauge64,
    accStatDstNumCallsMLimit                      CounterBasedGauge64,
    accStatDstMedBwMLimit                         CounterBasedGauge64,
    accStatDstMedStrMLimit                        CounterBasedGauge64,
    accStatDstNumRegsMLimit                       CounterBasedGauge64,
    accStatDstCallBurstRateMLimit                 CounterBasedGauge64,
    accStatDstCallSustainRateMLimit               CounterBasedGauge64,
    accStatDstInCallBurstRateMLimit               CounterBasedGauge64,
    accStatDstInCallSustainRateMLimit             CounterBasedGauge64,
    accStatDstOOCBurstRateMLimit                  CounterBasedGauge64,
    accStatDstOOCSustainRateMLimit                CounterBasedGauge64,
    accStatDstRegsBurstRateMLimit                 CounterBasedGauge64,
    accStatDstRegsSustainRateMLimit               CounterBasedGauge64,
    accStatSrcMSRPSIWCallsCurrent                 CounterBasedGauge64,
    accStatSrcMSRPSPtCallsCurrent                 CounterBasedGauge64,
    accStatSrcMSRPSIWCallRate                     CounterBasedGauge64,
    accStatSrcMSRPSPtCallRate                     CounterBasedGauge64,
    accStatDstMSRPSIWCallsCurrent                 CounterBasedGauge64,
    accStatDstMSRPSPtCallsCurrent                 CounterBasedGauge64,
    accStatDstMSRPSIWCallRate                     CounterBasedGauge64,
    accStatDstMSRPSPtCallRate                     CounterBasedGauge64,
    accStatNumCallsHwmNMP                         CounterBasedGauge64,
    accStatMedBwHwmNMP                            CounterBasedGauge64,
    accStatMedStreamsHwmNMP                       CounterBasedGauge64,
    accStatNumRegsHwmNMP                          CounterBasedGauge64,
    accStatCallBurstRateHwmNMP                    CounterBasedGauge64,
    accStatCallSustainRateHwmNMP                  CounterBasedGauge64,
    accStatInCallBurstRateHwmNMP                  CounterBasedGauge64,
    accStatInCallSustainRateHwmNMP                CounterBasedGauge64,
    accStatOOCBurstRateHwmNMP                     CounterBasedGauge64,
    accStatOOCSustainRateHwmNMP                   CounterBasedGauge64,
    accStatRegsBurstRateHwmNMP                    CounterBasedGauge64,
    accStatRegsSustainRateHwmNMP                  CounterBasedGauge64,
    accStatSrcNumCallsHwmNMP                      CounterBasedGauge64,
    accStatSrcMedBwHwmNMP                         CounterBasedGauge64,
    accStatSrcMedStreamsHwmNMP                    CounterBasedGauge64,
    accStatSrcNumRegsHwmNMP                       CounterBasedGauge64,
    accStatSrcCallBurstRateHwmNMP                 CounterBasedGauge64,
    accStatSrcCallSustainRateHwmNMP               CounterBasedGauge64,
    accStatSrcInCallBurstRateHwmNMP               CounterBasedGauge64,
    accStatSrcInCallSustainRateHwmNMP             CounterBasedGauge64,
    accStatSrcOOCBurstRateHwmNMP                  CounterBasedGauge64,
    accStatSrcOOCSustainRateHwmNMP                CounterBasedGauge64,
    accStatSrcRegsBurstRateHwmNMP                 CounterBasedGauge64,
    accStatSrcRegsSustainRateHwmNMP               CounterBasedGauge64,
    accStatDstNumCallsHwmNMP                      CounterBasedGauge64,
    accStatDstMedBwHwmNMP                         CounterBasedGauge64,
    accStatDstMedStreamsHwmNMP                    CounterBasedGauge64,
    accStatDstNumRegsHwmNMP                       CounterBasedGauge64,
    accStatDstCallBurstRateHwmNMP                 CounterBasedGauge64,
    accStatDstCallSustainRateHwmNMP               CounterBasedGauge64,
    accStatDstInCallBurstRateHwmNMP               CounterBasedGauge64,
    accStatDstInCallSustainRateHwmNMP             CounterBasedGauge64,
    accStatDstOOCBurstRateHwmNMP                  CounterBasedGauge64,
    accStatDstOOCSustainRateHwmNMP                CounterBasedGauge64,
    accStatDstRegsBurstRateHwmNMP                 CounterBasedGauge64,
    accStatDstRegsSustainRateHwmNMP               CounterBasedGauge64
  }

  accStatAccountName OBJECT-TYPE
    SYNTAX      DisplayString (SIZE(1..32))
    MAX-ACCESS  not-accessible
    STATUS      current
    DESCRIPTION "The name of the account. This is the index field
                 for account statistics."
    ::= { perimetaAccountStatsEntry 1 }

  accStatSummaryPeriod OBJECT-TYPE
    SYNTAX       INTEGER {
                   summaryPeriod1CurrentClctnIntv(1)
                 }
    MAX-ACCESS   not-accessible
    STATUS       current
    DESCRIPTION  "The period over which the statistics were collected.
                  This is an index field."
    ::= { perimetaAccountStatsEntry 2 }

  accStatNumCallsHwm OBJECT-TYPE
    SYNTAX       CounterBasedGauge64
    MAX-ACCESS   read-only
    STATUS       current
    DESCRIPTION  "High water mark of active calls within
                  account"
    ::= { perimetaAccountStatsEntry 35 }

  accStatMedBwHwm OBJECT-TYPE
    SYNTAX       CounterBasedGauge64
    MAX-ACCESS   read-only
    STATUS       current
    DESCRIPTION  "High water mark of media bandwidth
                  within account"
    ::= { perimetaAccountStatsEntry 36 }

  accStatMedStreamsHwm OBJECT-TYPE
    SYNTAX       CounterBasedGauge64
    MAX-ACCESS   read-only
    STATUS       current
    DESCRIPTION  "High water mark of media streams within
                  account"
    ::= { perimetaAccountStatsEntry 37 }

  accStatNumRegsHwm OBJECT-TYPE
    SYNTAX       CounterBasedGauge64
    MAX-ACCESS   read-only
    STATUS       current
    DESCRIPTION  "High water mark of concurrent
                  registrations within account"
    ::= { perimetaAccountStatsEntry 38 }

  accStatCallBurstRateHwm OBJECT-TYPE
    SYNTAX       CounterBasedGauge64
    MAX-ACCESS   read-only
    STATUS       current
    DESCRIPTION  "High water mark of burst rate of call
                  setup within account"
    ::= { perimetaAccountStatsEntry 39 }

  accStatCallSustainRateHwm OBJECT-TYPE
    SYNTAX       CounterBasedGauge64
    MAX-ACCESS   read-only
    STATUS       current
    DESCRIPTION  "High water mark of sustained rate of
                  call setup within account"
    ::= { perimetaAccountStatsEntry 40 }

  accStatInCallBurstRateHwm OBJECT-TYPE
    SYNTAX       CounterBasedGauge64
    MAX-ACCESS   read-only
    STATUS       current
    DESCRIPTION  "High water mark of burst rate of in-call
                  messages within account"
    ::= { perimetaAccountStatsEntry 41 }

  accStatInCallSustainRateHwm OBJECT-TYPE
    SYNTAX       CounterBasedGauge64
    MAX-ACCESS   read-only
    STATUS       current
    DESCRIPTION  "High water mark of sustained rate of
                  in-call messages within account"
    ::= { perimetaAccountStatsEntry 42 }

  accStatOOCBurstRateHwm OBJECT-TYPE
    SYNTAX       CounterBasedGauge64
    MAX-ACCESS   read-only
    STATUS       current
    DESCRIPTION  "High water mark of burst rate of
                  out-of-call messages within account"
    ::= { perimetaAccountStatsEntry 43 }

  accStatOOCSustainRateHwm OBJECT-TYPE
    SYNTAX       CounterBasedGauge64
    MAX-ACCESS   read-only
    STATUS       current
    DESCRIPTION  "High water mark of sustained rate of
                  out-of-call messages within the account"
    ::= { perimetaAccountStatsEntry 44 }

  accStatRegsRateHwm OBJECT-TYPE
    SYNTAX       CounterBasedGauge64
    MAX-ACCESS   read-only
    STATUS       current
    DESCRIPTION  "High water mark of burst rate of
                  registration within account"
    ::= { perimetaAccountStatsEntry 45 }

  accStatRegsSustainRateHwm OBJECT-TYPE
    SYNTAX       CounterBasedGauge64
    MAX-ACCESS   read-only
    STATUS       current
    DESCRIPTION  "High water mark of sustained rate of
                  registration within account"
    ::= { perimetaAccountStatsEntry 46 }

  accStatNumCallsPerc OBJECT-TYPE
    SYNTAX       CounterBasedGauge64
    UNITS        "/ 10000 %"
    MAX-ACCESS   read-only
    STATUS       current
    DESCRIPTION  "% of currently active calls versus call
                  limit within account"
    ::= { perimetaAccountStatsEntry 47 }

  accStatMedBwPerc OBJECT-TYPE
    SYNTAX       CounterBasedGauge64
    UNITS        "/ 10000 %"
    MAX-ACCESS   read-only
    STATUS       current
    DESCRIPTION  "% of media bandwidth versus bandwidth
                  limit within account"
    ::= { perimetaAccountStatsEntry 48 }

  accStatMedStrPerc OBJECT-TYPE
    SYNTAX       CounterBasedGauge64
    UNITS        "/ 10000 %"
    MAX-ACCESS   read-only
    STATUS       current
    DESCRIPTION  "% of media streams versus limit within
                  account"
    ::= { perimetaAccountStatsEntry 49 }

  accStatNumRegsPerc OBJECT-TYPE
    SYNTAX       CounterBasedGauge64
    UNITS        "/ 10000 %"
    MAX-ACCESS   read-only
    STATUS       current
    DESCRIPTION  "% of registrations versus limit within
                  account"
    ::= { perimetaAccountStatsEntry 50 }

  accStatCallBurstRatePerc OBJECT-TYPE
    SYNTAX       CounterBasedGauge64
    UNITS        "/ 10000 %"
    MAX-ACCESS   read-only
    STATUS       current
    DESCRIPTION  "% of burst call rate versus limit within
                  account"
    ::= { perimetaAccountStatsEntry 51 }

  accStatCallSustainRatePerc OBJECT-TYPE
    SYNTAX       CounterBasedGauge64
    UNITS        "/ 10000 %"
    MAX-ACCESS   read-only
    STATUS       current
    DESCRIPTION  "% of sustained call rate versus limit
                  within account"
    ::= { perimetaAccountStatsEntry 52 }

  accStatInCallBurstRatePerc OBJECT-TYPE
    SYNTAX       CounterBasedGauge64
    UNITS        "/ 10000 %"
    MAX-ACCESS   read-only
    STATUS       current
    DESCRIPTION  "% of burst in-call message rate versus
                  limit within account"
    ::= { perimetaAccountStatsEntry 53 }

  accStatInCallSustainRatePerc OBJECT-TYPE
    SYNTAX       CounterBasedGauge64
    UNITS        "/ 10000 %"
    MAX-ACCESS   read-only
    STATUS       current
    DESCRIPTION  "% of sustained in-call message rate
                  versus limit within account"
    ::= { perimetaAccountStatsEntry 54 }

  accStatOOCBurstRatePerc OBJECT-TYPE
    SYNTAX       CounterBasedGauge64
    UNITS        "/ 10000 %"
    MAX-ACCESS   read-only
    STATUS       current
    DESCRIPTION  "% of burst out-of-call message rate
                  versus limit within account"
    ::= { perimetaAccountStatsEntry 55 }

  accStatOOCSustainRatePerc OBJECT-TYPE
    SYNTAX       CounterBasedGauge64
    UNITS        "/ 10000 %"
    MAX-ACCESS   read-only
    STATUS       current
    DESCRIPTION  "% of sustained out-of-call message rate
                  versus limit within account"
    ::= { perimetaAccountStatsEntry 56 }

  accStatRegsBurstRatePerc OBJECT-TYPE
    SYNTAX       CounterBasedGauge64
    UNITS        "/ 10000 %"
    MAX-ACCESS   read-only
    STATUS       current
    DESCRIPTION  "% of burst registration rate versus
                  limit within account"
    ::= { perimetaAccountStatsEntry 57 }

  accStatRegsSustainRatePerc OBJECT-TYPE
    SYNTAX       CounterBasedGauge64
    UNITS        "/ 10000 %"
    MAX-ACCESS   read-only
    STATUS       current
    DESCRIPTION  "% of sustained registration rate versus
                  limit within account"
    ::= { perimetaAccountStatsEntry 58 }

  accStatSrcNumCallsHwm OBJECT-TYPE
    SYNTAX       CounterBasedGauge64
    MAX-ACCESS   read-only
    STATUS       current
    DESCRIPTION  "High water mark of calls within source
                  account"
    ::= { perimetaAccountStatsEntry 83 }

  accStatSrcMedBwHwm OBJECT-TYPE
    SYNTAX       CounterBasedGauge64
    MAX-ACCESS   read-only
    STATUS       current
    DESCRIPTION  "High water mark of media bandwidth
                  within source account"
    ::= { perimetaAccountStatsEntry 84 }

  accStatSrcMedStreamsHwm OBJECT-TYPE
    SYNTAX       CounterBasedGauge64
    MAX-ACCESS   read-only
    STATUS       current
    DESCRIPTION  "High water mark of media streams within
                  source account"
    ::= { perimetaAccountStatsEntry 85 }

  accStatSrcNumRegsHwm OBJECT-TYPE
    SYNTAX       CounterBasedGauge64
    MAX-ACCESS   read-only
    STATUS       current
    DESCRIPTION  "High water mark of concurrent
                  registrations within source account"
    ::= { perimetaAccountStatsEntry 86 }

  accStatSrcCallBurstRateHwm OBJECT-TYPE
    SYNTAX       CounterBasedGauge64
    MAX-ACCESS   read-only
    STATUS       current
    DESCRIPTION  "High water mark of burst rate of call
                  setup within source account"
    ::= { perimetaAccountStatsEntry 87 }

  accStatSrcCallSustainRateHwm OBJECT-TYPE
    SYNTAX       CounterBasedGauge64
    MAX-ACCESS   read-only
    STATUS       current
    DESCRIPTION  "High water mark of sustained rate of
                  call setup within source account"
    ::= { perimetaAccountStatsEntry 88 }

  accStatSrcInCallBurstRateHwm OBJECT-TYPE
    SYNTAX       CounterBasedGauge64
    MAX-ACCESS   read-only
    STATUS       current
    DESCRIPTION  "High water mark of burst rate of in-call
                  messages within source account"
    ::= { perimetaAccountStatsEntry 89 }

  accStatSrcInCallSustainRateHwm OBJECT-TYPE
    SYNTAX       CounterBasedGauge64
    MAX-ACCESS   read-only
    STATUS       current
    DESCRIPTION  "High water mark of sustained rate of
                  in-call messages within source account"
    ::= { perimetaAccountStatsEntry 90 }

  accStatSrcOOCBurstRateHwm OBJECT-TYPE
    SYNTAX       CounterBasedGauge64
    MAX-ACCESS   read-only
    STATUS       current
    DESCRIPTION  "High water mark of burst rate of
                  out-of-call messages within source
                  account"
    ::= { perimetaAccountStatsEntry 91 }

  accStatSrcOOCSustainRateHwm OBJECT-TYPE
    SYNTAX       CounterBasedGauge64
    MAX-ACCESS   read-only
    STATUS       current
    DESCRIPTION  "High water mark of sustained rate of
                  out-of-call messages within the source
                  account"
    ::= { perimetaAccountStatsEntry 92 }

  accStatSrcRegsRateHwm OBJECT-TYPE
    SYNTAX       CounterBasedGauge64
    MAX-ACCESS   read-only
    STATUS       current
    DESCRIPTION  "High water mark of burst rate of
                  registration within source account"
    ::= { perimetaAccountStatsEntry 93 }

  accStatSrcRegsSustainRateHwm OBJECT-TYPE
    SYNTAX       CounterBasedGauge64
    MAX-ACCESS   read-only
    STATUS       current
    DESCRIPTION  "High water mark of sustained rate of
                  registration within source account"
    ::= { perimetaAccountStatsEntry 94 }

  accStatSrcNumCallsPerc OBJECT-TYPE
    SYNTAX       CounterBasedGauge64
    UNITS        "/ 10000 %"
    MAX-ACCESS   read-only
    STATUS       current
    DESCRIPTION  "% of currently active calls versus call
                  limit within source account"
    ::= { perimetaAccountStatsEntry 95 }

  accStatSrcMedBwPerc OBJECT-TYPE
    SYNTAX       CounterBasedGauge64
    UNITS        "/ 10000 %"
    MAX-ACCESS   read-only
    STATUS       current
    DESCRIPTION  "% of media bandwidth versus bandwidth
                  limit within source account"
    ::= { perimetaAccountStatsEntry 96 }

  accStatSrcMedStrPerc OBJECT-TYPE
    SYNTAX       CounterBasedGauge64
    UNITS        "/ 10000 %"
    MAX-ACCESS   read-only
    STATUS       current
    DESCRIPTION  "% of media streams versus limit within
                  source account"
    ::= { perimetaAccountStatsEntry 97 }

  accStatSrcNumRegsPerc OBJECT-TYPE
    SYNTAX       CounterBasedGauge64
    UNITS        "/ 10000 %"
    MAX-ACCESS   read-only
    STATUS       current
    DESCRIPTION  "% of registrations versus limit within
                  source account"
    ::= { perimetaAccountStatsEntry 98 }

  accStatSrcCallBurstRatePerc OBJECT-TYPE
    SYNTAX       CounterBasedGauge64
    UNITS        "/ 10000 %"
    MAX-ACCESS   read-only
    STATUS       current
    DESCRIPTION  "% of burst call rate versus limit within
                  source account"
    ::= { perimetaAccountStatsEntry 99 }

  accStatSrcCallSustainRatePerc OBJECT-TYPE
    SYNTAX       CounterBasedGauge64
    UNITS        "/ 10000 %"
    MAX-ACCESS   read-only
    STATUS       current
    DESCRIPTION  "% of sustained call rate versus limit
                  within source account"
    ::= { perimetaAccountStatsEntry 100 }

  accStatSrcInCallBurstRatePerc OBJECT-TYPE
    SYNTAX       CounterBasedGauge64
    UNITS        "/ 10000 %"
    MAX-ACCESS   read-only
    STATUS       current
    DESCRIPTION  "% of burst in-call message rate versus
                  limit within source account"
    ::= { perimetaAccountStatsEntry 101 }

  accStatSrcInCallSustainRatePerc OBJECT-TYPE
    SYNTAX       CounterBasedGauge64
    UNITS        "/ 10000 %"
    MAX-ACCESS   read-only
    STATUS       current
    DESCRIPTION  "% of sustained in-call message rate
                  versus limit within source account"
    ::= { perimetaAccountStatsEntry 102 }

  accStatSrcOOCBurstRatePerc OBJECT-TYPE
    SYNTAX       CounterBasedGauge64
    UNITS        "/ 10000 %"
    MAX-ACCESS   read-only
    STATUS       current
    DESCRIPTION  "% of burst out-of-call message rate
                  versus limit within source account"
    ::= { perimetaAccountStatsEntry 103 }

  accStatSrcOOCSustainRatePerc OBJECT-TYPE
    SYNTAX       CounterBasedGauge64
    UNITS        "/ 10000 %"
    MAX-ACCESS   read-only
    STATUS       current
    DESCRIPTION  "% of sustained out-of-call message rate
                  versus limit within source account"
    ::= { perimetaAccountStatsEntry 104 }

  accStatSrcRegsBurstRatePerc OBJECT-TYPE
    SYNTAX       CounterBasedGauge64
    UNITS        "/ 10000 %"
    MAX-ACCESS   read-only
    STATUS       current
    DESCRIPTION  "% of burst registration rate versus
                  limit within source account"
    ::= { perimetaAccountStatsEntry 105 }

  accStatSrcRegsSustainRatePerc OBJECT-TYPE
    SYNTAX       CounterBasedGauge64
    UNITS        "/ 10000 %"
    MAX-ACCESS   read-only
    STATUS       current
    DESCRIPTION  "% of sustained registration rate versus
                  limit within source account"
    ::= { perimetaAccountStatsEntry 106 }

  accStatDstNumCallsHwm OBJECT-TYPE
    SYNTAX       CounterBasedGauge64
    MAX-ACCESS   read-only
    STATUS       current
    DESCRIPTION  "High water mark of calls within
                  destination account"
    ::= { perimetaAccountStatsEntry 131 }

  accStatDstMedBwHwm OBJECT-TYPE
    SYNTAX       CounterBasedGauge64
    MAX-ACCESS   read-only
    STATUS       current
    DESCRIPTION  "High water mark of media bandwidth
                  within destination account"
    ::= { perimetaAccountStatsEntry 132 }

  accStatDstMedStreamsHwm OBJECT-TYPE
    SYNTAX       CounterBasedGauge64
    MAX-ACCESS   read-only
    STATUS       current
    DESCRIPTION  "High water mark of media streams within
                  destination account"
    ::= { perimetaAccountStatsEntry 133 }

  accStatDstNumRegsHwm OBJECT-TYPE
    SYNTAX       CounterBasedGauge64
    MAX-ACCESS   read-only
    STATUS       current
    DESCRIPTION  "High water mark of concurrent
                  registrations within destination account"
    ::= { perimetaAccountStatsEntry 134 }

  accStatDstCallBurstRateHwm OBJECT-TYPE
    SYNTAX       CounterBasedGauge64
    MAX-ACCESS   read-only
    STATUS       current
    DESCRIPTION  "High water mark of burst rate of call
                  setup within destination account"
    ::= { perimetaAccountStatsEntry 135 }

  accStatDstCallSustainRateHwm OBJECT-TYPE
    SYNTAX       CounterBasedGauge64
    MAX-ACCESS   read-only
    STATUS       current
    DESCRIPTION  "High water mark of sustained rate of
                  call setup within destination account"
    ::= { perimetaAccountStatsEntry 136 }

  accStatDstInCallBurstRateHwm OBJECT-TYPE
    SYNTAX       CounterBasedGauge64
    MAX-ACCESS   read-only
    STATUS       current
    DESCRIPTION  "High water mark of burst rate of in-call
                  messages within destination account"
    ::= { perimetaAccountStatsEntry 137 }

  accStatDstInCallSustainRateHwm OBJECT-TYPE
    SYNTAX       CounterBasedGauge64
    MAX-ACCESS   read-only
    STATUS       current
    DESCRIPTION  "High water mark of sustained rate of
                  in-call messages within destination
                  account"
    ::= { perimetaAccountStatsEntry 138 }

  accStatDstOOCBurstRateHwm OBJECT-TYPE
    SYNTAX       CounterBasedGauge64
    MAX-ACCESS   read-only
    STATUS       current
    DESCRIPTION  "High water mark of burst rate of
                  out-of-call messages within destination
                  account"
    ::= { perimetaAccountStatsEntry 139 }

  accStatDstOOCSustainRateHwm OBJECT-TYPE
    SYNTAX       CounterBasedGauge64
    MAX-ACCESS   read-only
    STATUS       current
    DESCRIPTION  "High water mark of sustained rate of
                  out-of-call messages within the
                  destination account"
    ::= { perimetaAccountStatsEntry 140 }

  accStatDstRegsRateHwm OBJECT-TYPE
    SYNTAX       CounterBasedGauge64
    MAX-ACCESS   read-only
    STATUS       current
    DESCRIPTION  "High water mark of burst rate of
                  registration within destination account"
    ::= { perimetaAccountStatsEntry 141 }

  accStatDstRegsSustainRateHwm OBJECT-TYPE
    SYNTAX       CounterBasedGauge64
    MAX-ACCESS   read-only
    STATUS       current
    DESCRIPTION  "High water mark of sustained rate of
                  registration within destination account"
    ::= { perimetaAccountStatsEntry 142 }

  accStatDstNumCallsPerc OBJECT-TYPE
    SYNTAX       CounterBasedGauge64
    UNITS        "/ 10000 %"
    MAX-ACCESS   read-only
    STATUS       current
    DESCRIPTION  "% of currently active calls versus call
                  limit within destination account"
    ::= { perimetaAccountStatsEntry 143 }

  accStatDstMedBwPerc OBJECT-TYPE
    SYNTAX       CounterBasedGauge64
    UNITS        "/ 10000 %"
    MAX-ACCESS   read-only
    STATUS       current
    DESCRIPTION  "% of media bandwidth versus bandwidth
                  limit within destination account"
    ::= { perimetaAccountStatsEntry 144 }

  accStatDstMedStrPerc OBJECT-TYPE
    SYNTAX       CounterBasedGauge64
    UNITS        "/ 10000 %"
    MAX-ACCESS   read-only
    STATUS       current
    DESCRIPTION  "% of media streams versus limit within
                  destination account"
    ::= { perimetaAccountStatsEntry 145 }

  accStatDstNumRegsPerc OBJECT-TYPE
    SYNTAX       CounterBasedGauge64
    UNITS        "/ 10000 %"
    MAX-ACCESS   read-only
    STATUS       current
    DESCRIPTION  "% of registrations versus limit within
                  destination account"
    ::= { perimetaAccountStatsEntry 146 }

  accStatDstCallBurstRatePerc OBJECT-TYPE
    SYNTAX       CounterBasedGauge64
    UNITS        "/ 10000 %"
    MAX-ACCESS   read-only
    STATUS       current
    DESCRIPTION  "% of burst call rate versus limit within
                  destination account"
    ::= { perimetaAccountStatsEntry 147 }

  accStatDstCallSustainRatePerc OBJECT-TYPE
    SYNTAX       CounterBasedGauge64
    UNITS        "/ 10000 %"
    MAX-ACCESS   read-only
    STATUS       current
    DESCRIPTION  "% of sustained call rate versus limit
                  within destination account"
    ::= { perimetaAccountStatsEntry 148 }

  accStatDstInCallBurstRatePerc OBJECT-TYPE
    SYNTAX       CounterBasedGauge64
    UNITS        "/ 10000 %"
    MAX-ACCESS   read-only
    STATUS       current
    DESCRIPTION  "% of burst in-call message rate versus
                  limit within destination account"
    ::= { perimetaAccountStatsEntry 149 }

  accStatDstInCallSustainRatePerc OBJECT-TYPE
    SYNTAX       CounterBasedGauge64
    UNITS        "/ 10000 %"
    MAX-ACCESS   read-only
    STATUS       current
    DESCRIPTION  "% of sustained in-call message rate
                  versus limit within destination account"
    ::= { perimetaAccountStatsEntry 150 }

  accStatDstOOCBurstRatePerc OBJECT-TYPE
    SYNTAX       CounterBasedGauge64
    UNITS        "/ 10000 %"
    MAX-ACCESS   read-only
    STATUS       current
    DESCRIPTION  "% of burst out-of-call message rate
                  versus limit within destination account"
    ::= { perimetaAccountStatsEntry 151 }

  accStatDstOOCSustainRatePerc OBJECT-TYPE
    SYNTAX       CounterBasedGauge64
    UNITS        "/ 10000 %"
    MAX-ACCESS   read-only
    STATUS       current
    DESCRIPTION  "% of sustained out-of-call message rate
                  versus limit within destination account"
    ::= { perimetaAccountStatsEntry 152 }

  accStatDstRegsBurstRatePerc OBJECT-TYPE
    SYNTAX       CounterBasedGauge64
    UNITS        "/ 10000 %"
    MAX-ACCESS   read-only
    STATUS       current
    DESCRIPTION  "% of burst registration rate versus
                  limit within destination account"
    ::= { perimetaAccountStatsEntry 153 }

  accStatDstRegsSustainRatePerc OBJECT-TYPE
    SYNTAX       CounterBasedGauge64
    UNITS        "/ 10000 %"
    MAX-ACCESS   read-only
    STATUS       current
    DESCRIPTION  "% of sustained registration rate versus
                  limit within destination account"
    ::= { perimetaAccountStatsEntry 154 }

  accStatNumCallsMLimit OBJECT-TYPE
    SYNTAX       CounterBasedGauge64
    MAX-ACCESS   read-only
    STATUS       current
    DESCRIPTION  "Active call limit within account"
    ::= { perimetaAccountStatsEntry 155 }

  accStatMedBwMLimit OBJECT-TYPE
    SYNTAX       CounterBasedGauge64
    MAX-ACCESS   read-only
    STATUS       current
    DESCRIPTION  "Bandwidth limit within account"
    ::= { perimetaAccountStatsEntry 156 }

  accStatMedStrMLimit OBJECT-TYPE
    SYNTAX       CounterBasedGauge64
    MAX-ACCESS   read-only
    STATUS       current
    DESCRIPTION  "Media streams limit within account"
    ::= { perimetaAccountStatsEntry 157 }

  accStatNumRegsMLimit OBJECT-TYPE
    SYNTAX       CounterBasedGauge64
    MAX-ACCESS   read-only
    STATUS       current
    DESCRIPTION  "Registrations limit within account"
    ::= { perimetaAccountStatsEntry 158 }

  accStatCallBurstRateMLimit OBJECT-TYPE
    SYNTAX       CounterBasedGauge64
    MAX-ACCESS   read-only
    STATUS       current
    DESCRIPTION  "Burst call rate limit (per min) within
                  account"
    ::= { perimetaAccountStatsEntry 159 }

  accStatCallSustainRateMLimit OBJECT-TYPE
    SYNTAX       CounterBasedGauge64
    MAX-ACCESS   read-only
    STATUS       current
    DESCRIPTION  "Sustained call rate limit (per min)
                  within account"
    ::= { perimetaAccountStatsEntry 160 }

  accStatInCallBurstRateMLimit OBJECT-TYPE
    SYNTAX       CounterBasedGauge64
    MAX-ACCESS   read-only
    STATUS       current
    DESCRIPTION  "Burst in-call message rate limit (per
                  min) within account"
    ::= { perimetaAccountStatsEntry 161 }

  accStatInCallSustainRateMLimit OBJECT-TYPE
    SYNTAX       CounterBasedGauge64
    MAX-ACCESS   read-only
    STATUS       current
    DESCRIPTION  "Sustained in-call message rate limit
                  (per min) within account"
    ::= { perimetaAccountStatsEntry 162 }

  accStatOOCBurstRateMLimit OBJECT-TYPE
    SYNTAX       CounterBasedGauge64
    MAX-ACCESS   read-only
    STATUS       current
    DESCRIPTION  "Burst out-of-call message rate limit
                  (per min) within account"
    ::= { perimetaAccountStatsEntry 163 }

  accStatOOCSustainRateMLimit OBJECT-TYPE
    SYNTAX       CounterBasedGauge64
    MAX-ACCESS   read-only
    STATUS       current
    DESCRIPTION  "Sustained out-of-call message rate limit
                  (per min) within account"
    ::= { perimetaAccountStatsEntry 164 }

  accStatRegsBurstRateMLimit OBJECT-TYPE
    SYNTAX       CounterBasedGauge64
    MAX-ACCESS   read-only
    STATUS       current
    DESCRIPTION  "Burst registration rate limit (per min)
                  within account"
    ::= { perimetaAccountStatsEntry 165 }

  accStatRegsSustainRateMLimit OBJECT-TYPE
    SYNTAX       CounterBasedGauge64
    MAX-ACCESS   read-only
    STATUS       current
    DESCRIPTION  "Sustained registration rate limit (per
                  min) within account"
    ::= { perimetaAccountStatsEntry 166 }

  accStatSrcNumCallsMLimit OBJECT-TYPE
    SYNTAX       CounterBasedGauge64
    MAX-ACCESS   read-only
    STATUS       current
    DESCRIPTION  "Currently active calls limit within
                  source account"
    ::= { perimetaAccountStatsEntry 167 }

  accStatSrcMedBwMLimit OBJECT-TYPE
    SYNTAX       CounterBasedGauge64
    MAX-ACCESS   read-only
    STATUS       current
    DESCRIPTION  "Media bandwidth limit within source
                  account"
    ::= { perimetaAccountStatsEntry 168 }

  accStatSrcMedStrMLimit OBJECT-TYPE
    SYNTAX       CounterBasedGauge64
    MAX-ACCESS   read-only
    STATUS       current
    DESCRIPTION  "Media streams limit within source
                  account"
    ::= { perimetaAccountStatsEntry 169 }

  accStatSrcNumRegsMLimit OBJECT-TYPE
    SYNTAX       CounterBasedGauge64
    MAX-ACCESS   read-only
    STATUS       current
    DESCRIPTION  "Registrations limit within source
                  account"
    ::= { perimetaAccountStatsEntry 170 }

  accStatSrcCallBurstRateMLimit OBJECT-TYPE
    SYNTAX       CounterBasedGauge64
    MAX-ACCESS   read-only
    STATUS       current
    DESCRIPTION  "Burst call rate limit (per min) within
                  source account"
    ::= { perimetaAccountStatsEntry 171 }

  accStatSrcCallSustainRateMLimit OBJECT-TYPE
    SYNTAX       CounterBasedGauge64
    MAX-ACCESS   read-only
    STATUS       current
    DESCRIPTION  "Sustained call rate limit (per min)
                  within source account"
    ::= { perimetaAccountStatsEntry 172 }

  accStatSrcInCallBurstRateMLimit OBJECT-TYPE
    SYNTAX       CounterBasedGauge64
    MAX-ACCESS   read-only
    STATUS       current
    DESCRIPTION  "Burst in-call message rate limit (per
                  min) within source account"
    ::= { perimetaAccountStatsEntry 173 }

  accStatSrcInCallSustainRateMLimit OBJECT-TYPE
    SYNTAX       CounterBasedGauge64
    MAX-ACCESS   read-only
    STATUS       current
    DESCRIPTION  "Sustained in-call message rate limit
                  (per min) within source account"
    ::= { perimetaAccountStatsEntry 174 }

  accStatSrcOOCBurstRateMLimit OBJECT-TYPE
    SYNTAX       CounterBasedGauge64
    MAX-ACCESS   read-only
    STATUS       current
    DESCRIPTION  "Burst out-of-call message rate limit
                  (per min) within source account"
    ::= { perimetaAccountStatsEntry 175 }

  accStatSrcOOCSustainRateMLimit OBJECT-TYPE
    SYNTAX       CounterBasedGauge64
    MAX-ACCESS   read-only
    STATUS       current
    DESCRIPTION  "Sustained out-of-call message rate limit
                  (per min) within source account"
    ::= { perimetaAccountStatsEntry 176 }

  accStatSrcRegsBurstRateMLimit OBJECT-TYPE
    SYNTAX       CounterBasedGauge64
    MAX-ACCESS   read-only
    STATUS       current
    DESCRIPTION  "Burst registration rate limit (per min)
                  within source account"
    ::= { perimetaAccountStatsEntry 177 }

  accStatSrcRegsSustainRateMLimit OBJECT-TYPE
    SYNTAX       CounterBasedGauge64
    MAX-ACCESS   read-only
    STATUS       current
    DESCRIPTION  "Sustained registration rate limit (per
                  min) within source account"
    ::= { perimetaAccountStatsEntry 178 }

  accStatDstNumCallsMLimit OBJECT-TYPE
    SYNTAX       CounterBasedGauge64
    MAX-ACCESS   read-only
    STATUS       current
    DESCRIPTION  "Currently active calls limit within
                  destination account"
    ::= { perimetaAccountStatsEntry 179 }

  accStatDstMedBwMLimit OBJECT-TYPE
    SYNTAX       CounterBasedGauge64
    MAX-ACCESS   read-only
    STATUS       current
    DESCRIPTION  "Media bandwidth limit within destination
                  account"
    ::= { perimetaAccountStatsEntry 180 }

  accStatDstMedStrMLimit OBJECT-TYPE
    SYNTAX       CounterBasedGauge64
    MAX-ACCESS   read-only
    STATUS       current
    DESCRIPTION  "Media streams limit within destination
                  account"
    ::= { perimetaAccountStatsEntry 181 }

  accStatDstNumRegsMLimit OBJECT-TYPE
    SYNTAX       CounterBasedGauge64
    MAX-ACCESS   read-only
    STATUS       current
    DESCRIPTION  "Registrations limit within destination
                  account"
    ::= { perimetaAccountStatsEntry 182 }

  accStatDstCallBurstRateMLimit OBJECT-TYPE
    SYNTAX       CounterBasedGauge64
    MAX-ACCESS   read-only
    STATUS       current
    DESCRIPTION  "Burst call rate limit (per min) within
                  destination account"
    ::= { perimetaAccountStatsEntry 183 }

  accStatDstCallSustainRateMLimit OBJECT-TYPE
    SYNTAX       CounterBasedGauge64
    MAX-ACCESS   read-only
    STATUS       current
    DESCRIPTION  "Sustained call rate limit (per min)
                  within destination account"
    ::= { perimetaAccountStatsEntry 184 }

  accStatDstInCallBurstRateMLimit OBJECT-TYPE
    SYNTAX       CounterBasedGauge64
    MAX-ACCESS   read-only
    STATUS       current
    DESCRIPTION  "Burst in-call message rate limit (per
                  min) within destination account"
    ::= { perimetaAccountStatsEntry 185 }

  accStatDstInCallSustainRateMLimit OBJECT-TYPE
    SYNTAX       CounterBasedGauge64
    MAX-ACCESS   read-only
    STATUS       current
    DESCRIPTION  "Sustained in-call message rate limit
                  (per min) within destination account"
    ::= { perimetaAccountStatsEntry 186 }

  accStatDstOOCBurstRateMLimit OBJECT-TYPE
    SYNTAX       CounterBasedGauge64
    MAX-ACCESS   read-only
    STATUS       current
    DESCRIPTION  "Burst out-of-call message rate limit
                  (per min) within destination account"
    ::= { perimetaAccountStatsEntry 187 }

  accStatDstOOCSustainRateMLimit OBJECT-TYPE
    SYNTAX       CounterBasedGauge64
    MAX-ACCESS   read-only
    STATUS       current
    DESCRIPTION  "Sustained out-of-call message rate limit
                  (per min) within destination account"
    ::= { perimetaAccountStatsEntry 188 }

  accStatDstRegsBurstRateMLimit OBJECT-TYPE
    SYNTAX       CounterBasedGauge64
    MAX-ACCESS   read-only
    STATUS       current
    DESCRIPTION  "Burst registration rate limit (per min)
                  within destination account"
    ::= { perimetaAccountStatsEntry 189 }

  accStatDstRegsSustainRateMLimit OBJECT-TYPE
    SYNTAX       CounterBasedGauge64
    MAX-ACCESS   read-only
    STATUS       current
    DESCRIPTION  "Sustained registration rate limit (per
                  min) within destination account"
    ::= { perimetaAccountStatsEntry 190 }

  accStatSrcMSRPSIWCallsCurrent OBJECT-TYPE
    SYNTAX       CounterBasedGauge64
    MAX-ACCESS   read-only
    STATUS       current
    DESCRIPTION  "Current number of MSRPS interworking
                  calls on this source account"
    ::= { perimetaAccountStatsEntry 191 }

  accStatSrcMSRPSPtCallsCurrent OBJECT-TYPE
    SYNTAX       CounterBasedGauge64
    MAX-ACCESS   read-only
    STATUS       current
    DESCRIPTION  "Current number of MSRPS passthrough
                  calls on this source account"
    ::= { perimetaAccountStatsEntry 192 }

  accStatSrcMSRPSIWCallRate OBJECT-TYPE
    SYNTAX       CounterBasedGauge64
    MAX-ACCESS   read-only
    STATUS       current
    DESCRIPTION  "MSRPS interworking calls/second rate on
                  this source account"
    ::= { perimetaAccountStatsEntry 195 }

  accStatSrcMSRPSPtCallRate OBJECT-TYPE
    SYNTAX       CounterBasedGauge64
    MAX-ACCESS   read-only
    STATUS       current
    DESCRIPTION  "MSRPS passthrough calls/second rate on
                  this source account"
    ::= { perimetaAccountStatsEntry 196 }

  accStatDstMSRPSIWCallsCurrent OBJECT-TYPE
    SYNTAX       CounterBasedGauge64
    MAX-ACCESS   read-only
    STATUS       current
    DESCRIPTION  "Current number of MSRPS interworking
                  calls on this destination account"
    ::= { perimetaAccountStatsEntry 197 }

  accStatDstMSRPSPtCallsCurrent OBJECT-TYPE
    SYNTAX       CounterBasedGauge64
    MAX-ACCESS   read-only
    STATUS       current
    DESCRIPTION  "Current number of MSRPS passthrough
                  calls on this destination account"
    ::= { perimetaAccountStatsEntry 198 }

  accStatDstMSRPSIWCallRate OBJECT-TYPE
    SYNTAX       CounterBasedGauge64
    MAX-ACCESS   read-only
    STATUS       current
    DESCRIPTION  "MSRPS interworking calls/second rate on
                  this destination account"
    ::= { perimetaAccountStatsEntry 201 }

  accStatDstMSRPSPtCallRate OBJECT-TYPE
    SYNTAX       CounterBasedGauge64
    MAX-ACCESS   read-only
    STATUS       current
    DESCRIPTION  "MSRPS passthrough calls/second rate on
                  this destination account"
    ::= { perimetaAccountStatsEntry 202 }

  accStatNumCallsHwmNMP OBJECT-TYPE
    SYNTAX       CounterBasedGauge64
    MAX-ACCESS   read-only
    STATUS       current
    DESCRIPTION  "High water mark of active calls within
                  account during this statistics
                  collection interval"
    ::= { perimetaAccountStatsEntry 203 }

  accStatMedBwHwmNMP OBJECT-TYPE
    SYNTAX       CounterBasedGauge64
    MAX-ACCESS   read-only
    STATUS       current
    DESCRIPTION  "High water mark of media bandwidth
                  within account during this statistics
                  collection interval"
    ::= { perimetaAccountStatsEntry 204 }

  accStatMedStreamsHwmNMP OBJECT-TYPE
    SYNTAX       CounterBasedGauge64
    MAX-ACCESS   read-only
    STATUS       current
    DESCRIPTION  "High water mark of media streams within
                  account during this statistics
                  collection interval"
    ::= { perimetaAccountStatsEntry 205 }

  accStatNumRegsHwmNMP OBJECT-TYPE
    SYNTAX       CounterBasedGauge64
    MAX-ACCESS   read-only
    STATUS       current
    DESCRIPTION  "High water mark of concurrent
                  registrations within account during this
                  statistics collection interval"
    ::= { perimetaAccountStatsEntry 206 }

  accStatCallBurstRateHwmNMP OBJECT-TYPE
    SYNTAX       CounterBasedGauge64
    MAX-ACCESS   read-only
    STATUS       current
    DESCRIPTION  "High water mark of burst rate of call
                  setup within account during this
                  statistics collection interval"
    ::= { perimetaAccountStatsEntry 207 }

  accStatCallSustainRateHwmNMP OBJECT-TYPE
    SYNTAX       CounterBasedGauge64
    MAX-ACCESS   read-only
    STATUS       current
    DESCRIPTION  "High water mark of sustained rate of
                  call setup within account during this
                  statistics collection interval"
    ::= { perimetaAccountStatsEntry 208 }

  accStatInCallBurstRateHwmNMP OBJECT-TYPE
    SYNTAX       CounterBasedGauge64
    MAX-ACCESS   read-only
    STATUS       current
    DESCRIPTION  "High water mark of burst rate of in-call
                  messages within account during this
                  statistics collection interval"
    ::= { perimetaAccountStatsEntry 209 }

  accStatInCallSustainRateHwmNMP OBJECT-TYPE
    SYNTAX       CounterBasedGauge64
    MAX-ACCESS   read-only
    STATUS       current
    DESCRIPTION  "High water mark of sustained rate of
                  in-call messages within account during
                  this statistics collection interval"
    ::= { perimetaAccountStatsEntry 210 }

  accStatOOCBurstRateHwmNMP OBJECT-TYPE
    SYNTAX       CounterBasedGauge64
    MAX-ACCESS   read-only
    STATUS       current
    DESCRIPTION  "High water mark of burst rate of
                  out-of-call messages within account
                  during this statistics collection
                  interval"
    ::= { perimetaAccountStatsEntry 211 }

  accStatOOCSustainRateHwmNMP OBJECT-TYPE
    SYNTAX       CounterBasedGauge64
    MAX-ACCESS   read-only
    STATUS       current
    DESCRIPTION  "High water mark of sustained rate of
                  out-of-call messages within the account
                  during this statistics collection
                  interval"
    ::= { perimetaAccountStatsEntry 212 }

  accStatRegsBurstRateHwmNMP OBJECT-TYPE
    SYNTAX       CounterBasedGauge64
    MAX-ACCESS   read-only
    STATUS       current
    DESCRIPTION  "High water mark of burst rate of
                  registration within account during this
                  statistics collection interval"
    ::= { perimetaAccountStatsEntry 213 }

  accStatRegsSustainRateHwmNMP OBJECT-TYPE
    SYNTAX       CounterBasedGauge64
    MAX-ACCESS   read-only
    STATUS       current
    DESCRIPTION  "High water mark of sustained rate of
                  registration within account during this
                  statistics collection interval"
    ::= { perimetaAccountStatsEntry 214 }

  accStatSrcNumCallsHwmNMP OBJECT-TYPE
    SYNTAX       CounterBasedGauge64
    MAX-ACCESS   read-only
    STATUS       current
    DESCRIPTION  "High water mark of active calls within
                  source account during this statistics
                  collection interval"
    ::= { perimetaAccountStatsEntry 215 }

  accStatSrcMedBwHwmNMP OBJECT-TYPE
    SYNTAX       CounterBasedGauge64
    MAX-ACCESS   read-only
    STATUS       current
    DESCRIPTION  "High water mark of media bandwidth
                  within source account during this
                  statistics collection interval"
    ::= { perimetaAccountStatsEntry 216 }

  accStatSrcMedStreamsHwmNMP OBJECT-TYPE
    SYNTAX       CounterBasedGauge64
    MAX-ACCESS   read-only
    STATUS       current
    DESCRIPTION  "High water mark of media streams within
                  source account during this statistics
                  collection interval"
    ::= { perimetaAccountStatsEntry 217 }

  accStatSrcNumRegsHwmNMP OBJECT-TYPE
    SYNTAX       CounterBasedGauge64
    MAX-ACCESS   read-only
    STATUS       current
    DESCRIPTION  "High water mark of concurrent
                  registrations within source account
                  during this statistics collection
                  interval"
    ::= { perimetaAccountStatsEntry 218 }

  accStatSrcCallBurstRateHwmNMP OBJECT-TYPE
    SYNTAX       CounterBasedGauge64
    MAX-ACCESS   read-only
    STATUS       current
    DESCRIPTION  "High water mark of burst rate of call
                  setup within source account during this
                  statistics collection interval"
    ::= { perimetaAccountStatsEntry 219 }

  accStatSrcCallSustainRateHwmNMP OBJECT-TYPE
    SYNTAX       CounterBasedGauge64
    MAX-ACCESS   read-only
    STATUS       current
    DESCRIPTION  "High water mark of sustained rate of
                  call setup within source account during
                  this statistics collection interval"
    ::= { perimetaAccountStatsEntry 220 }

  accStatSrcInCallBurstRateHwmNMP OBJECT-TYPE
    SYNTAX       CounterBasedGauge64
    MAX-ACCESS   read-only
    STATUS       current
    DESCRIPTION  "High water mark of burst rate of in-call
                  messages within source account during
                  this statistics collection interval"
    ::= { perimetaAccountStatsEntry 221 }

  accStatSrcInCallSustainRateHwmNMP OBJECT-TYPE
    SYNTAX       CounterBasedGauge64
    MAX-ACCESS   read-only
    STATUS       current
    DESCRIPTION  "High water mark of sustained rate of
                  in-call messages within source account
                  during this statistics collection
                  interval"
    ::= { perimetaAccountStatsEntry 222 }

  accStatSrcOOCBurstRateHwmNMP OBJECT-TYPE
    SYNTAX       CounterBasedGauge64
    MAX-ACCESS   read-only
    STATUS       current
    DESCRIPTION  "High water mark of burst rate of
                  out-of-call messages within source
                  account during this statistics
                  collection interval"
    ::= { perimetaAccountStatsEntry 223 }

  accStatSrcOOCSustainRateHwmNMP OBJECT-TYPE
    SYNTAX       CounterBasedGauge64
    MAX-ACCESS   read-only
    STATUS       current
    DESCRIPTION  "High water mark of sustained rate of
                  out-of-call messages within the source
                  account during this statistics
                  collection interval"
    ::= { perimetaAccountStatsEntry 224 }

  accStatSrcRegsBurstRateHwmNMP OBJECT-TYPE
    SYNTAX       CounterBasedGauge64
    MAX-ACCESS   read-only
    STATUS       current
    DESCRIPTION  "High water mark of burst rate of
                  registration within source account
                  during this statistics collection
                  interval"
    ::= { perimetaAccountStatsEntry 225 }

  accStatSrcRegsSustainRateHwmNMP OBJECT-TYPE
    SYNTAX       CounterBasedGauge64
    MAX-ACCESS   read-only
    STATUS       current
    DESCRIPTION  "High water mark of sustained rate of
                  registration within source account
                  during this statistics collection
                  interval"
    ::= { perimetaAccountStatsEntry 226 }

  accStatDstNumCallsHwmNMP OBJECT-TYPE
    SYNTAX       CounterBasedGauge64
    MAX-ACCESS   read-only
    STATUS       current
    DESCRIPTION  "High water mark of active calls within
                  destination account during this
                  statistics collection interval"
    ::= { perimetaAccountStatsEntry 227 }

  accStatDstMedBwHwmNMP OBJECT-TYPE
    SYNTAX       CounterBasedGauge64
    MAX-ACCESS   read-only
    STATUS       current
    DESCRIPTION  "High water mark of media bandwidth
                  within destination account during this
                  statistics collection interval"
    ::= { perimetaAccountStatsEntry 228 }

  accStatDstMedStreamsHwmNMP OBJECT-TYPE
    SYNTAX       CounterBasedGauge64
    MAX-ACCESS   read-only
    STATUS       current
    DESCRIPTION  "High water mark of media streams within
                  destination account during this
                  statistics collection interval"
    ::= { perimetaAccountStatsEntry 229 }

  accStatDstNumRegsHwmNMP OBJECT-TYPE
    SYNTAX       CounterBasedGauge64
    MAX-ACCESS   read-only
    STATUS       current
    DESCRIPTION  "High water mark of concurrent
                  registrations within destination account
                  during this statistics collection
                  interval"
    ::= { perimetaAccountStatsEntry 230 }

  accStatDstCallBurstRateHwmNMP OBJECT-TYPE
    SYNTAX       CounterBasedGauge64
    MAX-ACCESS   read-only
    STATUS       current
    DESCRIPTION  "High water mark of burst rate of call
                  setup within destination account during
                  this statistics collection interval"
    ::= { perimetaAccountStatsEntry 231 }

  accStatDstCallSustainRateHwmNMP OBJECT-TYPE
    SYNTAX       CounterBasedGauge64
    MAX-ACCESS   read-only
    STATUS       current
    DESCRIPTION  "High water mark of sustained rate of
                  call setup within destination account
                  during this statistics collection
                  interval"
    ::= { perimetaAccountStatsEntry 232 }

  accStatDstInCallBurstRateHwmNMP OBJECT-TYPE
    SYNTAX       CounterBasedGauge64
    MAX-ACCESS   read-only
    STATUS       current
    DESCRIPTION  "High water mark of burst rate of in-call
                  messages within destination account
                  during this statistics collection
                  interval"
    ::= { perimetaAccountStatsEntry 233 }

  accStatDstInCallSustainRateHwmNMP OBJECT-TYPE
    SYNTAX       CounterBasedGauge64
    MAX-ACCESS   read-only
    STATUS       current
    DESCRIPTION  "High water mark of sustained rate of
                  in-call messages within destination
                  account during this statistics
                  collection interval"
    ::= { perimetaAccountStatsEntry 234 }

  accStatDstOOCBurstRateHwmNMP OBJECT-TYPE
    SYNTAX       CounterBasedGauge64
    MAX-ACCESS   read-only
    STATUS       current
    DESCRIPTION  "High water mark of burst rate of
                  out-of-call messages within destination
                  account during this statistics
                  collection interval"
    ::= { perimetaAccountStatsEntry 235 }

  accStatDstOOCSustainRateHwmNMP OBJECT-TYPE
    SYNTAX       CounterBasedGauge64
    MAX-ACCESS   read-only
    STATUS       current
    DESCRIPTION  "High water mark of sustained rate of
                  out-of-call messages within the
                  destination account during this
                  statistics collection interval"
    ::= { perimetaAccountStatsEntry 236 }

  accStatDstRegsBurstRateHwmNMP OBJECT-TYPE
    SYNTAX       CounterBasedGauge64
    MAX-ACCESS   read-only
    STATUS       current
    DESCRIPTION  "High water mark of burst rate of
                  registration within destination account
                  during this statistics collection
                  interval"
    ::= { perimetaAccountStatsEntry 237 }

  accStatDstRegsSustainRateHwmNMP OBJECT-TYPE
    SYNTAX       CounterBasedGauge64
    MAX-ACCESS   read-only
    STATUS       current
    DESCRIPTION  "High water mark of sustained rate of
                  registration within destination account
                  during this statistics collection
                  interval"
    ::= { perimetaAccountStatsEntry 238 }

-- /**********************************************************/
-- /* Per-adjacency per-method information about SIP         */
-- /* responses                                              */
-- /**********************************************************/

  perimetaAdjacencyMethods OBJECT IDENTIFIER ::= { perimeta 5 }

  perimetaAdjacencyMethodStatsTable OBJECT-TYPE
    SYNTAX      SEQUENCE OF PerimetaAdjacencyMethodStatsEntry
    MAX-ACCESS  not-accessible
    STATUS      current
    DESCRIPTION "This table contains statistics from Perimeta at
                 per-adjacency per-method scope, indexed by
                 adjacency name and SIP method."
    ::= { perimetaAdjacencyMethods 1 }

  perimetaAdjacencyMethodStatsEntry OBJECT-TYPE
    SYNTAX      PerimetaAdjacencyMethodStatsEntry
    MAX-ACCESS  not-accessible
    STATUS      current
    DESCRIPTION "The entry in the Perimeta adjacency stats table
                 contains all the per-adjacency per-method
                 statistics, indexed on adjacency name and SIP
                 method."
    INDEX      { adjMthdStatAdjacencyName,
                 adjMthdStatSIPMethod,
                 adjMthdStatSummaryPeriod }
    ::= { perimetaAdjacencyMethodStatsTable 1 }

  PerimetaAdjacencyMethodStatsEntry ::= SEQUENCE
  {
    adjMthdStatAdjacencyName                      DisplayString,
    adjMthdStatSIPMethod                          INTEGER,
    adjMthdStatSummaryPeriod                      INTEGER,
    adjMthdStatRequestsRcvdRate                   CounterBasedGauge64,
    adjMthdStatRequestsRcvdCount                  CounterBasedGauge64,
    adjMthdStatRequestsSentRate                   CounterBasedGauge64,
    adjMthdStatRequestsSentCount                  CounterBasedGauge64,
    adjMthdStat1XXRcvdRate                        CounterBasedGauge64,
    adjMthdStat1XXRcvdCount                       CounterBasedGauge64,
    adjMthdStat1XXSentRate                        CounterBasedGauge64,
    adjMthdStat1XXSentCount                       CounterBasedGauge64,
    adjMthdStat2XXRcvdRate                        CounterBasedGauge64,
    adjMthdStat2XXRcvdCount                       CounterBasedGauge64,
    adjMthdStat2XXSentRate                        CounterBasedGauge64,
    adjMthdStat2XXSentCount                       CounterBasedGauge64,
    adjMthdStat3XXRcvdRate                        CounterBasedGauge64,
    adjMthdStat3XXRcvdCount                       CounterBasedGauge64,
    adjMthdStat3XXSentRate                        CounterBasedGauge64,
    adjMthdStat3XXSentCount                       CounterBasedGauge64,
    adjMthdStat4XXRcvdRate                        CounterBasedGauge64,
    adjMthdStat4XXRcvdCount                       CounterBasedGauge64,
    adjMthdStat4XXSentRate                        CounterBasedGauge64,
    adjMthdStat4XXSentCount                       CounterBasedGauge64,
    adjMthdStat5XXRcvdRate                        CounterBasedGauge64,
    adjMthdStat5XXRcvdCount                       CounterBasedGauge64,
    adjMthdStat5XXSentRate                        CounterBasedGauge64,
    adjMthdStat5XXSentCount                       CounterBasedGauge64,
    adjMthdStat6XXRcvdRate                        CounterBasedGauge64,
    adjMthdStat6XXRcvdCount                       CounterBasedGauge64,
    adjMthdStat6XXSentRate                        CounterBasedGauge64,
    adjMthdStat6XXSentCount                       CounterBasedGauge64,
    adjMthdStatOtherRcvdRate                      CounterBasedGauge64,
    adjMthdStatOtherRcvdCount                     CounterBasedGauge64,
    adjMthdStatOtherSentRate                      CounterBasedGauge64,
    adjMthdStatOtherSentCount                     CounterBasedGauge64,
    adjMthdStatISARcvdRate                        CounterBasedGauge64,
    adjMthdStatISARcvdCount                       CounterBasedGauge64,
    adjMthdStatISARcvdPerc                        CounterBasedGauge64,
    adjMthdStatISASentRate                        CounterBasedGauge64,
    adjMthdStatISASentCount                       CounterBasedGauge64,
    adjMthdStatISASentPerc                        CounterBasedGauge64,
    adjMthdStatESERcvdRate                        CounterBasedGauge64,
    adjMthdStatESERcvdCount                       CounterBasedGauge64,
    adjMthdStatESESentRate                        CounterBasedGauge64,
    adjMthdStatESESentCount                       CounterBasedGauge64,
    adjMthdStatNon3xxRcvdCount                    CounterBasedGauge64,
    adjMthdStatNon3xxSentCount                    CounterBasedGauge64,
    adjMthdStatSERRcvdPerc                        CounterBasedGauge64,
    adjMthdStatSERSentPerc                        CounterBasedGauge64,
    adjMthdStatSEERRcvdPerc                       CounterBasedGauge64,
    adjMthdStatSEERSentPerc                       CounterBasedGauge64
  }

  adjMthdStatAdjacencyName OBJECT-TYPE
    SYNTAX      DisplayString (SIZE(1..32))
    MAX-ACCESS  not-accessible
    STATUS      current
    DESCRIPTION "The name of the adjacency. This an index field
                 for adjacency method statistics."
    ::= { perimetaAdjacencyMethodStatsEntry 1 }

  adjMthdStatSIPMethod OBJECT-TYPE
    SYNTAX       INTEGER {
                   unknown(1),
                   ack(2),
                   bye(3),
                   cancel(4),
                   info(5),
                   invite(6),
                   message(7),
                   notify(8),
                   options(9),
                   prack(10),
                   refer(11),
                   register(12),
                   subscribe(13),
                   update(14)
                 }
    MAX-ACCESS   not-accessible
    STATUS       current
    DESCRIPTION  "The SIP method that these statistics apply to.
                  This is an index field for adjacency method
                  statistics."
    ::= { perimetaAdjacencyMethodStatsEntry 2 }

  adjMthdStatSummaryPeriod OBJECT-TYPE
    SYNTAX       INTEGER {
                   summaryPeriod1CurrentClctnIntv(1)
                 }
    MAX-ACCESS   not-accessible
    STATUS       current
    DESCRIPTION  "The period over which the statistics were collected.
                  This is an index field."
    ::= { perimetaAdjacencyMethodStatsEntry 3 }

  adjMthdStatRequestsRcvdRate OBJECT-TYPE
    SYNTAX       CounterBasedGauge64
    MAX-ACCESS   read-only
    STATUS       current
    DESCRIPTION  "Requests with this SIP method received
                  by this adjacency (msgs/s)"
    ::= { perimetaAdjacencyMethodStatsEntry 5 }

  adjMthdStatRequestsRcvdCount OBJECT-TYPE
    SYNTAX       CounterBasedGauge64
    MAX-ACCESS   read-only
    STATUS       current
    DESCRIPTION  "Requests with this SIP method received
                  by this adjacency in the last collection
                  interval"
    ::= { perimetaAdjacencyMethodStatsEntry 6 }

  adjMthdStatRequestsSentRate OBJECT-TYPE
    SYNTAX       CounterBasedGauge64
    MAX-ACCESS   read-only
    STATUS       current
    DESCRIPTION  "Requests with this SIP method sent from
                  this adjacency (msgs/s)"
    ::= { perimetaAdjacencyMethodStatsEntry 8 }

  adjMthdStatRequestsSentCount OBJECT-TYPE
    SYNTAX       CounterBasedGauge64
    MAX-ACCESS   read-only
    STATUS       current
    DESCRIPTION  "Requests with this SIP method sent from
                  this adjacency in the last collection
                  period"
    ::= { perimetaAdjacencyMethodStatsEntry 9 }

  adjMthdStat1XXRcvdRate OBJECT-TYPE
    SYNTAX       CounterBasedGauge64
    MAX-ACCESS   read-only
    STATUS       current
    DESCRIPTION  "1XX responses to this SIP method
                  received by this adjacency (msgs/s)"
    ::= { perimetaAdjacencyMethodStatsEntry 11 }

  adjMthdStat1XXRcvdCount OBJECT-TYPE
    SYNTAX       CounterBasedGauge64
    MAX-ACCESS   read-only
    STATUS       current
    DESCRIPTION  "1XX responses to this SIP method
                  received by this adjacency in the last
                  collection period"
    ::= { perimetaAdjacencyMethodStatsEntry 12 }

  adjMthdStat1XXSentRate OBJECT-TYPE
    SYNTAX       CounterBasedGauge64
    MAX-ACCESS   read-only
    STATUS       current
    DESCRIPTION  "1XX responses to this SIP method sent
                  from this adjacency (msgs/s)"
    ::= { perimetaAdjacencyMethodStatsEntry 14 }

  adjMthdStat1XXSentCount OBJECT-TYPE
    SYNTAX       CounterBasedGauge64
    MAX-ACCESS   read-only
    STATUS       current
    DESCRIPTION  "1XX responses to this SIP method sent
                  from this adjacency in the last
                  collection period"
    ::= { perimetaAdjacencyMethodStatsEntry 15 }

  adjMthdStat2XXRcvdRate OBJECT-TYPE
    SYNTAX       CounterBasedGauge64
    MAX-ACCESS   read-only
    STATUS       current
    DESCRIPTION  "2XX responses to this SIP method
                  received by this adjacency (msgs/s)"
    ::= { perimetaAdjacencyMethodStatsEntry 17 }

  adjMthdStat2XXRcvdCount OBJECT-TYPE
    SYNTAX       CounterBasedGauge64
    MAX-ACCESS   read-only
    STATUS       current
    DESCRIPTION  "2XX responses to this SIP method
                  received by this adjacency in the last
                  collection period"
    ::= { perimetaAdjacencyMethodStatsEntry 18 }

  adjMthdStat2XXSentRate OBJECT-TYPE
    SYNTAX       CounterBasedGauge64
    MAX-ACCESS   read-only
    STATUS       current
    DESCRIPTION  "2XX responses to this SIP method sent
                  from this adjacency (msgs/s)"
    ::= { perimetaAdjacencyMethodStatsEntry 20 }

  adjMthdStat2XXSentCount OBJECT-TYPE
    SYNTAX       CounterBasedGauge64
    MAX-ACCESS   read-only
    STATUS       current
    DESCRIPTION  "2XX responses to this SIP method sent
                  from this adjacency in the last
                  collection period"
    ::= { perimetaAdjacencyMethodStatsEntry 21 }

  adjMthdStat3XXRcvdRate OBJECT-TYPE
    SYNTAX       CounterBasedGauge64
    MAX-ACCESS   read-only
    STATUS       current
    DESCRIPTION  "3XX responses to this SIP method
                  received by this adjacency (msgs/s)"
    ::= { perimetaAdjacencyMethodStatsEntry 23 }

  adjMthdStat3XXRcvdCount OBJECT-TYPE
    SYNTAX       CounterBasedGauge64
    MAX-ACCESS   read-only
    STATUS       current
    DESCRIPTION  "3XX responses to this SIP method
                  received by this adjacency in the last
                  collection period"
    ::= { perimetaAdjacencyMethodStatsEntry 24 }

  adjMthdStat3XXSentRate OBJECT-TYPE
    SYNTAX       CounterBasedGauge64
    MAX-ACCESS   read-only
    STATUS       current
    DESCRIPTION  "3XX responses to this SIP method sent
                  from this adjacency (msgs/s)"
    ::= { perimetaAdjacencyMethodStatsEntry 26 }

  adjMthdStat3XXSentCount OBJECT-TYPE
    SYNTAX       CounterBasedGauge64
    MAX-ACCESS   read-only
    STATUS       current
    DESCRIPTION  "3XX responses to this SIP method sent
                  from this adjacency in the last
                  collection period"
    ::= { perimetaAdjacencyMethodStatsEntry 27 }

  adjMthdStat4XXRcvdRate OBJECT-TYPE
    SYNTAX       CounterBasedGauge64
    MAX-ACCESS   read-only
    STATUS       current
    DESCRIPTION  "4XX responses to this SIP method
                  received by this adjacency (msgs/s)"
    ::= { perimetaAdjacencyMethodStatsEntry 29 }

  adjMthdStat4XXRcvdCount OBJECT-TYPE
    SYNTAX       CounterBasedGauge64
    MAX-ACCESS   read-only
    STATUS       current
    DESCRIPTION  "4XX responses to this SIP method
                  received by this adjacency in the last
                  collection period"
    ::= { perimetaAdjacencyMethodStatsEntry 30 }

  adjMthdStat4XXSentRate OBJECT-TYPE
    SYNTAX       CounterBasedGauge64
    MAX-ACCESS   read-only
    STATUS       current
    DESCRIPTION  "4XX responses to this SIP method sent
                  from this adjacency (msgs/s)"
    ::= { perimetaAdjacencyMethodStatsEntry 32 }

  adjMthdStat4XXSentCount OBJECT-TYPE
    SYNTAX       CounterBasedGauge64
    MAX-ACCESS   read-only
    STATUS       current
    DESCRIPTION  "4XX responses to this SIP method sent
                  from this adjacency in the last
                  collection period"
    ::= { perimetaAdjacencyMethodStatsEntry 33 }

  adjMthdStat5XXRcvdRate OBJECT-TYPE
    SYNTAX       CounterBasedGauge64
    MAX-ACCESS   read-only
    STATUS       current
    DESCRIPTION  "5XX responses to this SIP method
                  received by this adjacency (msgs/s)"
    ::= { perimetaAdjacencyMethodStatsEntry 35 }

  adjMthdStat5XXRcvdCount OBJECT-TYPE
    SYNTAX       CounterBasedGauge64
    MAX-ACCESS   read-only
    STATUS       current
    DESCRIPTION  "5XX responses to this SIP method
                  received by this adjacency in the last
                  collection period"
    ::= { perimetaAdjacencyMethodStatsEntry 36 }

  adjMthdStat5XXSentRate OBJECT-TYPE
    SYNTAX       CounterBasedGauge64
    MAX-ACCESS   read-only
    STATUS       current
    DESCRIPTION  "5XX responses to this SIP method sent
                  from this adjacency (msgs/s)"
    ::= { perimetaAdjacencyMethodStatsEntry 38 }

  adjMthdStat5XXSentCount OBJECT-TYPE
    SYNTAX       CounterBasedGauge64
    MAX-ACCESS   read-only
    STATUS       current
    DESCRIPTION  "5XX responses to this SIP method sent
                  from this adjacency in the last
                  collection period"
    ::= { perimetaAdjacencyMethodStatsEntry 39 }

  adjMthdStat6XXRcvdRate OBJECT-TYPE
    SYNTAX       CounterBasedGauge64
    MAX-ACCESS   read-only
    STATUS       current
    DESCRIPTION  "6XX responses to this SIP method
                  received by this adjacency (msgs/s)"
    ::= { perimetaAdjacencyMethodStatsEntry 41 }

  adjMthdStat6XXRcvdCount OBJECT-TYPE
    SYNTAX       CounterBasedGauge64
    MAX-ACCESS   read-only
    STATUS       current
    DESCRIPTION  "6XX responses to this SIP method
                  received by this adjacency in the last
                  collection period"
    ::= { perimetaAdjacencyMethodStatsEntry 42 }

  adjMthdStat6XXSentRate OBJECT-TYPE
    SYNTAX       CounterBasedGauge64
    MAX-ACCESS   read-only
    STATUS       current
    DESCRIPTION  "6XX responses to this SIP method sent
                  from this adjacency (msgs/s)"
    ::= { perimetaAdjacencyMethodStatsEntry 44 }

  adjMthdStat6XXSentCount OBJECT-TYPE
    SYNTAX       CounterBasedGauge64
    MAX-ACCESS   read-only
    STATUS       current
    DESCRIPTION  "6XX responses to this SIP method sent
                  from this adjacency in the last
                  collection period"
    ::= { perimetaAdjacencyMethodStatsEntry 45 }

  adjMthdStatOtherRcvdRate OBJECT-TYPE
    SYNTAX       CounterBasedGauge64
    MAX-ACCESS   read-only
    STATUS       current
    DESCRIPTION  "Other responses to this SIP method
                  received by this adjacency (msgs/s)"
    ::= { perimetaAdjacencyMethodStatsEntry 47 }

  adjMthdStatOtherRcvdCount OBJECT-TYPE
    SYNTAX       CounterBasedGauge64
    MAX-ACCESS   read-only
    STATUS       current
    DESCRIPTION  "Other responses to this SIP method
                  received by this adjacency in the last
                  collection period"
    ::= { perimetaAdjacencyMethodStatsEntry 48 }

  adjMthdStatOtherSentRate OBJECT-TYPE
    SYNTAX       CounterBasedGauge64
    MAX-ACCESS   read-only
    STATUS       current
    DESCRIPTION  "Other responses to this SIP method sent
                  from this adjacency (msgs/s)"
    ::= { perimetaAdjacencyMethodStatsEntry 50 }

  adjMthdStatOtherSentCount OBJECT-TYPE
    SYNTAX       CounterBasedGauge64
    MAX-ACCESS   read-only
    STATUS       current
    DESCRIPTION  "Other responses to this SIP method sent
                  from this adjacency in the last
                  collection period"
    ::= { perimetaAdjacencyMethodStatsEntry 51 }

  adjMthdStatISARcvdRate OBJECT-TYPE
    SYNTAX       CounterBasedGauge64
    MAX-ACCESS   read-only
    STATUS       current
    DESCRIPTION  "Ineffective session responses to this
                  SIP method received by this adjacency
                  (msgs/s)"
    ::= { perimetaAdjacencyMethodStatsEntry 53 }

  adjMthdStatISARcvdCount OBJECT-TYPE
    SYNTAX       CounterBasedGauge64
    MAX-ACCESS   read-only
    STATUS       current
    DESCRIPTION  "Ineffective session responses to this
                  SIP method received by this adjacency in
                  the last collection period"
    ::= { perimetaAdjacencyMethodStatsEntry 54 }

  adjMthdStatISARcvdPerc OBJECT-TYPE
    SYNTAX       CounterBasedGauge64
    MAX-ACCESS   read-only
    STATUS       current
    DESCRIPTION  "Percentage of ineffective session
                  responses to this SIP method received by
                  this adjacency in the last collection
                  period"
    ::= { perimetaAdjacencyMethodStatsEntry 55 }

  adjMthdStatISASentRate OBJECT-TYPE
    SYNTAX       CounterBasedGauge64
    MAX-ACCESS   read-only
    STATUS       current
    DESCRIPTION  "Ineffective session responses to this
                  SIP method sent from this adjacency
                  (msgs/s)"
    ::= { perimetaAdjacencyMethodStatsEntry 57 }

  adjMthdStatISASentCount OBJECT-TYPE
    SYNTAX       CounterBasedGauge64
    MAX-ACCESS   read-only
    STATUS       current
    DESCRIPTION  "Ineffective session responses to this
                  SIP method sent from this adjacency in
                  the last collection period"
    ::= { perimetaAdjacencyMethodStatsEntry 58 }

  adjMthdStatISASentPerc OBJECT-TYPE
    SYNTAX       CounterBasedGauge64
    MAX-ACCESS   read-only
    STATUS       current
    DESCRIPTION  "Percentage of ineffective session
                  responses to this SIP method sent from
                  this adjacency in the last collection
                  period"
    ::= { perimetaAdjacencyMethodStatsEntry 59 }

  adjMthdStatESERcvdRate OBJECT-TYPE
    SYNTAX       CounterBasedGauge64
    MAX-ACCESS   read-only
    STATUS       current
    DESCRIPTION  "Effective session establishment
                  responses to this SIP method received by
                  this adjacency (msgs/s)"
    ::= { perimetaAdjacencyMethodStatsEntry 61 }

  adjMthdStatESERcvdCount OBJECT-TYPE
    SYNTAX       CounterBasedGauge64
    MAX-ACCESS   read-only
    STATUS       current
    DESCRIPTION  "Effective session establishment
                  responses to this SIP method received by
                  this adjacency in the last collection
                  period"
    ::= { perimetaAdjacencyMethodStatsEntry 62 }

  adjMthdStatESESentRate OBJECT-TYPE
    SYNTAX       CounterBasedGauge64
    MAX-ACCESS   read-only
    STATUS       current
    DESCRIPTION  "Effective session establishment
                  responses to this SIP method sent from
                  this adjacency (msgs/s)"
    ::= { perimetaAdjacencyMethodStatsEntry 64 }

  adjMthdStatESESentCount OBJECT-TYPE
    SYNTAX       CounterBasedGauge64
    MAX-ACCESS   read-only
    STATUS       current
    DESCRIPTION  "Effective session establishment
                  responses to this SIP method sent from
                  this adjacency in the last collection
                  period"
    ::= { perimetaAdjacencyMethodStatsEntry 65 }

  adjMthdStatNon3xxRcvdCount OBJECT-TYPE
    SYNTAX       CounterBasedGauge64
    MAX-ACCESS   read-only
    STATUS       current
    DESCRIPTION  "Requests with this SIP method sent from
                  this adjacency less the number of 3XX
                  responses received by this adjacency in
                  the last collection period"
    ::= { perimetaAdjacencyMethodStatsEntry 66 }

  adjMthdStatNon3xxSentCount OBJECT-TYPE
    SYNTAX       CounterBasedGauge64
    MAX-ACCESS   read-only
    STATUS       current
    DESCRIPTION  "Requests with this SIP method received
                  by this adjacency less the number of 3XX
                  responses sent from this adjacency in
                  the last collection period"
    ::= { perimetaAdjacencyMethodStatsEntry 67 }

  adjMthdStatSERRcvdPerc OBJECT-TYPE
    SYNTAX       CounterBasedGauge64
    MAX-ACCESS   read-only
    STATUS       current
    DESCRIPTION  "Session Establishment Ratio for requests
                  using this method received by this
                  adjacency (in the last collection
                  period)"
    ::= { perimetaAdjacencyMethodStatsEntry 68 }

  adjMthdStatSERSentPerc OBJECT-TYPE
    SYNTAX       CounterBasedGauge64
    MAX-ACCESS   read-only
    STATUS       current
    DESCRIPTION  "Session Establishment Ratio for requests
                  using this method sent from this
                  adjacency (in the last collection
                  period)"
    ::= { perimetaAdjacencyMethodStatsEntry 69 }

  adjMthdStatSEERRcvdPerc OBJECT-TYPE
    SYNTAX       CounterBasedGauge64
    MAX-ACCESS   read-only
    STATUS       current
    DESCRIPTION  "Session Establishment Effectiveness
                  Ratio for this method received by this
                  adjacency (in the last collection
                  period)"
    ::= { perimetaAdjacencyMethodStatsEntry 70 }

  adjMthdStatSEERSentPerc OBJECT-TYPE
    SYNTAX       CounterBasedGauge64
    MAX-ACCESS   read-only
    STATUS       current
    DESCRIPTION  "Session Establishment Effectiveness
                  Ratio for this method sent from this
                  adjacency (in the last collection
                  period)"
    ::= { perimetaAdjacencyMethodStatsEntry 71 }

END
