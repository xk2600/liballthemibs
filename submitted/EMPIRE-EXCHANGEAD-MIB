-- <include>: "SNMPv2-SMI.my SNMPV2-TC.my SNMP2-CONF.my SNMP-FRAMEWORK-MIB.my INET-ADDRESS-MIB.my RFC-1212.my RFC1155-SMI.my" 
   --   ========================================================================
   -- 
   -- CA Technologies, Inc.
   -- Proprietary and Confidential Information
   -- 
   -- This material contains, and is part of a computer software program
   -- which is, proprietary and confidential information owned by CA Technologies,
   -- Inc.  The program, including this material, may not be duplicated, disclosed
   -- or reproduced in whole or in part for any purpose without the express
   -- written authorization of CA Technologies, Inc.  All authorized reproductions
   -- must be marked with this legend.
   --
   -- CA Technologies, Inc.    
   -- 
   -- Authors: Daniel R. Seligman, James A. Gordon, Heidi S. White
   --          CA Technologies
   --          273 Corporate Dr.
   --          Portsmouth, NH 03801
   -- 
   -- Copyright (c) 2012
   -- The Software that Manages eBusiness
   -- All rights reserved
   -- 
   -- 
   -- ------------------------------------------------------------------------
   -- MIB Name: exchangeAD-aim
   -- ------------------------------------------------------------------------
   -- Version: 1.1.1
   -- ------------------------------------------------------------------------
   -- This is the MIB for Active Directory/Exchange
   -- ------------------------------------------------------------------------
   --
   --
   -- ------------------------------------------------------------------------
   -- Note that, although the MODULE-COMPLIANCE construct is not employed in
   -- this MIB, not all objects must be supported for conformance.  It is
   -- expected that agents such as CA Technology's Active Directory/Exchange
   -- AIM may only support a functional subset of the objects.
   -- ------------------------------------------------------------------------


   EMPIRE-EXCHANGEAD-MIB DEFINITIONS ::= BEGIN

   IMPORTS

       InetAddressType,
       InetAddress
               FROM INET-ADDRESS-MIB

       SnmpAdminString
               FROM SNMP-FRAMEWORK-MIB

       MacAddress,
       RowStatus
               FROM SNMPv2-TC

       OBJECT-TYPE
                FROM RFC-1212

	   TRAP-TYPE
		        FROM RFC-1215

       Counter, 
       Gauge,
       enterprises, 
       TimeTicks 
              FROM RFC1155-SMI;

   -- ****************************************************************************
   -- OIDs of Exchange/AD agent start with 1.3.6.1.4.1.546.16.61
   -- ****************************************************************************


-- empireExchangeAdMIB MODULE-IDENTITY
--     LAST-UPDATED    "201210150000Z"
--     ORGANIZATION    "CA Technologies, Inc."
--     CONTACT-INFO
--             "CA Technologies, Inc.
--             273 Corporate Dr.
--             Portsmouth, NH 03801"
--     DESCRIPTION
--         "The MIB is used to manage Active Directory and Exchange."
-- 
--     REVISION        "201210150000Z"
--     DESCRIPTION
--         "Updated varbinds for several traps;  added exchAdDagFailOverTrap;  fixed some descriptions"
-- 
--     REVISION        "201206120000Z"
--     DESCRIPTION
--         "Made exchAdMailboxDatabaseInstInventoryIndex and exchAdMailboxDatabaseInvIndex obsolete"
-- 
--     REVISION        "201204240000Z"
--     DESCRIPTION
--         "DAG database copy table object name changes"
-- 
--     REVISION        "201204190000Z"
--     DESCRIPTION
--         "Corrected OID branch"
-- 
--     REVISION        "201204090000Z"
--     DESCRIPTION
--         "Multiple changes including removal of SNMPv2-SMI import & addition of IsOperationsMaster"
-- 
--     REVISION        "201203260000Z"
--     DESCRIPTION
--         "Ongoing changes towards MIB version 1.1"
-- 
--     REVISION        "201112190000Z"
--     DESCRIPTION
--         "MIB version 1.0"
-- 
--     REVISION        "201106290000Z"
--     DESCRIPTION
--         "commented out unused branches; fixed exchAdDomainTechnology"
-- 
--     REVISION        "201106170000Z"
--     DESCRIPTION
--         "Additional Compile errors addressed"
-- 
--     REVISION        "201106150000Z"
--     DESCRIPTION
--         "Reworked for SimpleWeb validation"
-- 
--     REVISION        "201105240000Z"
--     DESCRIPTION
--         "Traps added"
-- 
--     REVISION        "201105200000Z"
--     DESCRIPTION
--          "Initial Draft"
-- 
--     ::= { applications 61 }


   empire               OBJECT IDENTIFIER ::= { enterprises 546 }
   unix                 OBJECT IDENTIFIER ::= { empire 1 }
   sysmgmt              OBJECT IDENTIFIER ::= { unix 1 }

   applications         OBJECT IDENTIFIER ::= { empire 16 }
   empireExchangeAdMIB  OBJECT IDENTIFIER ::= { applications 61 }

-- ****************************************************************************
-- ****************************************************************************

   exchAdConfiguration                  OBJECT IDENTIFIER ::= { empireExchangeAdMIB 1 }
   exchAdInventory                      OBJECT IDENTIFIER ::= { empireExchangeAdMIB 2 }
   exchAdPerformance                    OBJECT IDENTIFIER ::= { empireExchangeAdMIB 3 }
   exchAdWindowsEvents                  OBJECT IDENTIFIER ::= { empireExchangeAdMIB 4 }
   exchAdDag                            OBJECT IDENTIFIER ::= { empireExchangeAdMIB 5 }
   exchAdSyntheticTests                 OBJECT IDENTIFIER ::= { empireExchangeAdMIB 6 }

-- { exchAdPerformance 1 } currently unused and available
   exchAdPerformanceHost                OBJECT IDENTIFIER ::= { exchAdPerformance 2 }
   exchAdPerformanceActiveDirectory     OBJECT IDENTIFIER ::= { exchAdPerformance 3 }
   exchAdPerformanceMailboxRole         OBJECT IDENTIFIER ::= { exchAdPerformance 4 }
   exchAdPerformanceHubTransportRole    OBJECT IDENTIFIER ::= { exchAdPerformance 5 }
   exchAdPerformanceClientAccessRole    OBJECT IDENTIFIER ::= { exchAdPerformance 6 }

   exchAdInventoryGen                   OBJECT IDENTIFIER ::= { exchAdInventory 1 }

--
-- Empty branches commented out but retained for future use
--
   exchAdInventoryMailboxRole           OBJECT IDENTIFIER ::= { exchAdInventory 4 }
   exchAdInventoryHubTransportRole      OBJECT IDENTIFIER ::= { exchAdInventory 5 }

--**************************************************************************
--
-- Configuration Parameters
--
--**************************************************************************

   exchAdPollInterval  OBJECT-TYPE
       SYNTAX       INTEGER
       ACCESS       read-write
       STATUS       mandatory
       DESCRIPTION "host poll interval in seconds - valid values are non-zero multiples of 30"
       DEFVAL   { 300 }
       ::= { exchAdConfiguration 1 }    

   exchAdWindowsEventTableSize  OBJECT-TYPE
       SYNTAX       INTEGER
       ACCESS       read-write
       STATUS       mandatory
       DESCRIPTION "configurable size of windows event table"
       DEFVAL   { 4000 }
       ::= { exchAdConfiguration 2 }  

   exchAdPollWindowsEvents  OBJECT-TYPE
       SYNTAX       INTEGER  {poll(1), doNotPoll(2)}
       ACCESS       read-write
       STATUS       mandatory
       DESCRIPTION "windows events poll switch"
       DEFVAL   { 1 }
       ::= { exchAdConfiguration 3 }

   exchAdEnableTraps  OBJECT-TYPE
       SYNTAX       INTEGER  {enable(1), disable(2)}
       ACCESS       read-write
       STATUS       mandatory
       DESCRIPTION "trap enable switch"
       DEFVAL   { 1 }
       ::= { exchAdConfiguration 4 }    

   exchAdInitiateDiscovery  OBJECT-TYPE
       SYNTAX       INTEGER
       ACCESS       read-write
       STATUS       mandatory
       DESCRIPTION "setting this object to the value 1 initiates discovery"
       ::= { exchAdConfiguration 5 }  

   exchAdWindowsEventCriticalityThreshold  OBJECT-TYPE
       SYNTAX       INTEGER  { information(1), warning(2), critical(3) }
       ACCESS       read-write
       STATUS       mandatory
       DESCRIPTION "threshold for retaining events in windows event table"
       DEFVAL   { 3 }
       ::= { exchAdConfiguration 6 }

--**************************************************************************  
--
-- Inventory Parameters
--
--**************************************************************************

   exchAdAgentName  OBJECT-TYPE
       SYNTAX       SnmpAdminString
       ACCESS       read-only
       STATUS       mandatory
       DESCRIPTION "name of the agent"
       ::= { exchAdInventoryGen 1 }

   exchAdAgentVersion  OBJECT-TYPE
       SYNTAX       SnmpAdminString
       ACCESS       read-only
       STATUS       mandatory
       DESCRIPTION "agent version"
       ::= { exchAdInventoryGen 2 }

   exchAdAgentStatus  OBJECT-TYPE
       SYNTAX       INTEGER {notReady(1), ready(2)}
       ACCESS       read-only
       STATUS       mandatory
       DESCRIPTION "agent status: not ready until AIM is fully initialized - this will revert to notReady when a discovery is initiated"
       ::= { exchAdInventoryGen 3 }

   exchAdSysUpTime  OBJECT-TYPE
       SYNTAX       TimeTicks
       ACCESS       read-only
       STATUS       mandatory
       DESCRIPTION 
            "time (in hundredths of a second) since the network management portion of the system was last re-initialized"
       ::= { exchAdInventoryGen 4 }

   exchAdLastDiscovery  OBJECT-TYPE
       SYNTAX       TimeTicks
       ACCESS       read-only
       STATUS       mandatory
       DESCRIPTION  "exchAdSysUpTime value at the completion of the last discovery"
       ::= { exchAdInventoryGen 5 }

   exchAdInventoryLastChange  OBJECT-TYPE
       SYNTAX       TimeTicks
       ACCESS       read-only
       STATUS       mandatory
       DESCRIPTION  "exchAdSysUpTime value at the completion of the last discovery or at the last change of the exchAdForestTableLastChange, exchAdDomainTableLastChange or exchAdManagedHostTableLastChange objects"
       ::= { exchAdInventoryGen 6 }

   exchAdHostName  OBJECT-TYPE
       SYNTAX       SnmpAdminString
       ACCESS       read-only
       STATUS       mandatory
       DESCRIPTION "name of the machine hosting the sysEDGE agent and AD/Ex AIM"
       ::= { exchAdInventoryGen 7 }

--**************************************************************************  
--
-- exchAdForestTable
--
--**************************************************************************

   exchAdForestTableSize  OBJECT-TYPE
       SYNTAX       INTEGER
       ACCESS       read-only
       STATUS       mandatory
       DESCRIPTION  "number of entries in exchAdForestTable"
       ::= { exchAdInventoryGen 8 }

   exchAdForestTableLastChange  OBJECT-TYPE
       SYNTAX       TimeTicks
       ACCESS       read-only
       STATUS       mandatory
       DESCRIPTION  "exchAdSysUpTime value at last change"
       ::= { exchAdInventoryGen 9 }

   exchAdForestTable OBJECT-TYPE
       SYNTAX      SEQUENCE OF ExchAdForestEntry
       ACCESS      not-accessible
       STATUS      mandatory
       DESCRIPTION
           "Forest table"
      ::= { exchAdInventoryGen 10 }

   exchAdForestEntry OBJECT-TYPE
       SYNTAX      ExchAdForestEntry
       ACCESS      not-accessible
       STATUS      mandatory
       DESCRIPTION
           "defines an entry in the exchAdForestTable"

       INDEX {
                exchAdForestIndex
             }
       ::= { exchAdForestTable 1 }

   ExchAdForestEntry ::=
       SEQUENCE {
           exchAdForestIndex               INTEGER,
           exchAdForestName                SnmpAdminString,
           exchAdForestNamingRoleOwner     SnmpAdminString,
           exchAdForestSchemaRoleOwner     SnmpAdminString,
           exchAdForestRootDomain          SnmpAdminString
       }

   exchAdForestIndex OBJECT-TYPE
       SYNTAX      INTEGER (0..2147483647)
       ACCESS      read-only
       STATUS      mandatory
       DESCRIPTION "unique index for each Forest"
       ::= { exchAdForestEntry 1 }

   exchAdForestName OBJECT-TYPE
       SYNTAX     SnmpAdminString
       ACCESS      read-only
       STATUS      mandatory
       DESCRIPTION "name of Forest"
       ::= { exchAdForestEntry 2 }

   exchAdForestNamingRoleOwner OBJECT-TYPE
       SYNTAX     SnmpAdminString
       ACCESS      read-only
       STATUS      mandatory
       DESCRIPTION "name of domain controller which is the naming master of this forest"
       ::= { exchAdForestEntry 3 }

   exchAdForestSchemaRoleOwner OBJECT-TYPE
       SYNTAX     SnmpAdminString
       ACCESS      read-only
       STATUS      mandatory
       DESCRIPTION "name of domain controller which is the schema master of this forest"
       ::= { exchAdForestEntry 4 }

   exchAdForestRootDomain OBJECT-TYPE
       SYNTAX     SnmpAdminString
       ACCESS      read-only
       STATUS      mandatory
       DESCRIPTION "name of root domain of this Forest"
       ::= { exchAdForestEntry 5 }

--**************************************************************************  
--
-- exchAdDomainTable
--
--**************************************************************************

   exchAdDomainTableSize  OBJECT-TYPE
       SYNTAX       INTEGER
       ACCESS       read-only
       STATUS       mandatory
       DESCRIPTION  "number of entries in exchAdDomainTable"
       ::= { exchAdInventoryGen 11 }

   exchAdDomainTableLastChange  OBJECT-TYPE
       SYNTAX       TimeTicks
       ACCESS       read-only
       STATUS       mandatory
       DESCRIPTION  "exchAdSysUpTime value at last change"
       ::= { exchAdInventoryGen 12 }

   exchAdDomainTable OBJECT-TYPE
       SYNTAX      SEQUENCE OF ExchAdDomainEntry
       ACCESS      not-accessible
       STATUS      mandatory
       DESCRIPTION
           "Domain table"
      ::= { exchAdInventoryGen 13 }

   exchAdDomainEntry OBJECT-TYPE
       SYNTAX      ExchAdDomainEntry
       ACCESS      not-accessible
       STATUS      mandatory
       DESCRIPTION
           "defines an entry in the exchAdDomainTable"

       INDEX {
                exchAdDomainIndex
             }
       ::= { exchAdDomainTable 1 }

   ExchAdDomainEntry ::=
       SEQUENCE {
           exchAdDomainIndex                  INTEGER,
           exchAdDomainName                   SnmpAdminString,
           exchAdDomainMgmtMode               INTEGER, 
           exchAdDomainTechnology             INTEGER, 
           exchAdDomainForestIndex            INTEGER,
           exchAdDomainDomainControllerIndex  INTEGER,
           exchAdDomainParentDomainIndex      INTEGER,
           exchAdDomainParentDomainName       SnmpAdminString,
           exchAdDomainInfrastructureMaster   SnmpAdminString,
           exchAdDomainPrimaryDCEmulator      SnmpAdminString,
           exchAdDomainRelativeIDMaster       SnmpAdminString
       }

   exchAdDomainIndex OBJECT-TYPE
       SYNTAX      INTEGER (0..2147483647)
       ACCESS      read-only
       STATUS      mandatory
       DESCRIPTION "unique index for each Domain"
       ::= { exchAdDomainEntry 1 }

   exchAdDomainName OBJECT-TYPE
       SYNTAX     SnmpAdminString
       ACCESS      read-only
       STATUS      mandatory
       DESCRIPTION "name of Domain"
       ::= { exchAdDomainEntry 2 }

   exchAdDomainMgmtMode OBJECT-TYPE
       SYNTAX     INTEGER {domainBased(1), hostBased(2)}
       ACCESS      read-only
       STATUS      mandatory
       DESCRIPTION "management mode of Domain"
       ::= { exchAdDomainEntry 3 }

   exchAdDomainTechnology OBJECT-TYPE
       SYNTAX     INTEGER {adAndEx(1), adOnly(2), exOnly(3)}
       ACCESS      read-only
       STATUS      mandatory
       DESCRIPTION "domain supported technology"
       ::= { exchAdDomainEntry 4 }

   exchAdDomainForestIndex OBJECT-TYPE
       SYNTAX      INTEGER
       ACCESS      read-only
       STATUS      mandatory
       DESCRIPTION "pointer to forest in exchAdForestTable"
       ::= { exchAdDomainEntry 5 }

   exchAdDomainDomainControllerIndex OBJECT-TYPE
       SYNTAX      INTEGER
       ACCESS      read-only
       STATUS      obsolete
       DESCRIPTION "pointer to domain controller in exchAdDomainControllerTable - this object is obsolete"
       ::= { exchAdDomainEntry 6 }

   exchAdDomainParentDomainIndex OBJECT-TYPE
       SYNTAX      INTEGER
       ACCESS      read-only
       STATUS      mandatory
       DESCRIPTION "pointer to parent Domain in this exchAdDomainTable - 0 if no parent"
       ::= { exchAdDomainEntry 7 }

   exchAdDomainParentDomainName OBJECT-TYPE
       SYNTAX     SnmpAdminString
       ACCESS      read-only
       STATUS      mandatory
       DESCRIPTION "parent Domain name"
       ::= { exchAdDomainEntry 8 }

   exchAdDomainInfrastructureMaster OBJECT-TYPE
       SYNTAX     SnmpAdminString
       ACCESS      read-only
       STATUS      mandatory
       DESCRIPTION "infrastructure master name of Domain"
       ::= { exchAdDomainEntry 9 }

   exchAdDomainPrimaryDCEmulator OBJECT-TYPE
       SYNTAX     SnmpAdminString
       ACCESS      read-only
       STATUS      mandatory
       DESCRIPTION "primary domain controller emulator name of Domain"
       ::= { exchAdDomainEntry 10 }

   exchAdDomainRelativeIDMaster OBJECT-TYPE
       SYNTAX     SnmpAdminString
       ACCESS      read-only
       STATUS      mandatory
       DESCRIPTION "relative ID master name of Domain"
       ::= { exchAdDomainEntry 11 }

--**************************************************************************  
--
-- exchAdUniversalHostTable
--
--**************************************************************************

   exchAdUniversalHostTableSize  OBJECT-TYPE
       SYNTAX       INTEGER
       ACCESS       read-only
       STATUS       mandatory
       DESCRIPTION  "number of entries in exchAdUniversalHostTable"
       ::= { exchAdInventoryGen 14 }

   exchAdUniversalHostTableLastChange  OBJECT-TYPE
       SYNTAX       TimeTicks
       ACCESS       read-only
       STATUS       mandatory
       DESCRIPTION  "exchAdSysUpTime value at last change"
       ::= { exchAdInventoryGen 15 }

   exchAdUniversalHostTable OBJECT-TYPE
       SYNTAX      SEQUENCE OF ExchAdUniversalHostEntry
       ACCESS      not-accessible
       STATUS      mandatory
       DESCRIPTION
           "table of hosts managed by all AIMs"
      ::= { exchAdInventoryGen 16 }

   exchAdUniversalHostEntry OBJECT-TYPE
       SYNTAX      ExchAdUniversalHostEntry
       ACCESS      not-accessible
       STATUS      mandatory
       DESCRIPTION
           "defines an entry in the exchAdUniversalHostTable"

       INDEX {
                exchAdUniversalHostIndex
             }
       ::= { exchAdUniversalHostTable 1 }

   ExchAdUniversalHostEntry ::=
       SEQUENCE {
           exchAdUniversalHostIndex          INTEGER,
           exchAdUniversalHostName           SnmpAdminString,
           exchAdUniversalHostTechnology     INTEGER,
           exchAdUniversalHostExRoleMask     INTEGER,
           exchAdUniversalHostAdRoleMask     INTEGER,
           exchAdUniversalHostManagedByAgent INTEGER,
           exchAdUniversalHostIpAddressType  InetAddressType,
           exchAdUniversalHostIpAddress      InetAddress,
           exchAdUniversalHostMacAddress     MacAddress,
           exchAdUniversalHostDomainName     SnmpAdminString,
           exchAdUniversalHostForestName     SnmpAdminString
       }

   exchAdUniversalHostIndex OBJECT-TYPE
          SYNTAX      INTEGER (0..2147483647)
          ACCESS      read-only
          STATUS      mandatory
          DESCRIPTION "unique index for each host"
          ::= { exchAdUniversalHostEntry 1 }

   exchAdUniversalHostName OBJECT-TYPE
          SYNTAX      SnmpAdminString
          ACCESS      read-only
          STATUS      mandatory
          DESCRIPTION "name of host"
          ::= { exchAdUniversalHostEntry 2 }

   exchAdUniversalHostTechnology OBJECT-TYPE
          SYNTAX      INTEGER {exchange(1), activeDirectory(2), both(3)}
          ACCESS      read-only
          STATUS      mandatory
          DESCRIPTION "host supported technology"
          ::= { exchAdUniversalHostEntry 3 }

   exchAdUniversalHostExRoleMask OBJECT-TYPE
          SYNTAX      INTEGER
          ACCESS      read-only
          STATUS      mandatory
          DESCRIPTION
            "This object is a bit field. Each bit represents the following Exchange roles:
            Hex: 0000 0001, Decimal:  1 - Edge Transport
            Hex: 0000 0002, Decimal:  2 - Hub Transport
            Hex: 0000 0004, Decimal:  4 - Client Access
            Hex: 0000 0008, Decimal:  8 - Mailbox
            Hex: 0000 0010, Decimal: 16 - Unified Messaging"
          ::= { exchAdUniversalHostEntry 4 }

   exchAdUniversalHostAdRoleMask OBJECT-TYPE
          SYNTAX      INTEGER
          ACCESS      read-only
          STATUS      mandatory
          DESCRIPTION
            "This object is a bit field. Each bit represents the following Active Directory roles:
            Hex: 0000 0001, Decimal:  1 - Domain Services
            Hex: 0000 0002, Decimal:  2 - ADAM
            Hex: 0000 0004, Decimal:  4 - Federation Services
            Hex: 0000 0008, Decimal:  8 - Rights Management Services
            Hex: 0000 0010, Decimal: 16 - Certification Server"
          ::= { exchAdUniversalHostEntry 5 }

   exchAdUniversalHostManagedByAgent OBJECT-TYPE
          SYNTAX      INTEGER {manage(1), doNotManage(2)}
          ACCESS      read-write
          STATUS      mandatory
          DESCRIPTION 
                      "host management flag:  Initialized to 1 if associated domain management mode is Domain-Based; 2 otherwise"
          ::= { exchAdUniversalHostEntry 6 }

   exchAdUniversalHostIpAddressType OBJECT-TYPE
          SYNTAX      InetAddressType
          ACCESS      read-only
          STATUS      mandatory
          DESCRIPTION "host IP address type"
          ::= { exchAdUniversalHostEntry 7 }

   exchAdUniversalHostIpAddress OBJECT-TYPE
          SYNTAX      InetAddress
          ACCESS      read-only
          STATUS      mandatory
          DESCRIPTION "host IP address"
          ::= { exchAdUniversalHostEntry 8 }

   exchAdUniversalHostMacAddress OBJECT-TYPE
          SYNTAX      MacAddress
          ACCESS      read-only
          STATUS      mandatory
          DESCRIPTION "host MAC address"
          ::= { exchAdUniversalHostEntry 9 }

   exchAdUniversalHostDomainName OBJECT-TYPE
          SYNTAX      SnmpAdminString
          ACCESS      read-only
          STATUS      mandatory
          DESCRIPTION "associated domain name"
          ::= { exchAdUniversalHostEntry 10 }

   exchAdUniversalHostForestName OBJECT-TYPE
          SYNTAX      SnmpAdminString
          ACCESS      read-only
          STATUS      mandatory
          DESCRIPTION "associated Forest name"
          ::= { exchAdUniversalHostEntry 11 }

--**************************************************************************  
--
-- exchAdManagedHostTable
--
--**************************************************************************

   exchAdManagedHostTableSize  OBJECT-TYPE
       SYNTAX       INTEGER
       ACCESS       read-only
       STATUS       mandatory
       DESCRIPTION  "number of entries in exchAdManagedHostTable"
       ::= { exchAdInventoryGen 17 }

   exchAdManagedHostTableLastChange  OBJECT-TYPE
       SYNTAX       TimeTicks
       ACCESS       read-only
       STATUS       mandatory
       DESCRIPTION  "exchAdSysUpTime value at last change"
       ::= { exchAdInventoryGen 18 }

   exchAdManagedHostTable OBJECT-TYPE
       SYNTAX      SEQUENCE OF ExchAdManagedHostEntry
       ACCESS      not-accessible
       STATUS      mandatory
       DESCRIPTION
           "table of hosts managed by this AIM"
      ::= { exchAdInventoryGen 19 }

   exchAdManagedHostEntry OBJECT-TYPE
       SYNTAX      ExchAdManagedHostEntry
       ACCESS      not-accessible
       STATUS      mandatory
       DESCRIPTION
           "defines an entry in the exchAdManagedHostTable"

       INDEX {
                exchAdManagedHostIndex
             }
       ::= { exchAdManagedHostTable 1 }

   ExchAdManagedHostEntry ::=
       SEQUENCE {
           exchAdManagedHostIndex               INTEGER,
           exchAdManagedHostName                SnmpAdminString,
           exchAdManagedHostTechnology          INTEGER,
           exchAdManagedHostExRoleMask          INTEGER,
           exchAdManagedHostAdRoleMask          INTEGER,
           exchAdManagedHostDagIndex            INTEGER,
           exchAdManagedHostIpAddressType       InetAddressType,
           exchAdManagedHostIpAddress           InetAddress,
           exchAdManagedHostMacAddress          MacAddress,
           exchAdManagedHostLastPollTime        TimeTicks,
           exchAdManagedHostPollStatus          INTEGER,
           exchAdManagedHostPreviousPollStatus  INTEGER,
           exchAdManagedHostDomainIndex         INTEGER,
           exchAdManagedHostForestIndex         INTEGER
       }

   exchAdManagedHostIndex OBJECT-TYPE
          SYNTAX      INTEGER (0..2147483647)
          ACCESS      read-only
          STATUS      mandatory
          DESCRIPTION 
             "unique index for each host, same as exchAdUniversalHostIndex"
          ::= { exchAdManagedHostEntry 1 }

   exchAdManagedHostName OBJECT-TYPE
          SYNTAX      SnmpAdminString
          ACCESS      read-only
          STATUS      mandatory
          DESCRIPTION "name of host"
          ::= { exchAdManagedHostEntry 2 }

   exchAdManagedHostTechnology OBJECT-TYPE
          SYNTAX      INTEGER {exchange(1), activeDirectory(2), both(3)}
          ACCESS      read-only
          STATUS      mandatory
          DESCRIPTION "host supported technology"
          ::= { exchAdManagedHostEntry 3 }

   exchAdManagedHostExRoleMask OBJECT-TYPE
          SYNTAX      INTEGER
          ACCESS      read-only
          STATUS      mandatory
          DESCRIPTION
            "This object is a bit field. Each bit represents the following Exchange roles:
            Hex: 0000 0001, Decimal:  1 - Edge Transport
            Hex: 0000 0002, Decimal:  2 - Hub Transport
            Hex: 0000 0004, Decimal:  4 - Client Access
            Hex: 0000 0008, Decimal:  8 - Mailbox
            Hex: 0000 0010, Decimal: 16 - Unified Messaging"
          ::= { exchAdManagedHostEntry 4 }

   exchAdManagedHostAdRoleMask OBJECT-TYPE
          SYNTAX      INTEGER
          ACCESS      read-only
          STATUS      mandatory
          DESCRIPTION
            "This object is a bit field. Each bit represents the following Active Directory roles:
            Hex: 0000 0001, Decimal:  1 - Domain Services
            Hex: 0000 0002, Decimal:  2 - ADAM
            Hex: 0000 0004, Decimal:  4 - Federation Services
            Hex: 0000 0008, Decimal:  8 - Rights Management Services
            Hex: 0000 0010, Decimal: 16 - Certification Server"
          ::= { exchAdManagedHostEntry 5 }

   exchAdManagedHostDagIndex OBJECT-TYPE
          SYNTAX      INTEGER
          ACCESS      read-only
          STATUS      mandatory
          DESCRIPTION 
            "pointer to DAG in exchAdDagTable - 0 if not in a DAG"
          ::= { exchAdManagedHostEntry 6 }

   exchAdManagedHostIpAddressType OBJECT-TYPE
          SYNTAX      InetAddressType
          ACCESS      read-only
          STATUS      mandatory
          DESCRIPTION "host IP address type"
          ::= { exchAdManagedHostEntry 7 }

   exchAdManagedHostIpAddress OBJECT-TYPE
          SYNTAX      InetAddress
          ACCESS      read-only
          STATUS      mandatory
          DESCRIPTION "host IP address"
          ::= { exchAdManagedHostEntry 8 }

   exchAdManagedHostMacAddress OBJECT-TYPE
          SYNTAX      MacAddress
          ACCESS      read-only
          STATUS      mandatory
          DESCRIPTION "host MAC address"
          ::= { exchAdManagedHostEntry 9 }

   exchAdManagedHostLastPollTime OBJECT-TYPE
          SYNTAX      TimeTicks
          ACCESS      read-only
          STATUS      mandatory
          DESCRIPTION "exchAdSysUpTime value at last successful poll"
          ::= { exchAdManagedHostEntry 10 }

   exchAdManagedHostPollStatus OBJECT-TYPE
          SYNTAX      INTEGER {initial(1), established(2), failed(3)}
          ACCESS      read-only
          STATUS      mandatory
          DESCRIPTION "status of AIM's ability to successfully communicate with the host on its most recent poll"
          ::= { exchAdManagedHostEntry 11 }

   exchAdManagedHostPreviousPollStatus OBJECT-TYPE
          SYNTAX      INTEGER {initial(1), established(2), failed(3)}
          ACCESS      read-only
          STATUS      mandatory
          DESCRIPTION "value of exchAdManagedHostPollStatus from the previous poll"
          ::= { exchAdManagedHostEntry 12 }

   exchAdManagedHostDomainIndex OBJECT-TYPE
          SYNTAX      INTEGER
          ACCESS      read-only
          STATUS      mandatory
          DESCRIPTION "pointer to domain in exchAdDomainTable"
          ::= { exchAdManagedHostEntry 13 }

   exchAdManagedHostForestIndex OBJECT-TYPE
          SYNTAX      INTEGER
          ACCESS      read-only
          STATUS      mandatory
          DESCRIPTION "pointer to forest in exchAdForestTable"
          ::= { exchAdManagedHostEntry 14 }

--**************************************************************************  
--
-- exchAdDomainControllerTable
--
-- This table's implementation was changed from version 1.0 to version 1.1. The
-- 1.0 version of this MIB was never implemented by the ADES AIM agent.
--
--**************************************************************************

   exchAdDomainControllerTable OBJECT-TYPE
       SYNTAX      SEQUENCE OF ExchAdDomainControllerEntry
       ACCESS      not-accessible
       STATUS      mandatory
       DESCRIPTION
           "Domain Controller table"
      ::= { exchAdInventoryGen 20 }

   exchAdDomainControllerEntry OBJECT-TYPE
       SYNTAX      ExchAdDomainControllerEntry
       ACCESS      not-accessible
       STATUS      mandatory
       DESCRIPTION
           "defines an entry in the exchAdDomainControllerTable"

       INDEX {
                exchAdDomainControllerIndex
             }
       ::= { exchAdDomainControllerTable 1 }

   ExchAdDomainControllerEntry ::=
       SEQUENCE {
           exchAdDomainControllerIndex               INTEGER,
           exchAdDomainControllerName                SnmpAdminString,
           exchAdDomainControllerFqdn                SnmpAdminString,
           exchAdDomainControllerHostIndex           INTEGER,
           exchAdDomainControllerDomainIndex         INTEGER,
           exchAdDomainControllerIsReadOnly          INTEGER,
           exchAdDomainControllerSiteName            SnmpAdminString,
           exchAdDomainControllerIsOperationsMaster  INTEGER
       }

   exchAdDomainControllerIndex OBJECT-TYPE
       SYNTAX      INTEGER (0..2147483647)
       ACCESS      read-only
       STATUS      mandatory
       DESCRIPTION "unique index for each Domain Controller, same as exchAdUniversalHostIndex"
       ::= { exchAdDomainControllerEntry 1 }

   exchAdDomainControllerName OBJECT-TYPE
       SYNTAX     SnmpAdminString
       ACCESS      read-only
       STATUS      mandatory
       DESCRIPTION "name of Domain Controller"
       ::= { exchAdDomainControllerEntry 2 }

   exchAdDomainControllerFqdn OBJECT-TYPE
       SYNTAX     SnmpAdminString
       ACCESS      read-only
       STATUS      mandatory
       DESCRIPTION "fully qualified domain name (FQDN) of the Domain Controller"
       ::= { exchAdDomainControllerEntry 3 } 

   exchAdDomainControllerHostIndex OBJECT-TYPE
         SYNTAX      INTEGER
         ACCESS      read-only
         STATUS      obsolete
         DESCRIPTION "pointer to host in exchAdUniversalHostTable - this object is obsolete"
        ::= { exchAdDomainControllerEntry 4 }           

   exchAdDomainControllerDomainIndex OBJECT-TYPE
       SYNTAX      INTEGER
       ACCESS      read-only
       STATUS      mandatory
       DESCRIPTION "pointer to domain in exchAdDomainTable"
       ::= { exchAdDomainControllerEntry 5 }

   exchAdDomainControllerIsReadOnly OBJECT-TYPE
       SYNTAX      INTEGER { true(1), false(2)}
       ACCESS      read-only
       STATUS      mandatory
       DESCRIPTION "specifies whether the Domain Controller is read-only or not"
       ::= { exchAdDomainControllerEntry 6 }

   exchAdDomainControllerSiteName OBJECT-TYPE
       SYNTAX     SnmpAdminString
       ACCESS      read-only
       STATUS      mandatory
       DESCRIPTION "site name of the Domain Controller"
       ::= { exchAdDomainControllerEntry 7 } 

   exchAdDomainControllerIsOperationsMaster OBJECT-TYPE
       SYNTAX      INTEGER { true(1), false(2)}
       ACCESS      read-only
       STATUS      mandatory
       DESCRIPTION "specifies whether the Domain Controller is an operations master or not"
       ::= { exchAdDomainControllerEntry 8 }

--**************************************************************************  
--
-- exchAdGlobalCatalogTable
--
-- This table's implementation was changed from version 1.0 to version 1.1. The
-- 1.0 version of this MIB was never implemented by the ADES AIM agent.
--
--**************************************************************************

   exchAdGlobalCatalogTable OBJECT-TYPE
       SYNTAX      SEQUENCE OF ExchAdGlobalCatalogEntry
       ACCESS      not-accessible
       STATUS      mandatory
       DESCRIPTION
           "Global Catalog table"
      ::= { exchAdInventoryGen 21 }

   exchAdGlobalCatalogEntry OBJECT-TYPE
       SYNTAX      ExchAdGlobalCatalogEntry
       ACCESS      not-accessible
       STATUS      mandatory
       DESCRIPTION
           "defines an entry in the exchAdGlobalCatalogTable"

       INDEX {
                exchAdGlobalCatalogIndex
             }
       ::= { exchAdGlobalCatalogTable 1 }

   ExchAdGlobalCatalogEntry ::=
       SEQUENCE {
           exchAdGlobalCatalogIndex               INTEGER,
           exchAdGlobalCatalogName                SnmpAdminString,
           exchAdGlobalCataloglDmnCntrlrIndex     INTEGER
       }

   exchAdGlobalCatalogIndex OBJECT-TYPE
       SYNTAX      INTEGER (0..2147483647)
       ACCESS      read-only
       STATUS      mandatory
       DESCRIPTION "unique index for each Global Catalog, same as exchAdUniversalHostIndex"
       ::= { exchAdGlobalCatalogEntry 1 }

   exchAdGlobalCatalogName OBJECT-TYPE
       SYNTAX     SnmpAdminString
       ACCESS      read-only
       STATUS      mandatory
       DESCRIPTION "name of Global Catalog"
       ::= { exchAdGlobalCatalogEntry 2 }

   exchAdGlobalCataloglDmnCntrlrIndex OBJECT-TYPE
         SYNTAX      INTEGER
         ACCESS      read-only
         STATUS      obsolete
         DESCRIPTION "pointer to Domain Controller in exchAdDomainControllerTable - this object is obsolete"
        ::= { exchAdGlobalCatalogEntry 3 } 

--**************************************************************************  
--
-- exchAdDomainControllerReplicTable
--
-- This table's implementation was changed from version 1.0 to version 1.1. The
-- 1.0 version of this MIB was never implemented by the ADES AIM agent.
--
--**************************************************************************

   exchAdDomainControllerReplicTable OBJECT-TYPE
       SYNTAX      SEQUENCE OF ExchAdDomainControllerReplicEntry
       ACCESS      not-accessible
       STATUS      mandatory
       DESCRIPTION
           "Domain Controller replication table"
      ::= { exchAdInventoryGen 22 }

   exchAdDomainControllerReplicEntry OBJECT-TYPE
       SYNTAX      ExchAdDomainControllerReplicEntry
       ACCESS      not-accessible
       STATUS      mandatory
       DESCRIPTION
           "defines an entry in the exchAdDomainControllerReplicTable"

       INDEX {
                exchAdDomainControllerReplicDomainControllerIndex,
                exchAdDomainControllerReplicReplicIndex
             }
       ::= { exchAdDomainControllerReplicTable 1 }

   ExchAdDomainControllerReplicEntry ::=
       SEQUENCE {
           exchAdDomainControllerReplicDomainControllerIndex            INTEGER,
           exchAdDomainControllerReplicReplicIndex                      INTEGER,
           exchAdDomainControllerReplicSourceSvr                        SnmpAdminString,
           exchAdDomainControllerReplicDestinationSvr                   SnmpAdminString,
           exchAdDomainControllerReplicNeighborPartitionName            SnmpAdminString,
           exchAdDomainControllerReplicLastAttempt                      SnmpAdminString,
           exchAdDomainControllerReplicLastSuccessfulCycle              SnmpAdminString,
           exchAdDomainControllerReplicLastSyncMsg                      SnmpAdminString,
           exchAdDomainControllerReplicLastSyncResult                   INTEGER,
           exchAdDomainControllerReplicFailuresSinceLastSucessfulCycle  INTEGER
       }

   exchAdDomainControllerReplicDomainControllerIndex OBJECT-TYPE
       SYNTAX      INTEGER (0..2147483647)
       ACCESS      read-only
       STATUS      mandatory
       DESCRIPTION "unique index for each Domain Controller, same as exchAdUniversalHostIndex"
       ::= { exchAdDomainControllerReplicEntry 1 }

   exchAdDomainControllerReplicReplicIndex OBJECT-TYPE
       SYNTAX      INTEGER (0..2147483647)
       ACCESS      read-only
       STATUS      mandatory
       DESCRIPTION "unique index for each Replication within a Domain Controller"
       ::= { exchAdDomainControllerReplicEntry 2 }

   exchAdDomainControllerReplicSourceSvr OBJECT-TYPE
       SYNTAX      SnmpAdminString
       ACCESS      read-only
       STATUS      mandatory
       DESCRIPTION "name of the source server"
       ::= { exchAdDomainControllerReplicEntry 3 }

   exchAdDomainControllerReplicDestinationSvr OBJECT-TYPE
       SYNTAX      SnmpAdminString
       ACCESS      read-only
       STATUS      mandatory
       DESCRIPTION "name of the destination server"
       ::= { exchAdDomainControllerReplicEntry 4 }

   exchAdDomainControllerReplicNeighborPartitionName OBJECT-TYPE
       SYNTAX      SnmpAdminString
       ACCESS      read-only
       STATUS      mandatory
       DESCRIPTION "name of the replication neighbor partition"
       ::= { exchAdDomainControllerReplicEntry 5 }

   exchAdDomainControllerReplicLastAttempt OBJECT-TYPE
       SYNTAX      SnmpAdminString
       ACCESS      read-only
       STATUS      mandatory
       DESCRIPTION "time of the last replication attempt"
       ::= { exchAdDomainControllerReplicEntry 6 }

   exchAdDomainControllerReplicLastSuccessfulCycle OBJECT-TYPE
       SYNTAX      SnmpAdminString
       ACCESS      read-only
       STATUS      mandatory
       DESCRIPTION "the last successful replication cycle"
       ::= { exchAdDomainControllerReplicEntry 7 }

   exchAdDomainControllerReplicLastSyncMsg OBJECT-TYPE
       SYNTAX      SnmpAdminString
       ACCESS      read-only
       STATUS      mandatory
       DESCRIPTION "the last synchronization message"
       ::= { exchAdDomainControllerReplicEntry 8 }

   exchAdDomainControllerReplicLastSyncResult OBJECT-TYPE
       SYNTAX      INTEGER (0..2147483647)
       ACCESS      read-only
       STATUS      mandatory
       DESCRIPTION "the last synchronization result (0 = success, otherwise failure)"
       ::= { exchAdDomainControllerReplicEntry 9 }

   exchAdDomainControllerReplicFailuresSinceLastSucessfulCycle OBJECT-TYPE
       SYNTAX      INTEGER (0..2147483647)
       ACCESS      read-only
       STATUS      mandatory
       DESCRIPTION "number of replication failures since last successful replication cycle"
       ::= { exchAdDomainControllerReplicEntry 10 }

--**************************************************************************  
--
-- exchAdDomainControllerSiteLinkTable
--
-- This table was not in version 1.0.
--
--**************************************************************************

   exchAdDomainControllerSiteLinkTable OBJECT-TYPE
       SYNTAX      SEQUENCE OF ExchAdDomainControllerSiteLinkEntry
       ACCESS      not-accessible
       STATUS      mandatory
       DESCRIPTION
           "Domain Controller Site Link table"
      ::= { exchAdInventoryGen 23 }

   exchAdDomainControllerSiteLinkEntry OBJECT-TYPE
       SYNTAX      ExchAdDomainControllerSiteLinkEntry
       ACCESS      not-accessible
       STATUS      mandatory
       DESCRIPTION
           "defines an entry in the exchAdDomainControllerSiteLinkTable"

       INDEX {
                exchAdDomainControllerSiteLinkForestIndex,
                exchAdDomainControllerSiteLinkIndex
             }
       ::= { exchAdDomainControllerSiteLinkTable 1 }

   ExchAdDomainControllerSiteLinkEntry ::=
       SEQUENCE {
           exchAdDomainControllerSiteLinkForestIndex        INTEGER,
           exchAdDomainControllerSiteLinkIndex              INTEGER,
           exchAdDomainControllerSiteLinkName               SnmpAdminString
       }

   exchAdDomainControllerSiteLinkForestIndex OBJECT-TYPE
       SYNTAX      INTEGER (0..2147483647)
       ACCESS      read-only
       STATUS      mandatory
       DESCRIPTION "forest Identifier, same as exchAdForestIndex"
       ::= { exchAdDomainControllerSiteLinkEntry 1 }

   exchAdDomainControllerSiteLinkIndex OBJECT-TYPE
       SYNTAX      INTEGER (0..2147483647)
       ACCESS      read-only
       STATUS      mandatory
       DESCRIPTION "unique index for each Site Link within a Forest"
       ::= { exchAdDomainControllerSiteLinkEntry 2 }

   exchAdDomainControllerSiteLinkName OBJECT-TYPE
       SYNTAX      SnmpAdminString
       ACCESS      read-only
       STATUS      mandatory
       DESCRIPTION "name of Site Link"
       ::= { exchAdDomainControllerSiteLinkEntry 3 }

--**************************************************************************  
--
-- exchAdDomainControllerSubnetTable
--
-- This table was not in version 1.0.
--
--**************************************************************************

   exchAdDomainControllerSubnetTable OBJECT-TYPE
       SYNTAX      SEQUENCE OF ExchAdDomainControllerSubnetEntry
       ACCESS      not-accessible
       STATUS      mandatory
       DESCRIPTION
           "Domain Controller Subnet table"
      ::= { exchAdInventoryGen 24 }

   exchAdDomainControllerSubnetEntry OBJECT-TYPE
       SYNTAX      ExchAdDomainControllerSubnetEntry
       ACCESS      not-accessible
       STATUS      mandatory
       DESCRIPTION
           "defines an entry in the exchAdDomainControllerSubnetTable"

       INDEX {
                exchAdDomainControllerSubnetForestIndex,
                exchAdDomainControllerSubnetIndex
             }
       ::= { exchAdDomainControllerSubnetTable 1 }

   ExchAdDomainControllerSubnetEntry ::=
       SEQUENCE {
           exchAdDomainControllerSubnetForestIndex          INTEGER,
           exchAdDomainControllerSubnetIndex                INTEGER,
           exchAdDomainControllerSubnetName                 SnmpAdminString,
           exchAdDomainControllerSubnetLocation             SnmpAdminString
       }

   exchAdDomainControllerSubnetForestIndex OBJECT-TYPE
       SYNTAX      INTEGER (0..2147483647)
       ACCESS      read-only
       STATUS      mandatory
       DESCRIPTION "forest Identifier, same as exchAdForestIndex"
       ::= { exchAdDomainControllerSubnetEntry 1 }

   exchAdDomainControllerSubnetIndex OBJECT-TYPE
       SYNTAX      INTEGER (0..2147483647)
       ACCESS      read-only
       STATUS      mandatory
       DESCRIPTION "unique index for each Subnet within a Forest"
       ::= { exchAdDomainControllerSubnetEntry 2 }

   exchAdDomainControllerSubnetName OBJECT-TYPE
       SYNTAX      SnmpAdminString
       ACCESS      read-only
       STATUS      mandatory
       DESCRIPTION "name of Subnet"
       ::= { exchAdDomainControllerSubnetEntry 3 }

   exchAdDomainControllerSubnetLocation OBJECT-TYPE
       SYNTAX      SnmpAdminString
       ACCESS      read-only
       STATUS      mandatory
       DESCRIPTION "name of Subnet location"
       ::= { exchAdDomainControllerSubnetEntry 4 }

--**************************************************************************  
--
-- exchAdDomainControllerPrefRpcBrdgHdSvrTable
--
-- This table was not in version 1.0.
--
--**************************************************************************

   exchAdDomainControllerPrefRpcBrdgHdSvrTable OBJECT-TYPE
       SYNTAX      SEQUENCE OF ExchAdDomainControllerPrefRpcBrdgHdSvrEntry
       ACCESS      not-accessible
       STATUS      mandatory
       DESCRIPTION
           "Domain Controller Preferred RPC Bridgehead Server table"
      ::= { exchAdInventoryGen 25 }

   exchAdDomainControllerPrefRpcBrdgHdSvrEntry OBJECT-TYPE
       SYNTAX      ExchAdDomainControllerPrefRpcBrdgHdSvrEntry
       ACCESS      not-accessible
       STATUS      mandatory
       DESCRIPTION
           "defines an entry in the exchAdDomainControllerPrefRpcBrdgHdSvrTable"

       INDEX {
                exchAdDomainControllerPrefRpcBrdgHdSvrForestIndex,
                exchAdDomainControllerPrefRpcBrdgHdSvrIndex
             }
       ::= { exchAdDomainControllerPrefRpcBrdgHdSvrTable 1 }

   ExchAdDomainControllerPrefRpcBrdgHdSvrEntry ::=
       SEQUENCE {
           exchAdDomainControllerPrefRpcBrdgHdSvrForestIndex        INTEGER,
           exchAdDomainControllerPrefRpcBrdgHdSvrIndex              INTEGER,
           exchAdDomainControllerPrefRpcBrdgHdSvrName               SnmpAdminString
       }

   exchAdDomainControllerPrefRpcBrdgHdSvrForestIndex OBJECT-TYPE
       SYNTAX      INTEGER (0..2147483647)
       ACCESS      read-only
       STATUS      mandatory
       DESCRIPTION "forest Identifier, same as exchAdForestIndex"
       ::= { exchAdDomainControllerPrefRpcBrdgHdSvrEntry 1 }

   exchAdDomainControllerPrefRpcBrdgHdSvrIndex OBJECT-TYPE
       SYNTAX      INTEGER (0..2147483647)
       ACCESS      read-only
       STATUS      mandatory
       DESCRIPTION "unique index for each Preferred RPC Bridgehead Server within a Forest, same as exchAdUniversalHostIndex"
       ::= { exchAdDomainControllerPrefRpcBrdgHdSvrEntry 2 }

   exchAdDomainControllerPrefRpcBrdgHdSvrName OBJECT-TYPE
       SYNTAX      SnmpAdminString
       ACCESS      read-only
       STATUS      mandatory
       DESCRIPTION "name of Preferred RPC Bridgehead Server"
       ::= { exchAdDomainControllerPrefRpcBrdgHdSvrEntry 3 }

--**************************************************************************  
--
-- exchAdDomainControllerBrdgHdSvrTable
--
-- This table was not in version 1.0.
--
--**************************************************************************

   exchAdDomainControllerBrdgHdSvrTable OBJECT-TYPE
       SYNTAX      SEQUENCE OF ExchAdDomainControllerBrdgHdSvrEntry
       ACCESS      not-accessible
       STATUS      mandatory
       DESCRIPTION
           "Domain Controller Bridgehead Server table"
      ::= { exchAdInventoryGen 26 }

   exchAdDomainControllerBrdgHdSvrEntry OBJECT-TYPE
       SYNTAX      ExchAdDomainControllerBrdgHdSvrEntry
       ACCESS      not-accessible
       STATUS      mandatory
       DESCRIPTION
           "defines an entry in the exchAdDomainControllerBrdgHdSvrTable"

       INDEX {
                exchAdDomainControllerBrdgHdSvrForestIndex,
                exchAdDomainControllerBrdgHdSvrIndex
             }
       ::= { exchAdDomainControllerBrdgHdSvrTable 1 }

   ExchAdDomainControllerBrdgHdSvrEntry ::=
       SEQUENCE {
           exchAdDomainControllerBrdgHdSvrForestIndex       INTEGER,
           exchAdDomainControllerBrdgHdSvrIndex             INTEGER,
           exchAdDomainControllerBrdgHdSvrName              SnmpAdminString
       }

   exchAdDomainControllerBrdgHdSvrForestIndex OBJECT-TYPE
       SYNTAX      INTEGER (0..2147483647)
       ACCESS      read-only
       STATUS      mandatory
       DESCRIPTION "forest Identifier, same as exchAdForestIndex"
       ::= { exchAdDomainControllerBrdgHdSvrEntry 1 }

   exchAdDomainControllerBrdgHdSvrIndex OBJECT-TYPE
       SYNTAX      INTEGER (0..2147483647)
       ACCESS      read-only
       STATUS      mandatory
       DESCRIPTION "unique index for each Bridgehead Server within a Forest, same as exchAdUniversalHostIndex"
       ::= { exchAdDomainControllerBrdgHdSvrEntry 2 }

   exchAdDomainControllerBrdgHdSvrName OBJECT-TYPE
       SYNTAX      SnmpAdminString
       ACCESS      read-only
       STATUS      mandatory
       DESCRIPTION "name of Bridgehead Server"
       ::= { exchAdDomainControllerBrdgHdSvrEntry 3 }

--**************************************************************************  
--
-- Inventory parameters: Mailbox Role
--
--**************************************************************************

--**************************************************************************  
--
-- exchAdMailboxHostInventoryTable
--
--**************************************************************************

   exchAdMailboxHostInventoryTable OBJECT-TYPE
       SYNTAX      SEQUENCE OF ExchAdMailboxHostInventoryEntry
       ACCESS      not-accessible
       STATUS      mandatory
       DESCRIPTION
           "mailbox host inventory table"
      ::= { exchAdInventoryMailboxRole 1 }

    exchAdMailboxHostInventoryEntry OBJECT-TYPE
       SYNTAX      ExchAdMailboxHostInventoryEntry
       ACCESS      not-accessible
       STATUS      mandatory
       DESCRIPTION
           "defines an entry in the exchAdMailboxHostInventoryTable"

       INDEX {
                exchAdMailboxHostInvHostIndex
             }
       ::= { exchAdMailboxHostInventoryTable 1 }

   ExchAdMailboxHostInventoryEntry ::=
       SEQUENCE {
            exchAdMailboxHostInvHostIndex                           INTEGER,
            exchAdMailboxHostInvDataPath                            SnmpAdminString,
            exchAdMailboxHostInvEdition                             SnmpAdminString,
            exchAdMailboxHostInvFqdn                                SnmpAdminString,
            exchAdMailboxHostInvIsExchange2007OrLater               INTEGER, 
            exchAdMailboxHostInvOrganizationalUnit                  SnmpAdminString,
            exchAdMailboxHostInvAdminDisplayVersion                 SnmpAdminString,
            exchAdMailboxHostInvSite                                SnmpAdminString,
            exchAdMailboxHostInvCurrentConfigDomainControllerIndex  INTEGER,
            exchAdMailboxHostInvProductID                           SnmpAdminString,
            exchAdMailboxHostInvIsExchangeTrialEdition              INTEGER, 
            exchAdMailboxHostInvIsExpiredExchangeTrialEdition       INTEGER, 
            exchAdMailboxHostInvRemainingTrialPeriod                INTEGER,
            exchAdMailboxHostInvOriginatingServerIndex              INTEGER,
            exchAdMailboxHostInvExchangeVersion                     SnmpAdminString,
            exchAdMailboxHostInvIdentity                            SnmpAdminString,
            exchAdMailboxHostInvLogPathForManagedFolders            SnmpAdminString,
            exchAdMailboxHostInvMessageTrackingLogEnabled           INTEGER,  
            exchAdMailboxHostInvMessageTrackingLogPath              SnmpAdminString,
            exchAdMailboxHostInvMAPIEncryptionRequired              INTEGER,
            exchAdMailboxHostInvNumMailboxes                        INTEGER
            }

   exchAdMailboxHostInvHostIndex OBJECT-TYPE
       SYNTAX      INTEGER (0..2147483647)
       ACCESS      read-only
       STATUS      mandatory
       DESCRIPTION
          "unique index for each host, same as exchAdUniversalHostIndex"
       ::= { exchAdMailboxHostInventoryEntry 1 }

   exchAdMailboxHostInvDataPath OBJECT-TYPE
       SYNTAX      SnmpAdminString
       ACCESS      read-only
       STATUS      mandatory
       DESCRIPTION
          "data path of the Exchange Server"
       ::= { exchAdMailboxHostInventoryEntry 2 }

   exchAdMailboxHostInvEdition OBJECT-TYPE
       SYNTAX      SnmpAdminString
       ACCESS      read-only
       STATUS      mandatory
       DESCRIPTION
          "name of the Exchange Server Edition"
       ::= { exchAdMailboxHostInventoryEntry 3 }

   exchAdMailboxHostInvFqdn OBJECT-TYPE
       SYNTAX      SnmpAdminString
       ACCESS      read-only
       STATUS      mandatory
       DESCRIPTION
          "Fully Qualified Domain Name of the Exchange Server"
       ::= { exchAdMailboxHostInventoryEntry 4 }

   exchAdMailboxHostInvIsExchange2007OrLater OBJECT-TYPE
       SYNTAX      INTEGER {ex2007orlater(1), other(2)}
       ACCESS      read-only
       STATUS      mandatory
       DESCRIPTION
          "Indicates whether Exchange server version installed is 2007 or later"
       ::= { exchAdMailboxHostInventoryEntry 5 }

   exchAdMailboxHostInvOrganizationalUnit OBJECT-TYPE
       SYNTAX      SnmpAdminString
       ACCESS      read-only
       STATUS      mandatory
       DESCRIPTION
          "organizational unit"
       ::= { exchAdMailboxHostInventoryEntry 6 }

   exchAdMailboxHostInvAdminDisplayVersion OBJECT-TYPE
       SYNTAX      SnmpAdminString
       ACCESS      read-only
       STATUS      mandatory
       DESCRIPTION
          "displays the Admins Display version and the build number of the Exchange Server"
       ::= { exchAdMailboxHostInventoryEntry 7 }

   exchAdMailboxHostInvSite OBJECT-TYPE
       SYNTAX      SnmpAdminString
       ACCESS      read-only
       STATUS      mandatory
       DESCRIPTION
          "site name on IIS server"
       ::= { exchAdMailboxHostInventoryEntry 8 }

   exchAdMailboxHostInvCurrentConfigDomainControllerIndex OBJECT-TYPE
       SYNTAX      INTEGER
       ACCESS      read-only
       STATUS      mandatory
       DESCRIPTION
          "pointer to Config Domain Controller in exchAdDomainControllerTable, same as exchAdUniversalHostIndex"
       ::= { exchAdMailboxHostInventoryEntry 9 }

   exchAdMailboxHostInvProductID OBJECT-TYPE
       SYNTAX      SnmpAdminString
       ACCESS      read-only
       STATUS      mandatory
       DESCRIPTION
          "Product ID"
       ::= { exchAdMailboxHostInventoryEntry 10 }

   exchAdMailboxHostInvIsExchangeTrialEdition OBJECT-TYPE
       SYNTAX      INTEGER {trial(1), other(2)}
       ACCESS      read-only
       STATUS      mandatory
       DESCRIPTION
          "whether Exchange Server is of 2007 or 2010 trial version"
       ::= { exchAdMailboxHostInventoryEntry 11 }

   exchAdMailboxHostInvIsExpiredExchangeTrialEdition OBJECT-TYPE
       SYNTAX      INTEGER {expired(1), unexpired(2)}
       ACCESS      read-only
       STATUS      mandatory
       DESCRIPTION
          " whether trial period has expired"
       ::= { exchAdMailboxHostInventoryEntry 12 }

   exchAdMailboxHostInvRemainingTrialPeriod OBJECT-TYPE
       SYNTAX      INTEGER
       ACCESS      read-only
       STATUS      mandatory
       DESCRIPTION
          "number of remaining trial period days; zero if trial period has expired"
       ::= { exchAdMailboxHostInventoryEntry 13 }

   exchAdMailboxHostInvOriginatingServerIndex OBJECT-TYPE
       SYNTAX      INTEGER
       ACCESS      read-only
       STATUS      mandatory
       DESCRIPTION
          "pointer to originating server in exchAdUniversalHostTable, same as exchAdUniversalHostIndex"
       ::= { exchAdMailboxHostInventoryEntry 14 }

   exchAdMailboxHostInvExchangeVersion OBJECT-TYPE
       SYNTAX      SnmpAdminString
       ACCESS      read-only
       STATUS      mandatory
       DESCRIPTION
          "Exchange version name"
       ::= { exchAdMailboxHostInventoryEntry 15 }

   exchAdMailboxHostInvIdentity OBJECT-TYPE
       SYNTAX      SnmpAdminString
       ACCESS      read-only
       STATUS      mandatory
       DESCRIPTION
          "Identity of the exchange server"
       ::= { exchAdMailboxHostInventoryEntry 16 }

   exchAdMailboxHostInvLogPathForManagedFolders OBJECT-TYPE
       SYNTAX      SnmpAdminString
       ACCESS      read-only
       STATUS      mandatory
       DESCRIPTION
          "path to the directory that stores the managed folder log files"
       ::= { exchAdMailboxHostInventoryEntry 17 }

   exchAdMailboxHostInvMessageTrackingLogEnabled OBJECT-TYPE
       SYNTAX      INTEGER {enabled(1), disabled(2)}
       ACCESS      read-only
       STATUS      mandatory
       DESCRIPTION
          "whether message tracking is enabled. The default value is enabled(1)."
       ::= { exchAdMailboxHostInventoryEntry 18 }

   exchAdMailboxHostInvMessageTrackingLogPath OBJECT-TYPE
       SYNTAX      SnmpAdminString
       ACCESS      read-only
       STATUS      mandatory
       DESCRIPTION
          "location of the message tracking logs."
       ::= { exchAdMailboxHostInventoryEntry 19 }

   exchAdMailboxHostInvMAPIEncryptionRequired OBJECT-TYPE
       SYNTAX      INTEGER {required(1), notRequired(2)}
       ACCESS      read-only
       STATUS      mandatory
       DESCRIPTION
          "whether Exchange requires MAPI clients to use encrypted remote procedure calls (RPCs)"
       ::= { exchAdMailboxHostInventoryEntry 20 }

   exchAdMailboxHostInvNumMailboxes OBJECT-TYPE
       SYNTAX      INTEGER
       ACCESS      read-only
       STATUS      mandatory
       DESCRIPTION
          "number of mailboxes hosted on this server"
       ::= { exchAdMailboxHostInventoryEntry 21 }

--**************************************************************************  
--
-- exchAdMailboxHostInventory2007Table
--
--**************************************************************************

   exchAdMailboxHostInventory2007Table OBJECT-TYPE
       SYNTAX      SEQUENCE OF ExchAdMailboxHostInventory2007Entry
       ACCESS      not-accessible
       STATUS      mandatory
       DESCRIPTION
           "mailbox host inventory table: Exchange 2007 only"
      ::= { exchAdInventoryMailboxRole 2 }

   exchAdMailboxHostInventory2007Entry OBJECT-TYPE
       SYNTAX      ExchAdMailboxHostInventory2007Entry
       ACCESS      not-accessible
       STATUS      mandatory
       DESCRIPTION
           "defines an entry in the exchAdMailboxHostInventory2007Table"

       INDEX {
                exchAdMailboxHostInv2007HostIndex
             }
       ::= { exchAdMailboxHostInventory2007Table 1 }

   ExchAdMailboxHostInventory2007Entry ::=
       SEQUENCE {
            exchAdMailboxHostInv2007HostIndex                  INTEGER,
            exchAdMailboxHostInv2007IsMemberOfCluster          INTEGER,
            exchAdMailboxHostInv2007IsProvisionedServer        INTEGER, 
            exchAdMailboxHostInv2007ClusteredStorageType       SnmpAdminString,
            exchAdMailboxHostInv2007ExchangeVersion            SnmpAdminString,
            exchAdMailboxHostInv2007DistinguishedName          SnmpAdminString,
            exchAdMailboxHostInv2007RedundantMachines          SnmpAdminString
                }

   exchAdMailboxHostInv2007HostIndex OBJECT-TYPE
       SYNTAX      INTEGER (0..2147483647)
       ACCESS      read-only
       STATUS      mandatory
       DESCRIPTION
          "unique index for each host, same as exchAdUniversalHostIndex"
       ::= { exchAdMailboxHostInventory2007Entry 1 }

   exchAdMailboxHostInv2007IsMemberOfCluster OBJECT-TYPE
       SYNTAX      INTEGER {member(1), notMember(2)}
       ACCESS      read-only
       STATUS      mandatory
       DESCRIPTION
          "whether the host is a member of a cluster"
       ::= { exchAdMailboxHostInventory2007Entry 2 }

   exchAdMailboxHostInv2007IsProvisionedServer OBJECT-TYPE
       SYNTAX      INTEGER {provisioned(1), notProvisioned(2)}
       ACCESS      read-only
       STATUS      mandatory
       DESCRIPTION
          "whether host is provisioned"
       ::= { exchAdMailboxHostInventory2007Entry 3 }

   exchAdMailboxHostInv2007ClusteredStorageType OBJECT-TYPE
       SYNTAX      SnmpAdminString
       ACCESS      read-only
       STATUS      mandatory
       DESCRIPTION
          "clustered storage type"
       ::= { exchAdMailboxHostInventory2007Entry 4 }

   exchAdMailboxHostInv2007ExchangeVersion OBJECT-TYPE
       SYNTAX      SnmpAdminString
       ACCESS      read-only
       STATUS      mandatory
       DESCRIPTION
          "Exchange version name"
       ::= { exchAdMailboxHostInventory2007Entry 5 }

   exchAdMailboxHostInv2007DistinguishedName OBJECT-TYPE
       SYNTAX      SnmpAdminString
       ACCESS      read-only
       STATUS      mandatory
       DESCRIPTION
          "distinguished name"
       ::= { exchAdMailboxHostInventory2007Entry 6 }

   exchAdMailboxHostInv2007RedundantMachines OBJECT-TYPE
       SYNTAX      SnmpAdminString
       ACCESS      read-only
       STATUS      mandatory
       DESCRIPTION
          "list of redundant machines"
       ::= { exchAdMailboxHostInventory2007Entry 7 }

--**************************************************************************  
--
-- exchAdMailboxHostInventory2010Table
--
--**************************************************************************

   exchAdMailboxHostInventory2010Table OBJECT-TYPE
       SYNTAX      SEQUENCE OF ExchAdMailboxHostInventory2010Entry
       ACCESS      not-accessible
       STATUS      mandatory
       DESCRIPTION
           "mailbox host inventory table: Exchange 2010 only"
      ::= { exchAdInventoryMailboxRole 3 }

   exchAdMailboxHostInventory2010Entry OBJECT-TYPE
       SYNTAX      ExchAdMailboxHostInventory2010Entry
       ACCESS      not-accessible
       STATUS      mandatory
       DESCRIPTION
           "defines an entry in the exchAdMailboxHostInventory2010Table"

       INDEX {
                exchAdMailboxHostInv2010HostIndex
             }
       ::= { exchAdMailboxHostInventory2010Table 1 }

   ExchAdMailboxHostInventory2010Entry ::=
       SEQUENCE {
            exchAdMailboxHostInv2010HostIndex                     INTEGER,
            exchAdMailboxHostInv2010IsE14OrLater                  INTEGER,
            exchAdMailboxHostInv2010DagIndex                      INTEGER,
            exchAdMailboxHostInv2010TransportSyncDispatchEnabled  INTEGER,
            exchAdMailboxHostInv2010TransportSyncLogEnabled       INTEGER,
            exchAdMailboxHostInv2010TransportSyncLogFilePath      SnmpAdminString,
            exchAdMailboxHostInv2010IsExcludedFromProvisioning    INTEGER
                }

   exchAdMailboxHostInv2010HostIndex OBJECT-TYPE
       SYNTAX      INTEGER (0..2147483647)
       ACCESS      read-only
       STATUS      mandatory
       DESCRIPTION
          "unique index for each host, same as exchAdUniversalHostIndex"
       ::= { exchAdMailboxHostInventory2010Entry 1 }

   exchAdMailboxHostInv2010IsE14OrLater OBJECT-TYPE
       SYNTAX      INTEGER {e14orlater(1), other(2)}
       ACCESS      read-only
       STATUS      mandatory
       DESCRIPTION
          "whether server is E14 or Later"
       ::= { exchAdMailboxHostInventory2010Entry 2 }

   exchAdMailboxHostInv2010DagIndex OBJECT-TYPE
       SYNTAX      INTEGER
       ACCESS      read-only
       STATUS      mandatory
       DESCRIPTION
          "pointer to DAG in exchAdDagTable"
       ::= { exchAdMailboxHostInventory2010Entry 3 }

   exchAdMailboxHostInv2010TransportSyncDispatchEnabled OBJECT-TYPE
       SYNTAX      INTEGER {enabled(1), disabled(2)}
       ACCESS      read-only
       STATUS      mandatory
       DESCRIPTION
          "whether the transport sync dispatch is enabled"
       ::= { exchAdMailboxHostInventory2010Entry 4 }

   exchAdMailboxHostInv2010TransportSyncLogEnabled OBJECT-TYPE
       SYNTAX      INTEGER {enabled(1), disabled(2)}
       ACCESS      read-only
       STATUS      mandatory
       DESCRIPTION
          "whether Transport Sync Log is enabled"
       ::= { exchAdMailboxHostInventory2010Entry 5 }

   exchAdMailboxHostInv2010TransportSyncLogFilePath OBJECT-TYPE
       SYNTAX      SnmpAdminString
       ACCESS      read-only
       STATUS      mandatory
       DESCRIPTION
          "Transport Sync Log File path"
       ::= { exchAdMailboxHostInventory2010Entry 6 }

   exchAdMailboxHostInv2010IsExcludedFromProvisioning OBJECT-TYPE
       SYNTAX      INTEGER {included(1), excluded(2)}
       ACCESS      read-only
       STATUS      mandatory
       DESCRIPTION
          "whether host is excluded from provisioning"
       ::= { exchAdMailboxHostInventory2010Entry 7 }

--**************************************************************************  
--
-- exchAdMailboxStorageGroupInventory2007Table
--
--**************************************************************************

   exchAdMailboxStorageGroupInventory2007Table OBJECT-TYPE
       SYNTAX      SEQUENCE OF ExchAdMailboxStorageGroupInventory2007Entry
       ACCESS      not-accessible
       STATUS      mandatory
       DESCRIPTION
           "mailbox storage group inventory table: Exchange 2007 only"
      ::= { exchAdInventoryMailboxRole 4 }

    exchAdMailboxStorageGroupInventory2007Entry OBJECT-TYPE
       SYNTAX      ExchAdMailboxStorageGroupInventory2007Entry
       ACCESS      not-accessible
       STATUS      mandatory
       DESCRIPTION
           "defines an entry in the exchAdMailboxStorageGroupInventory2007Table"

       INDEX {
                exchAdMailboxStorageGroupInventory2007Index 
             }
       ::= { exchAdMailboxStorageGroupInventory2007Table 1 }

    ExchAdMailboxStorageGroupInventory2007Entry ::=
       SEQUENCE {
            exchAdMailboxStorageGroupInventory2007Index           INTEGER,
            exchAdMailboxStorageGroupInventory2007HostIndex       INTEGER
                }

    exchAdMailboxStorageGroupInventory2007Index OBJECT-TYPE
       SYNTAX      INTEGER (0..2147483647)
       ACCESS      read-only
       STATUS      mandatory
       DESCRIPTION
          "unique index for each mailbox storage group"
       ::= { exchAdMailboxStorageGroupInventory2007Entry 1 }

    exchAdMailboxStorageGroupInventory2007HostIndex OBJECT-TYPE
       SYNTAX      INTEGER
       ACCESS      read-only
       STATUS      mandatory
       DESCRIPTION
          "pointer to host in exchAdUniversalHostTable, same as exchAdUniversalHostIndex"
       ::= { exchAdMailboxStorageGroupInventory2007Entry 2 }

--**************************************************************************  
--
-- exchAdMailboxDatabaseInventoryTable
--
--**************************************************************************

    exchAdMailboxDatabaseInventoryTable OBJECT-TYPE
       SYNTAX      SEQUENCE OF ExchAdMailboxDatabaseInventoryEntry
       ACCESS      not-accessible
       STATUS      mandatory
       DESCRIPTION
           "mailbox database inventory table"
      ::= { exchAdInventoryMailboxRole 5 }

    exchAdMailboxDatabaseInventoryEntry OBJECT-TYPE
       SYNTAX      ExchAdMailboxDatabaseInventoryEntry
       ACCESS      not-accessible
       STATUS      mandatory
       DESCRIPTION
           "defines an entry in the exchAdMailboxDatabaseInventoryTable"

       INDEX {
                exchAdMailboxDatabaseInventoryIndex
             }
       ::= { exchAdMailboxDatabaseInventoryTable 1 }

    ExchAdMailboxDatabaseInventoryEntry ::=
       SEQUENCE {
            exchAdMailboxDatabaseInventoryIndex             INTEGER,
            exchAdMailboxDatabaseInventoryDatabaseName      SnmpAdminString,
            exchAdMailboxDatabaseInventoryHostIndex         INTEGER                 
                }

    exchAdMailboxDatabaseInventoryIndex OBJECT-TYPE
       SYNTAX      INTEGER (0..2147483647)
       ACCESS      read-only
       STATUS      mandatory
       DESCRIPTION
          "unique index for each database"
       ::= { exchAdMailboxDatabaseInventoryEntry 1 }

    exchAdMailboxDatabaseInventoryDatabaseName OBJECT-TYPE
       SYNTAX      SnmpAdminString
       ACCESS      read-only
       STATUS      mandatory
       DESCRIPTION
          "name of database"
       ::= { exchAdMailboxDatabaseInventoryEntry 2 }

    exchAdMailboxDatabaseInventoryHostIndex OBJECT-TYPE
       SYNTAX      INTEGER
       ACCESS      read-only
       STATUS      mandatory
       DESCRIPTION
          "pointer to host in exchAdUniversalHostTable, same as exchAdUniversalHostIndex"
       ::= { exchAdMailboxDatabaseInventoryEntry 3 }

--**************************************************************************  
--
-- exchAdMailboxDatabaseInventory2007Table
--
--**************************************************************************

   exchAdMailboxDatabaseInventory2007Table OBJECT-TYPE
       SYNTAX      SEQUENCE OF ExchAdMailboxDatabaseInventory2007Entry
       ACCESS      not-accessible
       STATUS      mandatory
       DESCRIPTION
           "mailbox database inventory table: Exchange 2007 only"
      ::= { exchAdInventoryMailboxRole 6 }

    exchAdMailboxDatabaseInventory2007Entry OBJECT-TYPE
       SYNTAX      ExchAdMailboxDatabaseInventory2007Entry
       ACCESS      not-accessible
       STATUS      mandatory
       DESCRIPTION
           "defines an entry in the exchAdMailboxDatabaseInventory2007Table"

       INDEX {
                exchAdMailboxDatabaseInventory2007Index
             }
       ::= { exchAdMailboxDatabaseInventory2007Table 1 }

    ExchAdMailboxDatabaseInventory2007Entry ::=
       SEQUENCE {
            exchAdMailboxDatabaseInventory2007Index             INTEGER,
            exchAdMailboxDatabaseInventory2007StorageGroupIndex INTEGER                 
                }

    exchAdMailboxDatabaseInventory2007Index OBJECT-TYPE
       SYNTAX      INTEGER (0..2147483647)
       ACCESS      read-only
       STATUS      mandatory
       DESCRIPTION
          "unique index for each Exchange 2007 database, same as exchAdMailboxDatabaseInventoryIndex"
       ::= { exchAdMailboxDatabaseInventory2007Entry 1 }

    exchAdMailboxDatabaseInventory2007StorageGroupIndex OBJECT-TYPE
       SYNTAX      INTEGER
       ACCESS      read-only
       STATUS      mandatory
       DESCRIPTION
          "pointer to  mailbox storage group in exchAdMailboxStorageGroupInventory2007Table"
       ::= { exchAdMailboxDatabaseInventory2007Entry 2 }                           

--**************************************************************************  
--
-- Inventory parameters: Hub Transport Role
--
--**************************************************************************

--**************************************************************************  
--
-- exchAdHubTransHostInventoryTable
--
--**************************************************************************

    exchAdHubTransHostInventoryTable OBJECT-TYPE
       SYNTAX      SEQUENCE OF ExchAdHubTransHostInventoryEntry
       ACCESS      not-accessible
       STATUS      mandatory
       DESCRIPTION
           "hub transport host inventory table"
      ::= { exchAdInventoryHubTransportRole 1 }

    exchAdHubTransHostInventoryEntry OBJECT-TYPE
       SYNTAX      ExchAdHubTransHostInventoryEntry
       ACCESS      not-accessible
       STATUS      mandatory
       DESCRIPTION
           "defines an entry in the exchAdHubTransHostInventoryTable"

       INDEX {
                exchAdHubTransHostInvHostIndex
             }
       ::= { exchAdHubTransHostInventoryTable 1 }

   ExchAdHubTransHostInventoryEntry ::=
       SEQUENCE {
            exchAdHubTransHostInvHostIndex                    INTEGER,
            exchAdHubTransHostInvConnectivityLogEnabled       INTEGER,
            exchAdHubTransHostInvConnectivityLogPath          SnmpAdminString,
            exchAdHubTransHostInvExternalDNSServers           SnmpAdminString,
            exchAdHubTransHostInvExternaIpAddressType         InetAddressType,
            exchAdHubTransHostInvExternaIpAddress             InetAddress,
            exchAdHubTransHostInvInternalDNSServers           SnmpAdminString,
            exchAdHubTransHostInvMessageTrackingLogEnabled    INTEGER,
            exchAdHubTransHostInvMessageTrackingLogPath       SnmpAdminString,
            exchAdHubTransHostInvRoutingTableLogPath          SnmpAdminString,
            exchAdHubTransHostInvOriginatingServerIndex       INTEGER,
            exchAdHubTransHostInvIdentity                     SnmpAdminString      
            }


   exchAdHubTransHostInvHostIndex OBJECT-TYPE
       SYNTAX      INTEGER (0..2147483647)
       ACCESS      read-only
       STATUS      mandatory
       DESCRIPTION
          "unique index for each host, same as exchAdUniversalHostIndex"
       ::= { exchAdHubTransHostInventoryEntry 1 }

   exchAdHubTransHostInvConnectivityLogEnabled OBJECT-TYPE
       SYNTAX      INTEGER {enabled(1), disabled(2)}
       ACCESS      read-only
       STATUS      mandatory
       DESCRIPTION
          "whether the connectivity log is enabled or disabled. "
       ::= { exchAdHubTransHostInventoryEntry 2 }

   exchAdHubTransHostInvConnectivityLogPath OBJECT-TYPE
       SYNTAX      SnmpAdminString
       ACCESS      read-only
       STATUS      mandatory
       DESCRIPTION
          " default connectivity log directory location"
       ::= { exchAdHubTransHostInventoryEntry 3 }

   exchAdHubTransHostInvExternalDNSServers OBJECT-TYPE
       SYNTAX      SnmpAdminString
       ACCESS      read-only
       STATUS      mandatory
       DESCRIPTION
          " list of DNS servers that should be used when resolving a domain name."
       ::= { exchAdHubTransHostInventoryEntry 4 }

   exchAdHubTransHostInvExternaIpAddressType OBJECT-TYPE
       SYNTAX      InetAddressType
       ACCESS      read-only
       STATUS      mandatory
       DESCRIPTION
          "IP address Type that is used in the received message header field"       ::= { exchAdHubTransHostInventoryEntry 5 }

   exchAdHubTransHostInvExternaIpAddress OBJECT-TYPE
       SYNTAX      InetAddress
       ACCESS      read-only
       STATUS      mandatory
       DESCRIPTION
          "IP address that is used in the received message header field"
       ::= { exchAdHubTransHostInventoryEntry 6 }

   exchAdHubTransHostInvInternalDNSServers OBJECT-TYPE
       SYNTAX      SnmpAdminString
       ACCESS      read-only
       STATUS      mandatory
       DESCRIPTION
          "list of DNS servers that should be used when resolving a domain name"
       ::= { exchAdHubTransHostInventoryEntry 7 }

   exchAdHubTransHostInvMessageTrackingLogEnabled OBJECT-TYPE
       SYNTAX      INTEGER {enabled(1), disabled(2)}
       ACCESS      read-only
       STATUS      mandatory
       DESCRIPTION
          "whether message tracking is enabled. The default value is enabled(1)"
       ::= { exchAdHubTransHostInventoryEntry 8 }

   exchAdHubTransHostInvMessageTrackingLogPath OBJECT-TYPE
       SYNTAX      SnmpAdminString
       ACCESS      read-only
       STATUS      mandatory
       DESCRIPTION
          " location of the message tracking logs"
       ::= { exchAdHubTransHostInventoryEntry 9 }

   exchAdHubTransHostInvRoutingTableLogPath OBJECT-TYPE
       SYNTAX      SnmpAdminString
       ACCESS      read-only
       STATUS      mandatory
       DESCRIPTION
          "directory location where routing table log files should be stored"
       ::= { exchAdHubTransHostInventoryEntry 10 }

   exchAdHubTransHostInvOriginatingServerIndex OBJECT-TYPE
       SYNTAX      INTEGER
       ACCESS      read-only
       STATUS      mandatory
       DESCRIPTION
          "pointer to originating server in exchAdUniversalHostTable, same as exchAdUniversalHostIndex"
       ::= { exchAdHubTransHostInventoryEntry 11 }

   exchAdHubTransHostInvIdentity OBJECT-TYPE
       SYNTAX      SnmpAdminString
       ACCESS      read-only
       STATUS      mandatory
       DESCRIPTION
          " identity of the transport server"
       ::= { exchAdHubTransHostInventoryEntry 12 }

--**************************************************************************  
--
-- exchAdHubTransHostInventory2010Table
--
--**************************************************************************

   exchAdHubTransHostInventory2010Table OBJECT-TYPE
       SYNTAX      SEQUENCE OF ExchAdHubTransHostInventory2010Entry
       ACCESS      not-accessible
       STATUS      mandatory
       DESCRIPTION
           "hub transport host inventory table: Exchange 2010 only"
      ::= { exchAdInventoryHubTransportRole 2 }

    exchAdHubTransHostInventory2010Entry OBJECT-TYPE
       SYNTAX      ExchAdHubTransHostInventory2010Entry
       ACCESS      not-accessible
       STATUS      mandatory
       DESCRIPTION
           "defines an entry in the exchAdHubTransHostInventory2010Table"

       INDEX {
                exchAdHubTransHostInv2010HostIndex
             }
       ::= { exchAdHubTransHostInventory2010Table 1 }

   ExchAdHubTransHostInventory2010Entry ::=
       SEQUENCE {
            exchAdHubTransHostInv2010HostIndex                     INTEGER,
            exchAdHubTransHostInv2010ServerStatisticsLogPath      SnmpAdminString
            }

   exchAdHubTransHostInv2010HostIndex OBJECT-TYPE
       SYNTAX      INTEGER (0..2147483647)
       ACCESS      read-only
       STATUS      mandatory
       DESCRIPTION
          "unique index for each host, same as exchAdUniversalHostIndex"
       ::= { exchAdHubTransHostInventory2010Entry 1 }

   exchAdHubTransHostInv2010ServerStatisticsLogPath OBJECT-TYPE
       SYNTAX      SnmpAdminString
       ACCESS      read-only
       STATUS      mandatory
       DESCRIPTION
          " location of server statistics log storage"
       ::= { exchAdHubTransHostInventory2010Entry 2 }

--**************************************************************************
--**************************************************************************
-- 
-- Performance Variables
--
--**************************************************************************
--**************************************************************************


--**************************************************************************  
--
-- Performance Variables: Host
--
--**************************************************************************

--**************************************************************************  
--
-- exchAdHostLogicalDiskTable
--
--**************************************************************************

   exchAdHostLogicalDiskTable OBJECT-TYPE
       SYNTAX      SEQUENCE OF ExchAdHostLogicalDiskEntry
       ACCESS      not-accessible
       STATUS      mandatory
       DESCRIPTION
           "logical disk variable table"
      ::= { exchAdPerformanceHost 1 }

    exchAdHostLogicalDiskEntry OBJECT-TYPE
       SYNTAX      ExchAdHostLogicalDiskEntry
       ACCESS      not-accessible
       STATUS      mandatory
       DESCRIPTION
           "defines an entry in the exchAdHostLogicalDiskTable"

       INDEX {
                exchAdHostLogicalDiskHostIndex,
                exchAdHostLogicalDiskIndex
             }
       ::= { exchAdHostLogicalDiskTable 1 }

   ExchAdHostLogicalDiskEntry ::=
       SEQUENCE {
           exchAdHostLogicalDiskHostIndex               INTEGER,
           exchAdHostLogicalDiskIndex                   INTEGER,
           exchAdHostLogicalDiskId                      SnmpAdminString,
           exchAdHostLogicalDiskAvgDiskmSecPerTransfer  Gauge,
           exchAdHostLogicalDiskAvgDiskmSecPerWrite     Gauge,
           exchAdHostLogicalDiskAvgDiskmSecPerRead      Gauge
       }



   exchAdHostLogicalDiskHostIndex OBJECT-TYPE
       SYNTAX      INTEGER (0..2147483647)
       ACCESS      read-only
       STATUS      mandatory
       DESCRIPTION
          "unique index for each host, same as exchAdUniversalHostIndex"
       ::= { exchAdHostLogicalDiskEntry 1 }

   exchAdHostLogicalDiskIndex OBJECT-TYPE
       SYNTAX      INTEGER (0..2147483647)
       ACCESS      read-only
       STATUS      mandatory
       DESCRIPTION
          "unique index for each logical disk on the host"
       ::= { exchAdHostLogicalDiskEntry 2 }

   exchAdHostLogicalDiskId OBJECT-TYPE
       SYNTAX     SnmpAdminString
       ACCESS      read-only
       STATUS      mandatory
       DESCRIPTION
          "unique identifier for each logical disk on the host"
       ::= { exchAdHostLogicalDiskEntry 3 }

   exchAdHostLogicalDiskAvgDiskmSecPerTransfer OBJECT-TYPE
       SYNTAX      Gauge
       ACCESS      read-only
       STATUS      mandatory
       DESCRIPTION
          "average time per logical disk transfer in milliseconds"
       ::= { exchAdHostLogicalDiskEntry 4 }


   exchAdHostLogicalDiskAvgDiskmSecPerWrite OBJECT-TYPE
       SYNTAX      Gauge
       ACCESS      read-only
       STATUS      mandatory
       DESCRIPTION
          "average time per logical disk write in milliseconds"
       ::= { exchAdHostLogicalDiskEntry 5 }


   exchAdHostLogicalDiskAvgDiskmSecPerRead OBJECT-TYPE
       SYNTAX      Gauge
       ACCESS      read-only
       STATUS      mandatory
       DESCRIPTION
          "average time per logical disk read in milliseconds"
       ::= { exchAdHostLogicalDiskEntry 6 }

--**************************************************************************  
--
-- exchAdHostPhysicalDiskTable
--
--**************************************************************************

   exchAdHostPhysicalDiskTable OBJECT-TYPE
       SYNTAX      SEQUENCE OF ExchAdHostPhysicalDiskEntry
       ACCESS      not-accessible
       STATUS      mandatory
       DESCRIPTION
           "physical disk variable table"
      ::= { exchAdPerformanceHost 2 }

    exchAdHostPhysicalDiskEntry OBJECT-TYPE
       SYNTAX      ExchAdHostPhysicalDiskEntry
       ACCESS      not-accessible
       STATUS      mandatory
       DESCRIPTION
           "defines an entry in the exchAdHostPhysicalDiskTable"

       INDEX {
                exchAdHostPhysicalDiskHostIndex,
                exchAdHostPhysicalDiskIndex
             }
       ::= { exchAdHostPhysicalDiskTable 1 }

   ExchAdHostPhysicalDiskEntry ::=
       SEQUENCE {
           exchAdHostPhysicalDiskHostIndex               INTEGER,
           exchAdHostPhysicalDiskIndex                   INTEGER,
           exchAdHostPhysicalDiskId                      SnmpAdminString,
           exchAdHostPhysicalDiskAvgDiskmSecPerTransfer  Gauge,
           exchAdHostPhysicalDiskAvgDiskmSecPerWrite     Gauge,
           exchAdHostPhysicalDiskAvgDiskmSecPerRead      Gauge
       }

   exchAdHostPhysicalDiskHostIndex OBJECT-TYPE
       SYNTAX      INTEGER (0..2147483647)
       ACCESS      read-only
       STATUS      mandatory
       DESCRIPTION
          "unique index for each host, same as exchAdUniversalHostIndex"
       ::= { exchAdHostPhysicalDiskEntry 1 }

   exchAdHostPhysicalDiskIndex OBJECT-TYPE
       SYNTAX      INTEGER (0..2147483647)
       ACCESS      read-only
       STATUS      mandatory
       DESCRIPTION
          "unique index for each physical disk on the host"
       ::= { exchAdHostPhysicalDiskEntry 2 }

   exchAdHostPhysicalDiskId OBJECT-TYPE
       SYNTAX     SnmpAdminString
       ACCESS      read-only
       STATUS      mandatory
       DESCRIPTION
          "unique identifier for each physical disk on the host"
       ::= { exchAdHostPhysicalDiskEntry 3 }    

   exchAdHostPhysicalDiskAvgDiskmSecPerTransfer OBJECT-TYPE
       SYNTAX      Gauge
       ACCESS      read-only
       STATUS      mandatory
       DESCRIPTION
          "average time per physical disk transfer in milliseconds"
       ::= { exchAdHostPhysicalDiskEntry 4 }  

   exchAdHostPhysicalDiskAvgDiskmSecPerWrite OBJECT-TYPE
       SYNTAX      Gauge
       ACCESS      read-only
       STATUS      mandatory
       DESCRIPTION
          "average time per physical disk write in milliseconds"
       ::= { exchAdHostPhysicalDiskEntry 5 }  

   exchAdHostPhysicalDiskAvgDiskmSecPerRead OBJECT-TYPE
       SYNTAX      Gauge
       ACCESS      read-only
       STATUS      mandatory
       DESCRIPTION
          "average time per physical disk read in milliseconds"
       ::= { exchAdHostPhysicalDiskEntry 6 }

--**************************************************************************  
--
-- exchAdHostProcessTable
--
--**************************************************************************

   exchAdHostProcessTable OBJECT-TYPE
       SYNTAX      SEQUENCE OF ExchAdHostProcessEntry
       ACCESS      not-accessible
       STATUS      mandatory
       DESCRIPTION
           "process variable table"
      ::= { exchAdPerformanceHost 3 }

    exchAdHostProcessEntry OBJECT-TYPE
       SYNTAX      ExchAdHostProcessEntry
       ACCESS      not-accessible
       STATUS      mandatory
       DESCRIPTION
           "defines an entry in the exchAdHostProcessTable"

       INDEX {
                exchAdHostProcessHostIndex,
                exchAdHostProcessIndex
             }
       ::= { exchAdHostProcessTable 1 }

   ExchAdHostProcessEntry ::=
       SEQUENCE {
           exchAdHostProcessHostIndex                   INTEGER,
           exchAdHostProcessIndex                       INTEGER,
           exchAdHostProcessId                          INTEGER,
           exchAdHostProcessProcTimePct                 Gauge,
           exchAdHostProcessName                        SnmpAdminString
       }

   exchAdHostProcessHostIndex OBJECT-TYPE
       SYNTAX      INTEGER (0..2147483647)
       ACCESS      read-only
       STATUS      mandatory
       DESCRIPTION
          "unique index for each host, same as exchAdUniversalHostIndex"
       ::= { exchAdHostProcessEntry 1 }

   exchAdHostProcessIndex OBJECT-TYPE
       SYNTAX      INTEGER (0..2147483647)
       ACCESS      read-only
       STATUS      mandatory
       DESCRIPTION
          "unique index for each process on the host"
       ::= { exchAdHostProcessEntry 2 }

   exchAdHostProcessId OBJECT-TYPE
       SYNTAX      INTEGER (0..2147483647)
       ACCESS      read-only
       STATUS      mandatory
       DESCRIPTION
          "process ID for each process on the host"
       ::= { exchAdHostProcessEntry 3 }                                         

   exchAdHostProcessProcTimePct OBJECT-TYPE
       SYNTAX      Gauge
       ACCESS      read-only
       STATUS      mandatory
       DESCRIPTION
          "process processor utilization in percent"
       ::= { exchAdHostProcessEntry 4 } 

   exchAdHostProcessName OBJECT-TYPE
       SYNTAX     SnmpAdminString
       ACCESS      read-only
       STATUS      mandatory
       DESCRIPTION
          "process name for each process on the host"
       ::= { exchAdHostProcessEntry 5 }                                         

--**************************************************************************  
--
-- Performance Variables: Active Directory
--
--**************************************************************************

--**************************************************************************  
--
-- exchAdAdNtdsPerformanceTable
--
--**************************************************************************

   exchAdAdNtdsPerformanceTable  OBJECT-TYPE
       SYNTAX      SEQUENCE OF ExchAdAdNtdsPerformanceEntry
       ACCESS      not-accessible
       STATUS      mandatory
       DESCRIPTION
           "active directory NTDS performance table"
      ::= { exchAdPerformanceActiveDirectory 1 }

    exchAdAdNtdsPerformanceEntry OBJECT-TYPE
       SYNTAX      ExchAdAdNtdsPerformanceEntry
       ACCESS      not-accessible
       STATUS      mandatory
       DESCRIPTION
           "defines an entry in the exchAdAdNtdsPerformanceTable"

       INDEX {
                exchAdAdNtdsHostIndex
             }
       ::= { exchAdAdNtdsPerformanceTable 1 }

    ExchAdAdNtdsPerformanceEntry ::=
       SEQUENCE {
           exchAdAdNtdsHostIndex                        INTEGER,
           exchAdAdNtdsDraInboundObjUpdRemaining        Gauge,
           exchAdAdNtdsDraOutboundBytesPerSec           Gauge,
           exchAdAdNtdsThreexchAds                      Gauge,
           exchAdAdNtdsKerberosAuthenticationsPerSec    Gauge,
           exchAdAdNtdsLdapClientSessions               Gauge,
           exchAdAdNtdsLdapSearchesPerSec               Gauge,
           exchAdAdNtdsLdapSuccessfulBindsPerSec        Gauge,
           exchAdAdNtdsNtlmAuthenticationsPerSec        Gauge,
           exchAdAdNtdsSyncRequests                     Counter,
           exchAdAdNtdsPendingSync                      Gauge
       }

   exchAdAdNtdsHostIndex OBJECT-TYPE
       SYNTAX      INTEGER (0..2147483647)
       ACCESS      read-only
       STATUS      mandatory
       DESCRIPTION
          "unique index for each host, same as exchAdUniversalHostIndex"
       ::= { exchAdAdNtdsPerformanceEntry 1 }

   exchAdAdNtdsDraInboundObjUpdRemaining OBJECT-TYPE
       SYNTAX      Gauge
       ACCESS      read-only
       STATUS      mandatory
       DESCRIPTION
          "NTDS DRA Inbound object updates remaining in packet"
       ::= { exchAdAdNtdsPerformanceEntry 2 }

   exchAdAdNtdsDraOutboundBytesPerSec OBJECT-TYPE
       SYNTAX      Gauge
       ACCESS      read-only
       STATUS      mandatory
       DESCRIPTION
          "NTDS DRA outbound bytes total per second"
       ::= { exchAdAdNtdsPerformanceEntry 3 }

   exchAdAdNtdsThreexchAds OBJECT-TYPE
       SYNTAX      Gauge
       ACCESS      read-only
       STATUS      mandatory
       DESCRIPTION
          "NTDS threads in use"
       ::= { exchAdAdNtdsPerformanceEntry 4 }

   exchAdAdNtdsKerberosAuthenticationsPerSec OBJECT-TYPE
       SYNTAX      Gauge
       ACCESS      read-only
       STATUS      mandatory
       DESCRIPTION
          "NTDS Kerberos authentications per second"
       ::= { exchAdAdNtdsPerformanceEntry 5 }

   exchAdAdNtdsLdapClientSessions OBJECT-TYPE
       SYNTAX      Gauge
       ACCESS      read-only
       STATUS      mandatory
       DESCRIPTION
          "NTDS LDAP client sessions"
       ::= { exchAdAdNtdsPerformanceEntry 6 }

   exchAdAdNtdsLdapSearchesPerSec OBJECT-TYPE
       SYNTAX      Gauge
       ACCESS      read-only
       STATUS      mandatory
       DESCRIPTION
          "NTDS LDAP searches per second"
       ::= { exchAdAdNtdsPerformanceEntry 7 }

   exchAdAdNtdsLdapSuccessfulBindsPerSec OBJECT-TYPE
       SYNTAX      Gauge
       ACCESS      read-only
       STATUS      mandatory
       DESCRIPTION
          "NDTS LDAP successful binds per second"
       ::= { exchAdAdNtdsPerformanceEntry 8 }

   exchAdAdNtdsNtlmAuthenticationsPerSec OBJECT-TYPE
       SYNTAX      Gauge
       ACCESS      read-only
       STATUS      mandatory
       DESCRIPTION
          "NTDS NTLM authentications per second"
       ::= { exchAdAdNtdsPerformanceEntry 9 }

   exchAdAdNtdsSyncRequests OBJECT-TYPE
       SYNTAX      Counter
       ACCESS      read-only
       STATUS      mandatory
       DESCRIPTION
          "NTDS synchronization requests"
       ::= { exchAdAdNtdsPerformanceEntry 10 }

   exchAdAdNtdsPendingSync OBJECT-TYPE
       SYNTAX      Gauge
       ACCESS      read-only
       STATUS      mandatory
       DESCRIPTION
          "NTDS pending replication synchronizations"
       ::= { exchAdAdNtdsPerformanceEntry 11 }

--**************************************************************************  
--
-- exchAdAdFileReplicationPerformanceTable
--
--**************************************************************************

   exchAdAdFileReplicationPerformanceTable OBJECT-TYPE
       SYNTAX      SEQUENCE OF ExchAdAdFileReplicationPerformanceEntry
       ACCESS      not-accessible
       STATUS      mandatory
       DESCRIPTION
           "active directory file replication performance table"
      ::= { exchAdPerformanceActiveDirectory 2 }

    exchAdAdFileReplicationPerformanceEntry OBJECT-TYPE
       SYNTAX      ExchAdAdFileReplicationPerformanceEntry
       ACCESS      not-accessible
       STATUS      mandatory
       DESCRIPTION
           "defines an entry in the exchAdAdFileReplicationPerformanceTable"

       INDEX {
                exchAdAdFileReplicationHostIndex
             }
       ::= { exchAdAdFileReplicationPerformanceTable 1 }

    ExchAdAdFileReplicationPerformanceEntry ::=
       SEQUENCE {
           exchAdAdFileReplicationHostIndex             INTEGER,
           exchAdAdFileReplicationPendingSynch          Gauge,
           exchAdAdFileReplicationStagingSpaceFree      Gauge,
           exchAdAdFileReplicationStagingSpaceInUse     Gauge
       }

   exchAdAdFileReplicationHostIndex OBJECT-TYPE
       SYNTAX      INTEGER (0..2147483647)
       ACCESS      read-only
       STATUS      mandatory
       DESCRIPTION
          "unique index for each host, same as exchAdUniversalHostIndex"
       ::= { exchAdAdFileReplicationPerformanceEntry 1 }

   exchAdAdFileReplicationPendingSynch OBJECT-TYPE
       SYNTAX      Gauge
       ACCESS      read-only
       STATUS      obsolete
       DESCRIPTION
          "NTDS pending replication synchronizations - this object is obsolete"
       ::= { exchAdAdFileReplicationPerformanceEntry 2 }

   exchAdAdFileReplicationStagingSpaceFree OBJECT-TYPE
       SYNTAX      Gauge
       ACCESS      read-only
       STATUS      obsolete
       DESCRIPTION
          "file replication space free in the staging directory in KB - this object is obsolete"
       ::= { exchAdAdFileReplicationPerformanceEntry 3 }

   exchAdAdFileReplicationStagingSpaceInUse OBJECT-TYPE
       SYNTAX      Gauge
       ACCESS      read-only
       STATUS      mandatory
       DESCRIPTION
          "file replication space used in the staging directory in bytes"
       ::= { exchAdAdFileReplicationPerformanceEntry 4 }


--**************************************************************************  
--
-- Performance Variables: Mailbox Role
--
--**************************************************************************

--**************************************************************************  
--
-- exchAdMailboxGeneralPerformanceTable
--
--**************************************************************************

   exchAdMailboxGeneralPerformanceTable OBJECT-TYPE
       SYNTAX      SEQUENCE OF ExchAdMailboxGeneralPerformanceEntry
       ACCESS      not-accessible
       STATUS      mandatory
       DESCRIPTION
           "mailbox general performance table"
      ::= { exchAdPerformanceMailboxRole 1 }

    exchAdMailboxGeneralPerformanceEntry OBJECT-TYPE
       SYNTAX      ExchAdMailboxGeneralPerformanceEntry
       ACCESS      not-accessible
       STATUS      mandatory
       DESCRIPTION
           "defines an entry in the exchAdMailboxGeneralPerformanceTable"

       INDEX {
                exchAdMailboxGenHostIndex
             }
       ::= { exchAdMailboxGeneralPerformanceTable 1 }

    ExchAdMailboxGeneralPerformanceEntry ::=
       SEQUENCE {
           exchAdMailboxGenHostIndex                          INTEGER,
           exchAdMailboxGenDatabasePageFaultStallsPerHour     Gauge,
           exchAdMailboxGenDatabaseLogRecordStallsPerSec      Gauge,
           exchAdMailboxGenDatabaseLogThreadsWaiting          Gauge,
           exchAdMailboxGenCalendarAttAvgCalAttProcTime       Gauge,
           exchAdMailboxGenCalendarAttRequestsFailed          Counter,
           exchAdMailboxGenDatabaseReadsAttachedAvgLatency    Gauge,
           exchAdMailboxGenDatabaseReadsRecoveryAvgLatency    Gauge,
           exchAdMailboxGenDatabaseWritesAttachedAvgLatency   Gauge,
           exchAdMailboxGenDatabaseWritesRecoveryAvgLatency   Gauge,
           exchAdMailboxGenDatabaseLogReadsAvgLatency         Gauge,
           exchAdMailboxGenDatabaseLogWritesAvgLatency        Gauge,
           exchAdMailboxGenDatabaseLogBytesWritePerSec        Gauge,
           exchAdMailboxGenResourceBookingAvgEventProcTime    Gauge,
           exchAdMailboxGenResourceBookingRequestsFailed      Counter,
           exchAdMailboxGenIsMbxTotMsgsDeliveredPerSec        Gauge,
           exchAdMailboxGenIsMbxTotMsgQueued                  Gauge,
           exchAdMailboxGenIsMbxTotSentPerSec                 Gauge,
           exchAdMailboxGenIsMbxTotSubmittedPerSec            Gauge,
           exchAdMailboxGenIsMbxAvgLatency                    Gauge,
           exchAdMailboxGenIsPublicTotMsgQueued               Gauge,
           exchAdMailboxGenIsPublicTotReplRcvQueueSize        Gauge,
           exchAdMailboxGenIsClientTotRpcFailSTB              Counter,
           exchAdMailboxGenIsRpcAvgLatency                    Gauge,
           exchAdMailboxGenIsRpcClientBackoffsPerSec          Gauge,
           exchAdMailboxGenIsRpcSlowPackets                   Gauge,
           exchAdMailboxGenIsRpcOperationsPerSec              Gauge,
           exchAdMailboxGenIsRpcCurrentRequests               Gauge,
           exchAdMailboxGenIsCurrentSlowQpThreads             Gauge,
           exchAdMailboxGenIsCurrentSlowSearchThreads         Gauge,
           exchAdMailboxGenIsCurrentUsers                     Gauge,
           exchAdMailboxGenStoreIntTotRpcAvgLatency           Gauge,
           exchAdMailboxGenStoreIntTotRpcOutst                Gauge
       }

   exchAdMailboxGenHostIndex OBJECT-TYPE
       SYNTAX      INTEGER (0..2147483647)
       ACCESS      read-only
       STATUS      mandatory
       DESCRIPTION
          "unique index for each host, same as exchAdUniversalHostIndex"
       ::= { exchAdMailboxGeneralPerformanceEntry 1 }

   exchAdMailboxGenDatabasePageFaultStallsPerHour OBJECT-TYPE
       SYNTAX      Gauge
       ACCESS      read-only
       STATUS      mandatory
       DESCRIPTION
          "database page fault stalls per hour, no pages available"
       ::= { exchAdMailboxGeneralPerformanceEntry 2 }

   exchAdMailboxGenDatabaseLogRecordStallsPerSec OBJECT-TYPE
       SYNTAX      Gauge
       ACCESS      read-only
       STATUS      mandatory
       DESCRIPTION
          "database log record stalls per second, full buffers"
       ::= { exchAdMailboxGeneralPerformanceEntry 3 }

   exchAdMailboxGenDatabaseLogThreadsWaiting OBJECT-TYPE
       SYNTAX      Gauge
       ACCESS      read-only
       STATUS      mandatory
       DESCRIPTION
          "database log threads waiting for data writes"
       ::= { exchAdMailboxGeneralPerformanceEntry 4 }

   exchAdMailboxGenCalendarAttAvgCalAttProcTime OBJECT-TYPE
       SYNTAX      Gauge
       ACCESS      read-only
       STATUS      mandatory
       DESCRIPTION
          "average Calendar Attendant event processing time in milliseconds"
       ::= { exchAdMailboxGeneralPerformanceEntry 5 }

   exchAdMailboxGenCalendarAttRequestsFailed OBJECT-TYPE
       SYNTAX      Counter
       ACCESS      read-only
       STATUS      mandatory
       DESCRIPTION
          "Calendar Attendant request failures"
       ::= { exchAdMailboxGeneralPerformanceEntry 6 }

   exchAdMailboxGenDatabaseReadsAttachedAvgLatency OBJECT-TYPE
       SYNTAX      Gauge
       ACCESS      read-only
       STATUS      mandatory
       DESCRIPTION
          "database reads attached, average latency in milliseconds"
       ::= { exchAdMailboxGeneralPerformanceEntry 7 }

   exchAdMailboxGenDatabaseReadsRecoveryAvgLatency OBJECT-TYPE
       SYNTAX      Gauge
       ACCESS      read-only
       STATUS      mandatory
       DESCRIPTION
          "database reads recovery, average latency in milliseconds"
       ::= { exchAdMailboxGeneralPerformanceEntry 8 }

   exchAdMailboxGenDatabaseWritesAttachedAvgLatency OBJECT-TYPE
       SYNTAX      Gauge
       ACCESS      read-only
       STATUS      mandatory
       DESCRIPTION
          "database writes attached, average latency in milliseconds"
       ::= { exchAdMailboxGeneralPerformanceEntry 9 }

   exchAdMailboxGenDatabaseWritesRecoveryAvgLatency OBJECT-TYPE
       SYNTAX      Gauge
       ACCESS      read-only
       STATUS      mandatory
       DESCRIPTION
          "database writes recovery, average latency in milliseconds"
       ::= { exchAdMailboxGeneralPerformanceEntry 10 }

   exchAdMailboxGenDatabaseLogReadsAvgLatency OBJECT-TYPE
       SYNTAX      Gauge
       ACCESS      read-only
       STATUS      mandatory
       DESCRIPTION
          "database log  reads, average latency in milliseconds"
       ::= { exchAdMailboxGeneralPerformanceEntry 11 }

   exchAdMailboxGenDatabaseLogWritesAvgLatency OBJECT-TYPE
       SYNTAX      Gauge
       ACCESS      read-only
       STATUS      mandatory
       DESCRIPTION
          "database log  writes, average latency in milliseconds"
       ::= { exchAdMailboxGeneralPerformanceEntry 12 }

   exchAdMailboxGenDatabaseLogBytesWritePerSec OBJECT-TYPE
       SYNTAX      Gauge
       ACCESS      read-only
       STATUS      mandatory
       DESCRIPTION
          "database log bytes written per second"
       ::= { exchAdMailboxGeneralPerformanceEntry 13 }

   exchAdMailboxGenResourceBookingAvgEventProcTime OBJECT-TYPE
       SYNTAX      Gauge
       ACCESS      read-only
       STATUS      mandatory
       DESCRIPTION
          "resource booking attendant average event processing time in milliseconds"
       ::= { exchAdMailboxGeneralPerformanceEntry 14 }

   exchAdMailboxGenResourceBookingRequestsFailed OBJECT-TYPE
       SYNTAX      Counter
       ACCESS      read-only
       STATUS      mandatory
       DESCRIPTION
          "resource booking request failures"
       ::= { exchAdMailboxGeneralPerformanceEntry 15 }

   exchAdMailboxGenIsMbxTotMsgsDeliveredPerSec OBJECT-TYPE
       SYNTAX      Gauge
       ACCESS      read-only
       STATUS      mandatory
       DESCRIPTION
          "total Mailbox Messages delivered per second"
       ::= { exchAdMailboxGeneralPerformanceEntry 16 }

   exchAdMailboxGenIsMbxTotMsgQueued OBJECT-TYPE
       SYNTAX      Gauge
       ACCESS      read-only
       STATUS      mandatory
       DESCRIPTION
          "total submitted Mailbox messages queued by transport"
       ::= { exchAdMailboxGeneralPerformanceEntry 17 }

   exchAdMailboxGenIsMbxTotSentPerSec OBJECT-TYPE
       SYNTAX      Gauge
       ACCESS      read-only
       STATUS      mandatory
       DESCRIPTION
          "total Mailbox Messages sent to transport per second"
       ::= { exchAdMailboxGeneralPerformanceEntry 18 }

   exchAdMailboxGenIsMbxTotSubmittedPerSec OBJECT-TYPE
       SYNTAX      Gauge
       ACCESS      read-only
       STATUS      mandatory
       DESCRIPTION
          "total Mailbox messages submitted by clients per second"
       ::= { exchAdMailboxGeneralPerformanceEntry 19 }

   exchAdMailboxGenIsMbxAvgLatency OBJECT-TYPE
       SYNTAX      Gauge
       ACCESS      read-only
       STATUS      mandatory
       DESCRIPTION
          "average Mailbox RPC latency over last 1024 packets in milliseconds"
       ::= { exchAdMailboxGeneralPerformanceEntry 20 }

   exchAdMailboxGenIsPublicTotMsgQueued OBJECT-TYPE
       SYNTAX      Gauge
       ACCESS      read-only
       STATUS      mandatory
       DESCRIPTION
          "total submitted Public messages queued"
       ::= { exchAdMailboxGeneralPerformanceEntry 21 }

   exchAdMailboxGenIsPublicTotReplRcvQueueSize OBJECT-TYPE
       SYNTAX      Gauge
       ACCESS      read-only
       STATUS      mandatory
       DESCRIPTION
          "total Public replication messages queued"
       ::= { exchAdMailboxGeneralPerformanceEntry 22 }

   exchAdMailboxGenIsClientTotRpcFailSTB OBJECT-TYPE
       SYNTAX      Counter
       ACCESS      read-only
       STATUS      mandatory
       DESCRIPTION
          "total client failed RPCs due to Server Too Busy ROC error"
       ::= { exchAdMailboxGeneralPerformanceEntry 23 }

   exchAdMailboxGenIsRpcAvgLatency OBJECT-TYPE
       SYNTAX      Gauge
       ACCESS      read-only
       STATUS      mandatory
       DESCRIPTION
          "average RPC latency over last 1024 packets in milliseconds"
       ::= { exchAdMailboxGeneralPerformanceEntry 24 }

   exchAdMailboxGenIsRpcClientBackoffsPerSec OBJECT-TYPE
       SYNTAX      Gauge
       ACCESS      read-only
       STATUS      mandatory
       DESCRIPTION
          "RPC client backoffs per second"
       ::= { exchAdMailboxGeneralPerformanceEntry 25 }

   exchAdMailboxGenIsRpcSlowPackets OBJECT-TYPE
       SYNTAX      Gauge
       ACCESS      read-only
       STATUS      mandatory
       DESCRIPTION
          "slow RPC packets count, i.e., packets in past 1024 with latencies longer than 2 seconds"
       ::= { exchAdMailboxGeneralPerformanceEntry 26 }

   exchAdMailboxGenIsRpcOperationsPerSec OBJECT-TYPE
       SYNTAX      Gauge
       ACCESS      read-only
       STATUS      mandatory
       DESCRIPTION
          "RPC operations per second"
       ::= { exchAdMailboxGeneralPerformanceEntry 27 }

   exchAdMailboxGenIsRpcCurrentRequests OBJECT-TYPE
       SYNTAX      Gauge
       ACCESS      read-only
       STATUS      mandatory
       DESCRIPTION
          "RPC requests currently executing  in information store process"
       ::= { exchAdMailboxGeneralPerformanceEntry 28 }

   exchAdMailboxGenIsCurrentSlowQpThreads OBJECT-TYPE
       SYNTAX      Gauge
       ACCESS      read-only
       STATUS      mandatory
       DESCRIPTION
          "current slow query processor threads"
       ::= { exchAdMailboxGeneralPerformanceEntry 29 }

   exchAdMailboxGenIsCurrentSlowSearchThreads OBJECT-TYPE
       SYNTAX      Gauge
       ACCESS      read-only
       STATUS      mandatory
       DESCRIPTION
          "current slow search threads"
       ::= { exchAdMailboxGeneralPerformanceEntry 30 }

   exchAdMailboxGenIsCurrentUsers OBJECT-TYPE
       SYNTAX      Gauge
       ACCESS      read-only
       STATUS      mandatory
       DESCRIPTION
          "users connected to information store"
       ::= { exchAdMailboxGeneralPerformanceEntry 31 }

   exchAdMailboxGenStoreIntTotRpcAvgLatency OBJECT-TYPE
       SYNTAX      Gauge
       ACCESS      read-only
       STATUS      mandatory
       DESCRIPTION
          "average latency of all RPC requests in milliseconds"
       ::= { exchAdMailboxGeneralPerformanceEntry 32 }

   exchAdMailboxGenStoreIntTotRpcOutst OBJECT-TYPE
       SYNTAX      Gauge
       ACCESS      read-only
       STATUS      mandatory
       DESCRIPTION
          "total outstanding RPC requests"
       ::= { exchAdMailboxGeneralPerformanceEntry 33 }

--**************************************************************************  
--
-- exchAdMailboxAdAccessCacheTable
--
--**************************************************************************

   exchAdMailboxAdAccessCacheTable OBJECT-TYPE
       SYNTAX      SEQUENCE OF ExchAdMailboxAdAccessCacheEntry
       ACCESS      not-accessible
       STATUS      mandatory
       DESCRIPTION
           "mailbox Active Directory access cache table"
      ::= { exchAdPerformanceMailboxRole 2 }

    exchAdMailboxAdAccessCacheEntry OBJECT-TYPE
       SYNTAX      ExchAdMailboxAdAccessCacheEntry
       ACCESS      not-accessible
       STATUS      mandatory
       DESCRIPTION
           "defines an entry in the exchAdMailboxAdAccessCacheTable"

       INDEX {
                exchAdMailboxAdAccessCacheHostIndex,
                exchAdMailboxAdAccessCacheIndex
             }
       ::= { exchAdMailboxAdAccessCacheTable 1 }

    ExchAdMailboxAdAccessCacheEntry ::=
       SEQUENCE {
           exchAdMailboxAdAccessCacheHostIndex             INTEGER,
           exchAdMailboxAdAccessCacheIndex                 INTEGER,
           exchAdMailboxAdAccessCacheId                    SnmpAdminString,
           exchAdMailboxAdAccessCacheLdapSearchRequests    Counter
       }

   exchAdMailboxAdAccessCacheHostIndex OBJECT-TYPE
       SYNTAX      INTEGER (0..2147483647)
       ACCESS      read-only
       STATUS      mandatory
       DESCRIPTION
          "unique index for each host, same as exchAdUniversalHostIndex"
       ::= { exchAdMailboxAdAccessCacheEntry 1 }

   exchAdMailboxAdAccessCacheIndex OBJECT-TYPE
       SYNTAX      INTEGER (0..2147483647)
       ACCESS      read-only
       STATUS      mandatory
       DESCRIPTION
          "unique index for each access cache on the host"
       ::= { exchAdMailboxAdAccessCacheEntry 2 }

   exchAdMailboxAdAccessCacheId OBJECT-TYPE
       SYNTAX      SnmpAdminString
       ACCESS      read-only
       STATUS      mandatory
       DESCRIPTION
          "unique identifier for each cache"
       ::= { exchAdMailboxAdAccessCacheEntry 3 }

   exchAdMailboxAdAccessCacheLdapSearchRequests OBJECT-TYPE
       SYNTAX      Counter
       ACCESS      read-only
       STATUS      mandatory
       DESCRIPTION
          "AD Access Cache LDAP search requests"
       ::= { exchAdMailboxAdAccessCacheEntry 4 }

--**************************************************************************  
--
-- exchAdMailboxAdAccDomainControllerTable
--
--**************************************************************************

    exchAdMailboxAdAccDomainControllerTable OBJECT-TYPE
       SYNTAX      SEQUENCE OF ExchAdMailboxAdAccDomainControllerEntry
       ACCESS      not-accessible
       STATUS      mandatory
       DESCRIPTION
           "mailbox AD Access Domain Controller table"
      ::= { exchAdPerformanceMailboxRole 3 }

    exchAdMailboxAdAccDomainControllerEntry OBJECT-TYPE
       SYNTAX      ExchAdMailboxAdAccDomainControllerEntry
       ACCESS      not-accessible
       STATUS      mandatory
       DESCRIPTION
           "defines an entry in the exchAdMailboxAdAccDomainControllerTable"

       INDEX {
                exchAdMailboxAdAccDomainControllerIndex
             }
       ::= { exchAdMailboxAdAccDomainControllerTable 1 }

    ExchAdMailboxAdAccDomainControllerEntry ::=
       SEQUENCE {
           exchAdMailboxAdAccDomainControllerIndex                       INTEGER,
           exchAdMailboxAdAccDomainControllerId                          SnmpAdminString,
           exchAdMailboxAdAccDomainControllerLdapReadTime                Gauge,
           exchAdMailboxAdAccDomainControllerLdapSearchTime              Gauge,
           exchAdMailboxAdAccDomainControllerLdapSearchTimeoutsPerMinute Gauge,
           exchAdMailboxAdAccDomainControllerLdapThreshViolPerMinute     Gauge
       }
   exchAdMailboxAdAccDomainControllerIndex OBJECT-TYPE
       SYNTAX      INTEGER (0..2147483647)
       ACCESS      read-only
       STATUS      mandatory
       DESCRIPTION
          "unique index for each mailbox host, same as exchAdUniversalHostIndex"
       ::= { exchAdMailboxAdAccDomainControllerEntry 1 }

   exchAdMailboxAdAccDomainControllerId OBJECT-TYPE
       SYNTAX      SnmpAdminString
       ACCESS      read-only
       STATUS      mandatory
       DESCRIPTION
          "unique identifier for each domain controller"
       ::= { exchAdMailboxAdAccDomainControllerEntry 2 }

   exchAdMailboxAdAccDomainControllerLdapReadTime OBJECT-TYPE
       SYNTAX      Gauge
       ACCESS      read-only
       STATUS      mandatory
       DESCRIPTION
          "AD Access Domain Controller LDAP read time in milliseconds"
       ::= { exchAdMailboxAdAccDomainControllerEntry 3 }

   exchAdMailboxAdAccDomainControllerLdapSearchTime OBJECT-TYPE
       SYNTAX      Gauge
       ACCESS      read-only
       STATUS      mandatory
       DESCRIPTION
          "AD Access Domain Controller LDAP search time in milliseconds"
       ::= { exchAdMailboxAdAccDomainControllerEntry 4 }

   exchAdMailboxAdAccDomainControllerLdapSearchTimeoutsPerMinute OBJECT-TYPE
       SYNTAX      Gauge
       ACCESS      read-only
       STATUS      mandatory
       DESCRIPTION
          "AD Access Domain Controller LDAP search timeouts per minute"
       ::= { exchAdMailboxAdAccDomainControllerEntry 5 }

   exchAdMailboxAdAccDomainControllerLdapThreshViolPerMinute OBJECT-TYPE
       SYNTAX      Gauge
       ACCESS      read-only
       STATUS      mandatory
       DESCRIPTION
          "AD Access Domain Controller LDAP threshold violations per minute"
       ::= { exchAdMailboxAdAccDomainControllerEntry 6 }

--**************************************************************************  
--
-- exchAdMailboxAdAccessProcessTable
--
--**************************************************************************

   exchAdMailboxAdAccessProcessTable OBJECT-TYPE
       SYNTAX      SEQUENCE OF ExchAdMailboxAdAccessProcessEntry
       ACCESS      not-accessible
       STATUS      mandatory
       DESCRIPTION
           "mailbox AD Access Process table"
      ::= { exchAdPerformanceMailboxRole 4 }

   exchAdMailboxAdAccessProcessEntry OBJECT-TYPE
       SYNTAX      ExchAdMailboxAdAccessProcessEntry
       ACCESS      not-accessible
       STATUS      mandatory
       DESCRIPTION
           "defines an entry in the exchAdMailboxAdAccessProcessTable"

       INDEX {
                exchAdMailboxAdAccessProcessHostIndex,
                exchAdMailboxAdAccessProcessIndex
             }
       ::= { exchAdMailboxAdAccessProcessTable 1 }

    ExchAdMailboxAdAccessProcessEntry ::=
       SEQUENCE {
           exchAdMailboxAdAccessProcessHostIndex         INTEGER,
           exchAdMailboxAdAccessProcessIndex             INTEGER,
           exchAdMailboxAdAccessProcessId                SnmpAdminString,
           exchAdMailboxAdAccessProcessLdapReadTime      Gauge,
           exchAdMailboxAdAccessProcessLdapSearchTime    Gauge
                }

    exchAdMailboxAdAccessProcessHostIndex OBJECT-TYPE
       SYNTAX      INTEGER (0..2147483647)
       ACCESS      read-only
       STATUS      mandatory
       DESCRIPTION
          "unique index for each mailbox host, same as exchAdUniversalHostIndex"
       ::= { exchAdMailboxAdAccessProcessEntry 1 }

    exchAdMailboxAdAccessProcessIndex OBJECT-TYPE
       SYNTAX      INTEGER (0..2147483647)
       ACCESS      read-only
       STATUS      mandatory
       DESCRIPTION
          "unique index for each process on the host"
       ::= { exchAdMailboxAdAccessProcessEntry 2 }

    exchAdMailboxAdAccessProcessId OBJECT-TYPE
       SYNTAX      SnmpAdminString
       ACCESS      read-only
       STATUS      mandatory
       DESCRIPTION
          "unique identifier for each process"
       ::= { exchAdMailboxAdAccessProcessEntry 3 }

    exchAdMailboxAdAccessProcessLdapReadTime OBJECT-TYPE
       SYNTAX      Gauge
       ACCESS      read-only
       STATUS      mandatory
       DESCRIPTION
          "AD Access Process LDAP read time in milliseconds"
       ::= { exchAdMailboxAdAccessProcessEntry 4 }

    exchAdMailboxAdAccessProcessLdapSearchTime OBJECT-TYPE
       SYNTAX      Gauge
       ACCESS      read-only
       STATUS      mandatory
       DESCRIPTION
          "AD Access Process LDAP search time in milliseconds"
       ::= { exchAdMailboxAdAccessProcessEntry 5 }

--**************************************************************************  
--
-- exchAdMailboxAssistTable
--
--**************************************************************************

   exchAdMailboxAssistTable OBJECT-TYPE
       SYNTAX      SEQUENCE OF ExchAdMailboxAssistEntry
       ACCESS      not-accessible
       STATUS      mandatory
       DESCRIPTION
           "mailbox assistant table"
      ::= { exchAdPerformanceMailboxRole 5 }

   exchAdMailboxAssistEntry OBJECT-TYPE
       SYNTAX      ExchAdMailboxAssistEntry
       ACCESS      not-accessible
       STATUS      mandatory
       DESCRIPTION
           "defines an entry in the exchAdMailboxAssistTable"

       INDEX {
                exchAdMailboxAssistHostIndex,
                exchAdMailboxAssistIndex
             }
       ::= { exchAdMailboxAssistTable 1 }

    ExchAdMailboxAssistEntry ::=
       SEQUENCE {
           exchAdMailboxAssistHostIndex                INTEGER,
           exchAdMailboxAssistIndex                    INTEGER,
           exchAdMailboxAssistId                       SnmpAdminString,
           exchAdMailboxAssistAvgEventProcTime         Gauge,
           exchAdMailboxAssistInMemoryEventQueueLength Gauge,
           exchAdMailboxAssistEventsPolled             Counter,
           exchAdMailboxAssistMailboxesProcessed       Counter
          }

    exchAdMailboxAssistHostIndex OBJECT-TYPE
       SYNTAX      INTEGER (0..2147483647)
       ACCESS      read-only
       STATUS      mandatory
       DESCRIPTION
          "unique index for each mailbox host, same as exchAdUniversalHostIndex"
       ::= { exchAdMailboxAssistEntry 1 }

    exchAdMailboxAssistIndex OBJECT-TYPE
       SYNTAX      INTEGER (0..2147483647)
       ACCESS      read-only
       STATUS      mandatory
       DESCRIPTION
          "unique index for each assistant on the host"
       ::= { exchAdMailboxAssistEntry 2 }

    exchAdMailboxAssistId OBJECT-TYPE
       SYNTAX      SnmpAdminString
       ACCESS      read-only
       STATUS      mandatory
       DESCRIPTION
          "unique identifier for each assistant"
       ::= { exchAdMailboxAssistEntry 3 }

    exchAdMailboxAssistAvgEventProcTime OBJECT-TYPE
       SYNTAX      Gauge
       ACCESS      read-only
       STATUS      mandatory
       DESCRIPTION
          "average assistant event processing time in seconds"
       ::= { exchAdMailboxAssistEntry 4 }

    exchAdMailboxAssistInMemoryEventQueueLength OBJECT-TYPE
       SYNTAX      Gauge
       ACCESS      read-only
       STATUS      mandatory
       DESCRIPTION
          "assistant In-memory event queue length"
       ::= { exchAdMailboxAssistEntry 5 }

    exchAdMailboxAssistEventsPolled OBJECT-TYPE
       SYNTAX      Counter
       ACCESS      read-only
       STATUS      mandatory
       DESCRIPTION
          "events polled by assistant"
       ::= { exchAdMailboxAssistEntry 6 }

    exchAdMailboxAssistMailboxesProcessed OBJECT-TYPE
       SYNTAX      Counter
       ACCESS      read-only
       STATUS      mandatory
       DESCRIPTION
          "mailboxes processed by assistant"
       ::= { exchAdMailboxAssistEntry 7 }

--**************************************************************************  
--
-- exchAdMailboxDatabaseInstTable
--
--**************************************************************************

   exchAdMailboxDatabaseInstTable OBJECT-TYPE
       SYNTAX      SEQUENCE OF ExchAdMailboxDatabaseInstEntry
       ACCESS      not-accessible
       STATUS      mandatory
       DESCRIPTION
           "database instance table"
      ::= { exchAdPerformanceMailboxRole 6 }

   exchAdMailboxDatabaseInstEntry OBJECT-TYPE
       SYNTAX      ExchAdMailboxDatabaseInstEntry
       ACCESS      not-accessible
       STATUS      mandatory
       DESCRIPTION
           "defines an entry in the exchAdMailboxDatabaseInstTable"

       INDEX {
                exchAdMailboxDatabaseInstHostIndex,
                exchAdMailboxDatabaseInstIndex
             }
       ::= { exchAdMailboxDatabaseInstTable 1 }

    ExchAdMailboxDatabaseInstEntry ::=
       SEQUENCE {
           exchAdMailboxDatabaseInstHostIndex        INTEGER,
           exchAdMailboxDatabaseInstIndex            INTEGER,
           exchAdMailboxDatabaseInstId               SnmpAdminString,
           exchAdMailboxDatabaseInstLogGenCkptDepth  Gauge,
           exchAdMailboxDatabaseInstReadAvgLatency   Gauge,
           exchAdMailboxDatabaseInstInventoryIndex   INTEGER,
           exchAdMailboxDatabaseInstWriteAvgLatency  Gauge
          }

    exchAdMailboxDatabaseInstHostIndex OBJECT-TYPE
       SYNTAX      INTEGER (0..2147483647)
       ACCESS      read-only
       STATUS      mandatory
       DESCRIPTION
          "unique index for each mailbox host, same as exchAdUniversalHostIndex"
       ::= { exchAdMailboxDatabaseInstEntry 1 }

    exchAdMailboxDatabaseInstIndex OBJECT-TYPE
       SYNTAX      INTEGER (0..2147483647)
       ACCESS      read-only
       STATUS      mandatory
       DESCRIPTION
          "unique index for each database instance on the host"
       ::= { exchAdMailboxDatabaseInstEntry 2 }

    exchAdMailboxDatabaseInstId OBJECT-TYPE
       SYNTAX      SnmpAdminString
       ACCESS      read-only
       STATUS      mandatory
       DESCRIPTION
          "unique identifier for each database instance"
       ::= { exchAdMailboxDatabaseInstEntry 3 }

    exchAdMailboxDatabaseInstLogGenCkptDepth OBJECT-TYPE
       SYNTAX      Gauge
       ACCESS      read-only
       STATUS      mandatory
       DESCRIPTION
          "database Log file generation checkpoint depth"
       ::= { exchAdMailboxDatabaseInstEntry 4 }

    exchAdMailboxDatabaseInstReadAvgLatency OBJECT-TYPE
       SYNTAX      Gauge
       ACCESS      read-only
       STATUS      mandatory
       DESCRIPTION
          "average Database read latency in milliseconds"
       ::= { exchAdMailboxDatabaseInstEntry 5 }

    exchAdMailboxDatabaseInstInventoryIndex OBJECT-TYPE
       SYNTAX      INTEGER
       ACCESS      read-only
       STATUS      obsolete
       DESCRIPTION
          "pointer to database in exchAdMailboxDatabaseInventoryTable - this object is obsolete"
       ::= { exchAdMailboxDatabaseInstEntry 6 }

    exchAdMailboxDatabaseInstWriteAvgLatency OBJECT-TYPE
       SYNTAX      Gauge
       ACCESS      read-only
       STATUS      mandatory
       DESCRIPTION
          "average Database write latency in milliseconds"
       ::= { exchAdMailboxDatabaseInstEntry 7 }

--**************************************************************************  
--
-- exchAdMailboxDatabaseTable
--
--**************************************************************************

   exchAdMailboxDatabaseTable OBJECT-TYPE
       SYNTAX      SEQUENCE OF ExchAdMailboxDatabaseEntry
       ACCESS      not-accessible
       STATUS      mandatory
       DESCRIPTION
           "database table"
      ::= { exchAdPerformanceMailboxRole 7 }

   exchAdMailboxDatabaseEntry OBJECT-TYPE
       SYNTAX      ExchAdMailboxDatabaseEntry
       ACCESS      not-accessible
       STATUS      mandatory
       DESCRIPTION
           "defines an entry in the exchAdMailboxDatabaseTable"

       INDEX {
                exchAdMailboxDatabaseHostIndex,
                exchAdMailboxDatabaseIndex
             }
       ::= { exchAdMailboxDatabaseTable 1 }

    ExchAdMailboxDatabaseEntry ::=
       SEQUENCE {
            exchAdMailboxDatabaseHostIndex            INTEGER,
            exchAdMailboxDatabaseIndex                INTEGER,
            exchAdMailboxDatabaseId                   SnmpAdminString,
            exchAdMailboxDatabaseCachHitsPct          Gauge,
            exchAdMailboxDatabaseCacheSize            Gauge,
            exchAdMailboxDatabasePageFaultStalls      Counter,
            exchAdMailboxDatabaseLogRecordStalls      Counter,
            exchAdMailboxDatabaseLogThreadsWaiting    Gauge,
            exchAdMailboxDatabaseVersionBucketsAlloc  Gauge,
            exchAdMailboxDatabaseInvIndex             INTEGER
          }

    exchAdMailboxDatabaseHostIndex OBJECT-TYPE
       SYNTAX      INTEGER (0..2147483647)
       ACCESS      read-only
       STATUS      mandatory
       DESCRIPTION
          "unique index for each mailbox host, same as exchAdUniversalHostIndex"
       ::= { exchAdMailboxDatabaseEntry 1 }

    exchAdMailboxDatabaseIndex OBJECT-TYPE
       SYNTAX      INTEGER (0..2147483647)
       ACCESS      read-only
       STATUS      mandatory
       DESCRIPTION
          "unique index for each database on the host"
       ::= { exchAdMailboxDatabaseEntry 2 }

    exchAdMailboxDatabaseId OBJECT-TYPE
       SYNTAX      SnmpAdminString
       ACCESS      read-only
       STATUS      mandatory
       DESCRIPTION
          "unique identifier for each database on the host"
       ::= { exchAdMailboxDatabaseEntry 3 }

    exchAdMailboxDatabaseCachHitsPct OBJECT-TYPE
       SYNTAX      Gauge
       ACCESS      read-only
       STATUS      mandatory
       DESCRIPTION
          "database cache hits percentage"
       ::= { exchAdMailboxDatabaseEntry 4 }

    exchAdMailboxDatabaseCacheSize OBJECT-TYPE
       SYNTAX      Gauge
       ACCESS      read-only
       STATUS      mandatory
       DESCRIPTION
          "database cache size in MB"
       ::= { exchAdMailboxDatabaseEntry 5 }

    exchAdMailboxDatabasePageFaultStalls OBJECT-TYPE
       SYNTAX      Counter
       ACCESS      read-only
       STATUS      mandatory
       DESCRIPTION
          "database page fault stalls, no pages available"
       ::= { exchAdMailboxDatabaseEntry 6 }

    exchAdMailboxDatabaseLogRecordStalls OBJECT-TYPE
       SYNTAX      Counter
       ACCESS      read-only
       STATUS      mandatory
       DESCRIPTION
          "database log record stalls due to full buffers"
       ::= { exchAdMailboxDatabaseEntry 7 }

    exchAdMailboxDatabaseLogThreadsWaiting OBJECT-TYPE
       SYNTAX      Gauge
       ACCESS      read-only
       STATUS      mandatory
       DESCRIPTION
          "database log threads waiting for data writes"
       ::= { exchAdMailboxDatabaseEntry 8 }

    exchAdMailboxDatabaseVersionBucketsAlloc OBJECT-TYPE
       SYNTAX      Gauge
       ACCESS      read-only
       STATUS      mandatory
       DESCRIPTION
          "database version buckets allocated"
       ::= { exchAdMailboxDatabaseEntry 9 }

    exchAdMailboxDatabaseInvIndex OBJECT-TYPE
       SYNTAX      INTEGER
       ACCESS      read-only
       STATUS      obsolete
       DESCRIPTION
          "pointer to database in exchAdMailboxDatabaseInventoryTable, same as exchAdMailboxDatabaseInventoryIndex - this object is obsolete"
       ::= { exchAdMailboxDatabaseEntry 10 }

--**************************************************************************  
--
-- exchAdMailboxReplicaSeederTable
--
--**************************************************************************

   exchAdMailboxReplicaSeederTable OBJECT-TYPE
       SYNTAX      SEQUENCE OF ExchAdMailboxReplicaSeederEntry
       ACCESS      not-accessible
       STATUS      mandatory
       DESCRIPTION
           "replica seeder table"
      ::= { exchAdPerformanceMailboxRole 8 }

   exchAdMailboxReplicaSeederEntry OBJECT-TYPE
       SYNTAX      ExchAdMailboxReplicaSeederEntry
       ACCESS      not-accessible
       STATUS      mandatory
       DESCRIPTION
           "defines an entry in the exchAdMailboxReplicaSeederTable"

       INDEX {
                exchAdMailboxReplicaSeederHostIndex,
                exchAdMailboxReplicaSeederIndex
             }
       ::= { exchAdMailboxReplicaSeederTable 1 }

    ExchAdMailboxReplicaSeederEntry ::=
       SEQUENCE {
            exchAdMailboxReplicaSeederHostIndex            INTEGER,
            exchAdMailboxReplicaSeederIndex                INTEGER,
            exchAdMailboxReplicaSeederId                   SnmpAdminString,
            exchAdMailboxReplicaSeederSeedingFinishedPct   Gauge
         }
    exchAdMailboxReplicaSeederHostIndex OBJECT-TYPE
       SYNTAX      INTEGER (0..2147483647)
       ACCESS      read-only
       STATUS      mandatory
       DESCRIPTION
          "unique index for each mailbox host, same as exchAdUniversalHostIndex"
       ::= { exchAdMailboxReplicaSeederEntry 1 }

    exchAdMailboxReplicaSeederIndex OBJECT-TYPE
       SYNTAX      INTEGER (0..2147483647)
       ACCESS      read-only
       STATUS      mandatory
       DESCRIPTION
          "unique index for each replica seeder on the host"
       ::= { exchAdMailboxReplicaSeederEntry 2 }

   exchAdMailboxReplicaSeederId OBJECT-TYPE
       SYNTAX      SnmpAdminString
       ACCESS      read-only
       STATUS      mandatory
       DESCRIPTION
          "unique identifier for each replica seeder"
       ::= { exchAdMailboxReplicaSeederEntry 3 }

   exchAdMailboxReplicaSeederSeedingFinishedPct OBJECT-TYPE
       SYNTAX      Gauge
       ACCESS      read-only
       STATUS      mandatory
       DESCRIPTION
          "Replication seeder finished percentage"
       ::= { exchAdMailboxReplicaSeederEntry 4 }

--**************************************************************************  
--
-- exchAdMailboxReplicationTable
--
--**************************************************************************

   exchAdMailboxReplicationTable OBJECT-TYPE
       SYNTAX      SEQUENCE OF ExchAdMailboxReplicationEntry
       ACCESS      not-accessible
       STATUS      mandatory
       DESCRIPTION
           "replication table"
      ::= { exchAdPerformanceMailboxRole 9 }

   exchAdMailboxReplicationEntry OBJECT-TYPE
       SYNTAX      ExchAdMailboxReplicationEntry
       ACCESS      not-accessible
       STATUS      mandatory
       DESCRIPTION
           "defines an entry in the exchAdMailboxReplicationTable"

       INDEX {
                exchAdMailboxReplicationHostIndex,
                exchAdMailboxReplicationIndex
             }
       ::= { exchAdMailboxReplicationTable 1 }

    ExchAdMailboxReplicationEntry ::=
       SEQUENCE {
            exchAdMailboxReplicationHostIndex            INTEGER,
            exchAdMailboxReplicationIndex                INTEGER,
            exchAdMailboxReplicationId                   SnmpAdminString,
            exchAdMailboxReplicationCopyQueueLength      Gauge,
            exchAdMailboxReplicationReplayQueueLength    Gauge
         }

    exchAdMailboxReplicationHostIndex OBJECT-TYPE
       SYNTAX      INTEGER (0..2147483647)
       ACCESS      read-only
       STATUS      mandatory
       DESCRIPTION
          "unique index for each mailbox host, same as exchAdUniversalHostIndex"
       ::= { exchAdMailboxReplicationEntry 1 }

   exchAdMailboxReplicationIndex OBJECT-TYPE
       SYNTAX      INTEGER (0..2147483647)
       ACCESS      read-only
       STATUS      mandatory
       DESCRIPTION
          "unique index for each replication on the host"
       ::= { exchAdMailboxReplicationEntry 2 }

   exchAdMailboxReplicationId OBJECT-TYPE
       SYNTAX      SnmpAdminString
       ACCESS      read-only
       STATUS      mandatory
       DESCRIPTION
          "unique identifier for each replication"
       ::= { exchAdMailboxReplicationEntry 3 }

   exchAdMailboxReplicationCopyQueueLength OBJECT-TYPE
       SYNTAX      Gauge
       ACCESS      read-only
       STATUS      mandatory
       DESCRIPTION
          "replication transaction log file copy queue length"
       ::= { exchAdMailboxReplicationEntry 4 }

   exchAdMailboxReplicationReplayQueueLength OBJECT-TYPE
       SYNTAX      Gauge
       ACCESS      read-only
       STATUS      mandatory
       DESCRIPTION
          "replication transaction log file replay queue length"
       ::= { exchAdMailboxReplicationEntry 5 }

--**************************************************************************  
--
-- exchAdMailboxSearchIndicesTable
--
--**************************************************************************

   exchAdMailboxSearchIndicesTable OBJECT-TYPE
       SYNTAX      SEQUENCE OF ExchAdMailboxSearchIndicesEntry
       ACCESS      not-accessible
       STATUS      mandatory
       DESCRIPTION
           "search indices table"
      ::= { exchAdPerformanceMailboxRole 10 }

   exchAdMailboxSearchIndicesEntry OBJECT-TYPE
       SYNTAX      ExchAdMailboxSearchIndicesEntry
       ACCESS      not-accessible
       STATUS      mandatory
       DESCRIPTION
           "defines an entry in the exchAdMailboxSearchIndicesTable"

       INDEX {
                exchAdMailboxSearchIndicesHostIndex,
                exchAdMailboxSearchIndicesIndex
             }
       ::= { exchAdMailboxSearchIndicesTable 1 }

    ExchAdMailboxSearchIndicesEntry ::=
       SEQUENCE {
            exchAdMailboxSearchIndicesHostIndex            INTEGER,
            exchAdMailboxSearchIndicesIndex                INTEGER,
            exchAdMailboxSearchIndicesId                   SnmpAdminString,
            exchAdMailboxSearchIndicesAvgDocIndexTime      Gauge,
            exchAdMailboxSearchIndicesFullCrawlModeStatus  INTEGER,
            exchAdMailboxSearchIndicesAvgRpcLatency        Gauge
         }

    exchAdMailboxSearchIndicesHostIndex OBJECT-TYPE
       SYNTAX      INTEGER (0..2147483647)
       ACCESS      read-only
       STATUS      mandatory
       DESCRIPTION
          "unique index for each mailbox host, same as exchAdUniversalHostIndex"
       ::= { exchAdMailboxSearchIndicesEntry 1 }

   exchAdMailboxSearchIndicesIndex OBJECT-TYPE
       SYNTAX      INTEGER (0..2147483647)
       ACCESS      read-only
       STATUS      mandatory
       DESCRIPTION
          "unique index for each search index on the host"
       ::= { exchAdMailboxSearchIndicesEntry 2 }

   exchAdMailboxSearchIndicesId OBJECT-TYPE
       SYNTAX      SnmpAdminString
       ACCESS      read-only
       STATUS      mandatory
       DESCRIPTION
          "unique identifier for each search index"
       ::= { exchAdMailboxSearchIndicesEntry 3 }


   exchAdMailboxSearchIndicesAvgDocIndexTime OBJECT-TYPE
       SYNTAX      Gauge
       ACCESS      read-only
       STATUS      mandatory
       DESCRIPTION
          "average document index time in milliseconds"
       ::= { exchAdMailboxSearchIndicesEntry 4 }

   exchAdMailboxSearchIndicesFullCrawlModeStatus OBJECT-TYPE
       SYNTAX      INTEGER {fullCrawl(1), not(2)}
       ACCESS      read-only
       STATUS      mandatory
       DESCRIPTION
          "Full crawl mode status (1=full crawl; 2=not)"
       ::= { exchAdMailboxSearchIndicesEntry 5 }

   exchAdMailboxSearchIndicesAvgRpcLatency OBJECT-TYPE
       SYNTAX      Gauge
       ACCESS      read-only
       STATUS      mandatory
       DESCRIPTION
          "average RPC latency in milliseconds"
       ::= { exchAdMailboxSearchIndicesEntry 6 }

--**************************************************************************  
--
-- exchAdMailboxStoreInterfaceTable
--
--**************************************************************************

   exchAdMailboxStoreInterfaceTable OBJECT-TYPE
       SYNTAX      SEQUENCE OF ExchAdMailboxStoreInterfaceEntry
       ACCESS      not-accessible
       STATUS      mandatory
       DESCRIPTION
           "store interface table"
      ::= { exchAdPerformanceMailboxRole 11 }

   exchAdMailboxStoreInterfaceEntry OBJECT-TYPE
       SYNTAX      ExchAdMailboxStoreInterfaceEntry
       ACCESS      not-accessible
       STATUS      mandatory
       DESCRIPTION
           "defines an entry in the exchAdMailboxStoreInterfaceTable"

       INDEX {
                exchAdMailboxStoreInterfaceHostIndex,
                exchAdMailboxStoreInterfaceIndex
             }
       ::= { exchAdMailboxStoreInterfaceTable 1 }

    ExchAdMailboxStoreInterfaceEntry ::=
       SEQUENCE {
            exchAdMailboxStoreInterfaceHostIndex            INTEGER,
            exchAdMailboxStoreInterfaceIndex                INTEGER,
            exchAdMailboxStoreInterfaceId                   SnmpAdminString,
            exchAdMailboxStoreInterfaceRopOutst             Gauge,
            exchAdMailboxStoreInterfaceFailedRpcRequests    Counter,
            exchAdMailboxStoreInterfaceRpcOutst             Gauge,
            exchAdMailboxStoreInterfaceRpcReq               Counter,
            exchAdMailboxStoreInterfaceSlowRpc              Counter,
            exchAdMailboxStoreInterfaceSlowRpcAvgLatency    Gauge
         }

    exchAdMailboxStoreInterfaceHostIndex OBJECT-TYPE
       SYNTAX      INTEGER (0..2147483647)
       ACCESS      read-only
       STATUS      mandatory
       DESCRIPTION
          "unique index for each mailbox host, same as exchAdUniversalHostIndex"
       ::= { exchAdMailboxStoreInterfaceEntry 1 }

   exchAdMailboxStoreInterfaceIndex OBJECT-TYPE
       SYNTAX      INTEGER (0..2147483647)
       ACCESS      read-only
       STATUS      mandatory
       DESCRIPTION
          "unique index for each store interface on the host"
       ::= { exchAdMailboxStoreInterfaceEntry 2 }

   exchAdMailboxStoreInterfaceId OBJECT-TYPE
       SYNTAX      SnmpAdminString
       ACCESS      read-only
       STATUS      mandatory
       DESCRIPTION
          "unique identifier for each store interface"
       ::= { exchAdMailboxStoreInterfaceEntry 3 }

   exchAdMailboxStoreInterfaceRopOutst OBJECT-TYPE
       SYNTAX      Gauge
       ACCESS      read-only
       STATUS      mandatory
       DESCRIPTION
          "outstanding remote operations requests"
       ::= { exchAdMailboxStoreInterfaceEntry 4 }

   exchAdMailboxStoreInterfaceFailedRpcRequests OBJECT-TYPE
       SYNTAX      Counter
       ACCESS      read-only
       STATUS      mandatory
       DESCRIPTION
          "failed RPC requests (error code plus exception failures)"
       ::= { exchAdMailboxStoreInterfaceEntry 5 }

   exchAdMailboxStoreInterfaceRpcOutst OBJECT-TYPE
       SYNTAX      Gauge
       ACCESS      read-only
       STATUS      mandatory
       DESCRIPTION
          "outstanding RPC requests"
       ::= { exchAdMailboxStoreInterfaceEntry 6 }

   exchAdMailboxStoreInterfaceRpcReq OBJECT-TYPE
       SYNTAX      Counter
       ACCESS      read-only
       STATUS      mandatory
       DESCRIPTION
          "RPC requests initiated"
       ::= { exchAdMailboxStoreInterfaceEntry 7 }

   exchAdMailboxStoreInterfaceSlowRpc OBJECT-TYPE
       SYNTAX      Counter
       ACCESS      read-only
       STATUS      mandatory
       DESCRIPTION
          "Slow RPC requests (> 500 ms)"
       ::= { exchAdMailboxStoreInterfaceEntry 8 }

   exchAdMailboxStoreInterfaceSlowRpcAvgLatency OBJECT-TYPE
       SYNTAX      Gauge
       ACCESS      read-only
       STATUS      mandatory
       DESCRIPTION
          "average latency of slow RPC requests in milliseconds"
       ::= { exchAdMailboxStoreInterfaceEntry 9 }

--**************************************************************************  
--
-- exchAdMailboxIsClientTable
--
--**************************************************************************

   exchAdMailboxIsClientTable OBJECT-TYPE
       SYNTAX      SEQUENCE OF ExchAdMailboxIsClientEntry
       ACCESS      not-accessible
       STATUS      mandatory
       DESCRIPTION
           "IS Client table"
      ::= { exchAdPerformanceMailboxRole 12 }

   exchAdMailboxIsClientEntry OBJECT-TYPE
       SYNTAX      ExchAdMailboxIsClientEntry
       ACCESS      not-accessible
       STATUS      mandatory
       DESCRIPTION
           "defines an entry in the exchAdMailboxIsClientTable"

       INDEX {
                exchAdMailboxIsClientHostIndex,
                exchAdMailboxIsClientIndex
             }
       ::= { exchAdMailboxIsClientTable 1 }

    ExchAdMailboxIsClientEntry ::=
       SEQUENCE {
            exchAdMailboxIsClientHostIndex            INTEGER,
            exchAdMailboxIsClientIndex                INTEGER,
            exchAdMailboxIsClientId                   SnmpAdminString,
            exchAdMailboxIsClientAvgLatency           Gauge,
            exchAdMailboxIsClientLdapReads            Counter,
            exchAdMailboxIsClientLdapSearches         Counter,
            exchAdMailboxIsClientDatabaseLogRecGen    Counter,
            exchAdMailboxIsClientDabatasePagesRead    Counter,
            exchAdMailboxIsClientRpcOperations        Counter
         }

    exchAdMailboxIsClientHostIndex OBJECT-TYPE
       SYNTAX      INTEGER (0..2147483647)
       ACCESS      read-only
       STATUS      mandatory
       DESCRIPTION
          "unique index for each mailbox host, same as exchAdUniversalHostIndex"
       ::= { exchAdMailboxIsClientEntry 1 }

    exchAdMailboxIsClientIndex OBJECT-TYPE
       SYNTAX      INTEGER (0..2147483647)
       ACCESS      read-only
       STATUS      mandatory
       DESCRIPTION
          "unique index for each IS Client on the host"
       ::= { exchAdMailboxIsClientEntry 2 }

    exchAdMailboxIsClientId OBJECT-TYPE
       SYNTAX      SnmpAdminString
       ACCESS      read-only
       STATUS      mandatory
       DESCRIPTION
          "unique identifier for each IS Client"
       ::= { exchAdMailboxIsClientEntry 3 }

    exchAdMailboxIsClientAvgLatency OBJECT-TYPE
       SYNTAX      Gauge
       ACCESS      read-only
       STATUS      mandatory
       DESCRIPTION
          "average Client RPC latency over last 1024 packets in milliseconds"
       ::= { exchAdMailboxIsClientEntry 4 }

    exchAdMailboxIsClientLdapReads OBJECT-TYPE
       SYNTAX      Counter
       ACCESS      read-only
       STATUS      mandatory
       DESCRIPTION
          "client LDAP reads"
       ::= { exchAdMailboxIsClientEntry 5 }

    exchAdMailboxIsClientLdapSearches OBJECT-TYPE
       SYNTAX      Counter
       ACCESS      read-only
       STATUS      mandatory
       DESCRIPTION
          "client LDAP searches"
       ::= { exchAdMailboxIsClientEntry 6 }

    exchAdMailboxIsClientDatabaseLogRecGen OBJECT-TYPE
       SYNTAX      Counter
       ACCESS      read-only
       STATUS      mandatory
       DESCRIPTION
          "client database log records"
       ::= { exchAdMailboxIsClientEntry 7 }

    exchAdMailboxIsClientDabatasePagesRead OBJECT-TYPE
       SYNTAX      Counter
       ACCESS      read-only
       STATUS      mandatory
       DESCRIPTION
          "client database pages read"
       ::= { exchAdMailboxIsClientEntry 8 }

    exchAdMailboxIsClientRpcOperations OBJECT-TYPE
       SYNTAX      Counter
       ACCESS      read-only
       STATUS      mandatory
       DESCRIPTION
          "client RPC operations"
       ::= { exchAdMailboxIsClientEntry 9 }

--**************************************************************************  
--
-- exchAdMailboxIsMailboxTable
--
--**************************************************************************

   exchAdMailboxIsMailboxTable OBJECT-TYPE
       SYNTAX      SEQUENCE OF ExchAdMailboxIsMailboxEntry
       ACCESS      not-accessible
       STATUS      mandatory
       DESCRIPTION
           "IS Mailbox table"
      ::= { exchAdPerformanceMailboxRole 13 }

   exchAdMailboxIsMailboxEntry OBJECT-TYPE
       SYNTAX      ExchAdMailboxIsMailboxEntry
       ACCESS      not-accessible
       STATUS      mandatory
       DESCRIPTION
           "defines an entry in the exchAdMailboxIsMailboxTable"

       INDEX {
                exchAdMailboxIsMailboxHostIndex,
                exchAdMailboxIsMailboxIndex
             }
       ::= { exchAdMailboxIsMailboxTable 1 }

    ExchAdMailboxIsMailboxEntry ::=
       SEQUENCE {
            exchAdMailboxIsMailboxHostIndex            INTEGER,
            exchAdMailboxIsMailboxIndex                INTEGER,
            exchAdMailboxIsMailboxId                   SnmpAdminString,
            exchAdMailboxIsMailboxCategorizations      Gauge,
            exchAdMailboxIsMailboxSearchTasks          Counter,       
            exchAdMailboxIsMailboxSlowFindrow          Counter
         }

    exchAdMailboxIsMailboxHostIndex OBJECT-TYPE
       SYNTAX      INTEGER (0..2147483647)
       ACCESS      read-only
       STATUS      mandatory
       DESCRIPTION
          "unique index for each mailbox host, same as exchAdUniversalHostIndex"
       ::= { exchAdMailboxIsMailboxEntry 1 }

    exchAdMailboxIsMailboxIndex OBJECT-TYPE
       SYNTAX      INTEGER (0..2147483647)
       ACCESS      read-only
       STATUS      mandatory
       DESCRIPTION
          "unique index for each IS Mailbox on the host"
       ::= { exchAdMailboxIsMailboxEntry 2 }

    exchAdMailboxIsMailboxId OBJECT-TYPE
       SYNTAX      SnmpAdminString
       ACCESS      read-only
       STATUS      mandatory
       DESCRIPTION
          "unique identifier for each IS Mailbox"
       ::= { exchAdMailboxIsMailboxEntry 3 }

    exchAdMailboxIsMailboxCategorizations OBJECT-TYPE
       SYNTAX      Gauge
       ACCESS      read-only
       STATUS      mandatory
       DESCRIPTION
          "existing mailbox categorizations"
       ::= { exchAdMailboxIsMailboxEntry 4 }

    exchAdMailboxIsMailboxSearchTasks OBJECT-TYPE
       SYNTAX      Counter
       ACCESS      read-only
       STATUS      mandatory
       DESCRIPTION
          "mailbox search tasks created"
       ::= { exchAdMailboxIsMailboxEntry 5 }

    exchAdMailboxIsMailboxSlowFindrow OBJECT-TYPE
       SYNTAX      Counter
       ACCESS      read-only
       STATUS      mandatory
       DESCRIPTION
          "slower mailbox FindRows"
       ::= { exchAdMailboxIsMailboxEntry 6 }

--**************************************************************************  
--
-- exchAdMailboxMailSubmissionTable
--
--**************************************************************************

   exchAdMailboxMailSubmissionTable OBJECT-TYPE
       SYNTAX      SEQUENCE OF ExchAdMailboxMailSubmissionEntry
       ACCESS      not-accessible
       STATUS      mandatory
       DESCRIPTION
           "mailbox submission table"
      ::= { exchAdPerformanceMailboxRole 14 }

   exchAdMailboxMailSubmissionEntry OBJECT-TYPE
       SYNTAX      ExchAdMailboxMailSubmissionEntry
       ACCESS      not-accessible
       STATUS      mandatory
       DESCRIPTION
           "defines an entry in the exchAdMailboxMailSubmissionTable"

       INDEX {
                exchAdMailboxMailSubmissionHostIndex,
                exchAdMailboxMailSubmissionIndex
             }
       ::= { exchAdMailboxMailSubmissionTable 1 }

    ExchAdMailboxMailSubmissionEntry ::=
       SEQUENCE {
            exchAdMailboxMailSubmissionHostIndex                   INTEGER,
            exchAdMailboxMailSubmissionIndex                       INTEGER,
            exchAdMailboxMailSubmissionId                          SnmpAdminString,
            exchAdMailboxMailSubmissionFailedSubmissions           Counter,
            exchAdMailboxMailSubmissionHubServersInRetry           Gauge,
            exchAdMailboxMailSubmissionSuccessfulSubmissions       Counter,
            exchAdMailboxMailSubmissionTemporaryFailedSubmissions  Counter
           }

    exchAdMailboxMailSubmissionHostIndex OBJECT-TYPE
       SYNTAX      INTEGER (0..2147483647)
       ACCESS      read-only
       STATUS      mandatory
       DESCRIPTION
          "unique index for each mailbox host, same as exchAdUniversalHostIndex"
       ::= { exchAdMailboxMailSubmissionEntry 1 }

    exchAdMailboxMailSubmissionIndex OBJECT-TYPE
       SYNTAX      INTEGER (0..2147483647)
       ACCESS      read-only
       STATUS      mandatory
       DESCRIPTION
          "unique index for each mail submission on the host"
       ::= { exchAdMailboxMailSubmissionEntry 2 }

    exchAdMailboxMailSubmissionId OBJECT-TYPE
       SYNTAX      SnmpAdminString
       ACCESS      read-only
       STATUS      mandatory
       DESCRIPTION
          "unique identifier for each mail submission"
       ::= { exchAdMailboxMailSubmissionEntry 3 }

    exchAdMailboxMailSubmissionFailedSubmissions OBJECT-TYPE
       SYNTAX      Counter
       ACCESS      read-only
       STATUS      mandatory
       DESCRIPTION
          "failed mail submissions"
       ::= { exchAdMailboxMailSubmissionEntry 4 }

    exchAdMailboxMailSubmissionHubServersInRetry OBJECT-TYPE
       SYNTAX      Gauge
       ACCESS      read-only
       STATUS      mandatory
       DESCRIPTION
          "hub servers in retry mode"
       ::= { exchAdMailboxMailSubmissionEntry 5 }

    exchAdMailboxMailSubmissionSuccessfulSubmissions OBJECT-TYPE
       SYNTAX      Counter
       ACCESS      read-only
       STATUS      mandatory
       DESCRIPTION
          "successful mail submissions"
       ::= { exchAdMailboxMailSubmissionEntry 6 }

    exchAdMailboxMailSubmissionTemporaryFailedSubmissions OBJECT-TYPE
       SYNTAX      Counter
       ACCESS      read-only
       STATUS      mandatory
       DESCRIPTION
          "temporary mail submission failures"
       ::= { exchAdMailboxMailSubmissionEntry 7 }


--**************************************************************************  
--
-- Performance Variables: Hub Transport Role
--
--**************************************************************************

--**************************************************************************  
--
-- exchAdHubTransGeneralPerformanceTable
--
--**************************************************************************

    exchAdHubTransGeneralPerformanceTable OBJECT-TYPE
       SYNTAX      SEQUENCE OF ExchAdHubTransGeneralPerformanceEntry
       ACCESS      not-accessible
       STATUS      mandatory
       DESCRIPTION
           "hub transport general performance table"
      ::= { exchAdPerformanceHubTransportRole 1 }

    exchAdHubTransGeneralPerformanceEntry OBJECT-TYPE
       SYNTAX      ExchAdHubTransGeneralPerformanceEntry
       ACCESS      not-accessible
       STATUS      mandatory
       DESCRIPTION
           "defines an entry in the exchAdHubTransGeneralPerformanceTable"

       INDEX {
                exchAdHubTransHostIndex
             }
       ::= { exchAdHubTransGeneralPerformanceTable 1 }

    ExchAdHubTransGeneralPerformanceEntry ::=
       SEQUENCE {
           exchAdHubTransHostIndex                                  INTEGER,
           exchAdHubTransStoreDriverTotMsgDeliveryAttInPerSec       Gauge,
           exchAdHubTransStoreDriverTotLocalDeliveryCallsInPerSec   Gauge,
           exchAdHubTransStoreDriverTotRecipientsDeliveredInPerSec  Gauge,
           exchAdHubTransStoreDriverTotSubmMailItemsOutPerSec       Gauge,
           exchAdHubTransDumpsterDeletesPerSec                      Gauge,
           exchAdHubTransDumpsterInsertsPerSec                      Gauge,
           exchAdHubTransDumpsterItems                              Gauge,
           exchAdHubTransDumpsterSize                               Gauge,
           exchAdHubTransQueuesTotActiveMbxDeliveryQueueLength      Gauge,
           exchAdHubTransQueuesTotActiveNonSmtpDeliveryQueueLength  Gauge,
           exchAdHubTransQueuesTotActiveRemoteDeliveryQueueLength   Gauge,
           exchAdHubTransQueuesTotAggDeliveryQueueLength            Gauge,
           exchAdHubTransQueuesTotLargestDeliveryQueueLength        Gauge,
           exchAdHubTransQueuesTotMsgsDeliveredPerSec               Gauge,
           exchAdHubTransQueuesTotMsgsDeliveryQueuedPerSec          Gauge,
           exchAdHubTransQueuesTotMsgsSubmissionPerSec              Gauge,
           exchAdHubTransQueuesTotMsgsPoisonQueueLength             Gauge,
           exchAdHubTransQueuesTotMsgsRetry                         Gauge,
           exchAdHubTransQueuesTotRetryNonSmtpQueues                Gauge,
           exchAdHubTransQueuesTotRetryRemoteDeliveryQueue          Gauge,
           exchAdHubTransQueuesTotSubmissionQueue                   Gauge,
           exchAdHubTransQueuesTotUnreachableQueue                  Gauge,
           exchAdHubTransQueuesAvgBytesPerMsgIn                     Gauge,
           exchAdHubTransQueuesTotSmtpMsgsRcvdPerSec                Gauge,
           exchAdHubTransQueuesTotSmtpMsgsSentPerSec                Gauge
       }

   exchAdHubTransHostIndex OBJECT-TYPE
       SYNTAX      INTEGER (0..2147483647)
       ACCESS      read-only
       STATUS      mandatory
       DESCRIPTION
          "unique index for each host, same as exchAdUniversalHostIndex"
       ::= { exchAdHubTransGeneralPerformanceEntry 1 }

    exchAdHubTransStoreDriverTotMsgDeliveryAttInPerSec OBJECT-TYPE
       SYNTAX      Gauge
       ACCESS      read-only
       STATUS      mandatory
       DESCRIPTION
          "inbound message delivery attempts per second"
       ::= { exchAdHubTransGeneralPerformanceEntry 2 }

    exchAdHubTransStoreDriverTotLocalDeliveryCallsInPerSec OBJECT-TYPE
       SYNTAX      Gauge
       ACCESS      read-only
       STATUS      mandatory
       DESCRIPTION
          "inbound local delivery calls per second"
       ::= { exchAdHubTransGeneralPerformanceEntry 3 }

    exchAdHubTransStoreDriverTotRecipientsDeliveredInPerSec OBJECT-TYPE
       SYNTAX      Gauge
       ACCESS      read-only
       STATUS      mandatory
       DESCRIPTION
          "Inbound recipients delivered per second"
       ::= { exchAdHubTransGeneralPerformanceEntry 4 }

    exchAdHubTransStoreDriverTotSubmMailItemsOutPerSec OBJECT-TYPE
       SYNTAX      Gauge
       ACCESS      read-only
       STATUS      mandatory
       DESCRIPTION
          "outbound  mail items submitted per second"
       ::= { exchAdHubTransGeneralPerformanceEntry 5 }

    exchAdHubTransDumpsterDeletesPerSec OBJECT-TYPE
       SYNTAX      Gauge
       ACCESS      read-only
       STATUS      mandatory
       DESCRIPTION
          "transport dumpster deletes per second"
       ::= { exchAdHubTransGeneralPerformanceEntry 6 }

    exchAdHubTransDumpsterInsertsPerSec OBJECT-TYPE
       SYNTAX      Gauge
       ACCESS      read-only
       STATUS      mandatory
       DESCRIPTION
          "transport dumpster inserts per second"
       ::= { exchAdHubTransGeneralPerformanceEntry 7 }

    exchAdHubTransDumpsterItems OBJECT-TYPE
       SYNTAX      Gauge
       ACCESS      read-only
       STATUS      mandatory
       DESCRIPTION
          "items currently in transport dumpster"
       ::= { exchAdHubTransGeneralPerformanceEntry 8 }

    exchAdHubTransDumpsterSize OBJECT-TYPE
       SYNTAX      Gauge
       ACCESS      read-only
       STATUS      mandatory
       DESCRIPTION
          "size of items currently in transport dumpster in bytes"
       ::= { exchAdHubTransGeneralPerformanceEntry 9 }

    exchAdHubTransQueuesTotActiveMbxDeliveryQueueLength OBJECT-TYPE
       SYNTAX      Gauge
       ACCESS      read-only
       STATUS      mandatory
       DESCRIPTION
          "total active mailbox delivery queue lengths over all transport queues"
       ::= { exchAdHubTransGeneralPerformanceEntry 10 }

    exchAdHubTransQueuesTotActiveNonSmtpDeliveryQueueLength OBJECT-TYPE
       SYNTAX      Gauge
       ACCESS      read-only
       STATUS      mandatory
       DESCRIPTION
          "total active non-SMTP delivery queue lengths over all transport queues"
       ::= { exchAdHubTransGeneralPerformanceEntry 11 }

    exchAdHubTransQueuesTotActiveRemoteDeliveryQueueLength OBJECT-TYPE
       SYNTAX      Gauge
       ACCESS      read-only
       STATUS      mandatory
       DESCRIPTION
          "total active remote delivery queue lengths over all transport queues"
       ::= { exchAdHubTransGeneralPerformanceEntry 12 }

    exchAdHubTransQueuesTotAggDeliveryQueueLength OBJECT-TYPE
       SYNTAX      Gauge
       ACCESS      read-only
       STATUS      mandatory
       DESCRIPTION
          "total aggregate delivery queue lengths over all transport queues"
       ::= { exchAdHubTransGeneralPerformanceEntry 13 }

    exchAdHubTransQueuesTotLargestDeliveryQueueLength OBJECT-TYPE
       SYNTAX      Gauge
       ACCESS      read-only
       STATUS      mandatory
       DESCRIPTION
          "largest delivery queue length over all transport queues"
       ::= { exchAdHubTransGeneralPerformanceEntry 14 }

    exchAdHubTransQueuesTotMsgsDeliveredPerSec OBJECT-TYPE
       SYNTAX      Gauge
       ACCESS      read-only
       STATUS      mandatory
       DESCRIPTION
          "messages delivered per second over all transport queues"
       ::= { exchAdHubTransGeneralPerformanceEntry 15 }

    exchAdHubTransQueuesTotMsgsDeliveryQueuedPerSec OBJECT-TYPE
       SYNTAX      Gauge
       ACCESS      read-only
       STATUS      mandatory
       DESCRIPTION
          "messages queued for delivery per second over all transport queues"
       ::= { exchAdHubTransGeneralPerformanceEntry 16 }

    exchAdHubTransQueuesTotMsgsSubmissionPerSec OBJECT-TYPE
       SYNTAX      Gauge
       ACCESS      read-only
       STATUS      mandatory
       DESCRIPTION
          "messages submitted per second to all transport queues"
       ::= { exchAdHubTransGeneralPerformanceEntry 17 }

    exchAdHubTransQueuesTotMsgsPoisonQueueLength OBJECT-TYPE
       SYNTAX      Gauge
       ACCESS      read-only
       STATUS      mandatory
       DESCRIPTION
          "total poison message queue lengths  over all transport queues"
       ::= { exchAdHubTransGeneralPerformanceEntry 18 }

    exchAdHubTransQueuesTotMsgsRetry OBJECT-TYPE
       SYNTAX      Gauge
       ACCESS      read-only
       STATUS      mandatory
       DESCRIPTION
          "total retry mailbox delivery queue lengths over all transport queues"
       ::= { exchAdHubTransGeneralPerformanceEntry 19 }

    exchAdHubTransQueuesTotRetryNonSmtpQueues OBJECT-TYPE
       SYNTAX      Gauge
       ACCESS      read-only
       STATUS      mandatory
       DESCRIPTION
          "total retry non-SMTP delivery queue lengths over all transport queues"
       ::= { exchAdHubTransGeneralPerformanceEntry 20 }

    exchAdHubTransQueuesTotRetryRemoteDeliveryQueue OBJECT-TYPE
       SYNTAX      Gauge
       ACCESS      read-only
       STATUS      mandatory
       DESCRIPTION
          "total retry remote delivery queue lengths over all transport queues"
       ::= { exchAdHubTransGeneralPerformanceEntry 21 }

    exchAdHubTransQueuesTotSubmissionQueue OBJECT-TYPE
       SYNTAX      Gauge
       ACCESS      read-only
       STATUS      mandatory
       DESCRIPTION
          "total submission queue lengths over all transport queues"
       ::= { exchAdHubTransGeneralPerformanceEntry 22 }

    exchAdHubTransQueuesTotUnreachableQueue OBJECT-TYPE
       SYNTAX      Gauge
       ACCESS      read-only
       STATUS      mandatory
       DESCRIPTION
          "total unreachable queue lengths over all transport queues"
       ::= { exchAdHubTransGeneralPerformanceEntry 23 }

    exchAdHubTransQueuesAvgBytesPerMsgIn OBJECT-TYPE
       SYNTAX      Gauge
       ACCESS      read-only
       STATUS      mandatory
       DESCRIPTION
          "average bytes per inbound message received over all transport queues"
       ::= { exchAdHubTransGeneralPerformanceEntry 24 }

    exchAdHubTransQueuesTotSmtpMsgsRcvdPerSec OBJECT-TYPE
       SYNTAX      Gauge
       ACCESS      read-only
       STATUS      mandatory
       DESCRIPTION
          "total messages received by SMTP server per second over all transport queues"
       ::= { exchAdHubTransGeneralPerformanceEntry 25 }

    exchAdHubTransQueuesTotSmtpMsgsSentPerSec OBJECT-TYPE
       SYNTAX      Gauge
       ACCESS      read-only
       STATUS      mandatory
       DESCRIPTION
          "Total messages sent by SMTP send connector per second over all transport queues"
       ::= { exchAdHubTransGeneralPerformanceEntry 26 }

--**************************************************************************  
--
-- exchAdHubTransDatabaseInstTable
--
--**************************************************************************

   exchAdHubTransDatabaseInstTable OBJECT-TYPE
       SYNTAX      SEQUENCE OF ExchAdHubTransDatabaseInstEntry
       ACCESS      not-accessible
       STATUS      mandatory
       DESCRIPTION
           "hub transport database instance table"
      ::= { exchAdPerformanceHubTransportRole 2 }

    exchAdHubTransDatabaseInstEntry OBJECT-TYPE
       SYNTAX      ExchAdHubTransDatabaseInstEntry
       ACCESS      not-accessible
       STATUS      mandatory
       DESCRIPTION
           "defines an entry in the exchAdHubTransDatabaseInstTable"

       INDEX {
                exchAdHubTransDatabaseInstHostIndex,
                exchAdHubTransDatabaseInstIndex
             }
       ::= { exchAdHubTransDatabaseInstTable 1 }

    ExchAdHubTransDatabaseInstEntry ::=
       SEQUENCE {
           exchAdHubTransDatabaseInstHostIndex              INTEGER,
           exchAdHubTransDatabaseInstIndex                  INTEGER,
           exchAdHubTransDatabaseInstId                     SnmpAdminString,
           exchAdHubTransDatabaseInstDatabaseWritesPerSec   Gauge,
           exchAdHubTransDatabaseInstDatabaseReadsPerSec    Gauge,
           exchAdHubTransDatabaseInstLogFileWritesPerSec    Gauge,
           exchAdHubTransDatabaseInstLogFileReadsPerSec     Gauge,
           exchAdHubTransDatabaseInstLogGenCkptDepth        Gauge,
           exchAdHubTransDatabaseInstLogRecordStallsPerSec  Gauge,
           exchAdHubTransDatabaseInstLogThreadsWaiting      Gauge,
           exchAdHubTransDatabaseInstVersionBucketsAlloc    Gauge
         }

   exchAdHubTransDatabaseInstHostIndex OBJECT-TYPE
       SYNTAX      INTEGER (0..2147483647)
       ACCESS      read-only
       STATUS      mandatory
       DESCRIPTION
          "unique index for each hub transport host, same as exchAdUniversalHostIndex"
       ::= { exchAdHubTransDatabaseInstEntry 1 }

    exchAdHubTransDatabaseInstIndex OBJECT-TYPE
       SYNTAX      INTEGER (0..2147483647)
       ACCESS      read-only
       STATUS      mandatory
       DESCRIPTION
          "unique index for each database instance on the host"
       ::= { exchAdHubTransDatabaseInstEntry 2 }

    exchAdHubTransDatabaseInstId OBJECT-TYPE
       SYNTAX      SnmpAdminString
       ACCESS      read-only
       STATUS      mandatory
       DESCRIPTION
          "unique identifier for each database instance"
       ::= { exchAdHubTransDatabaseInstEntry 3 }

    exchAdHubTransDatabaseInstDatabaseWritesPerSec OBJECT-TYPE
       SYNTAX      Gauge
       ACCESS      read-only
       STATUS      mandatory
       DESCRIPTION
          "database write operations completed per second"
       ::= { exchAdHubTransDatabaseInstEntry 4 }

    exchAdHubTransDatabaseInstDatabaseReadsPerSec OBJECT-TYPE
       SYNTAX      Gauge
       ACCESS      read-only
       STATUS      mandatory
       DESCRIPTION
          "database read operations completed per second"
       ::= { exchAdHubTransDatabaseInstEntry 5 }

    exchAdHubTransDatabaseInstLogFileWritesPerSec OBJECT-TYPE
       SYNTAX      Gauge
       ACCESS      read-only
       STATUS      mandatory
       DESCRIPTION
          "database Log file write operations completed per second"
       ::= { exchAdHubTransDatabaseInstEntry 6 }

    exchAdHubTransDatabaseInstLogFileReadsPerSec OBJECT-TYPE
       SYNTAX      Gauge
       ACCESS      read-only
       STATUS      mandatory
       DESCRIPTION
          "database Log file read operations completed per second"
       ::= { exchAdHubTransDatabaseInstEntry 7 }

    exchAdHubTransDatabaseInstLogGenCkptDepth OBJECT-TYPE
       SYNTAX      Gauge
       ACCESS      read-only
       STATUS      mandatory
       DESCRIPTION
          "database Log file generation checkpoint depth"
       ::= { exchAdHubTransDatabaseInstEntry 8 }

    exchAdHubTransDatabaseInstLogRecordStallsPerSec OBJECT-TYPE
       SYNTAX      Gauge
       ACCESS      read-only
       STATUS      mandatory
       DESCRIPTION
          "database Log record stalls per second, no buffers available"
       ::= { exchAdHubTransDatabaseInstEntry 9 }

    exchAdHubTransDatabaseInstLogThreadsWaiting OBJECT-TYPE
       SYNTAX      Gauge
       ACCESS      read-only
       STATUS      mandatory
       DESCRIPTION
          "database Log threads waiting for data writes"
       ::= { exchAdHubTransDatabaseInstEntry 10 }

    exchAdHubTransDatabaseInstVersionBucketsAlloc OBJECT-TYPE
       SYNTAX      Gauge
       ACCESS      read-only
       STATUS      mandatory
       DESCRIPTION
          "database Version buckets allocated"
       ::= { exchAdHubTransDatabaseInstEntry 11 }

--**************************************************************************  
--
-- exchAdHubTransExtensibilityAgentTable
--
--**************************************************************************

    exchAdHubTransExtensibilityAgentTable OBJECT-TYPE
       SYNTAX      SEQUENCE OF ExchAdHubTransExtensibilityAgentEntry
       ACCESS      not-accessible
       STATUS      mandatory
       DESCRIPTION
           "hub transport extensibility agent table"
      ::= { exchAdPerformanceHubTransportRole 3 }

    exchAdHubTransExtensibilityAgentEntry OBJECT-TYPE
       SYNTAX      ExchAdHubTransExtensibilityAgentEntry
       ACCESS      not-accessible
       STATUS      mandatory
       DESCRIPTION
           "defines an entry in the exchAdHubTransExtensibilityAgentTable"

       INDEX {
                exchAdHubTransExtensibilityAgentHostIndex,
                exchAdHubTransExtensibilityAgentIndex
             }
       ::= { exchAdHubTransExtensibilityAgentTable 1 }

    ExchAdHubTransExtensibilityAgentEntry ::=
       SEQUENCE {

           exchAdHubTransExtensibilityAgentHostIndex  INTEGER,
           exchAdHubTransExtensibilityAgentIndex      INTEGER,
           exchAdHubExtensibilityAgentId              SnmpAdminString,
           exchAdHubExtAgentAvgAgentProcTime          Gauge,
           exchAdHubExtAgentAgentInvocations          Counter
       }
    exchAdHubTransExtensibilityAgentHostIndex OBJECT-TYPE
       SYNTAX      INTEGER (0..2147483647)
       ACCESS      read-only
       STATUS      mandatory
       DESCRIPTION
          "unique index for each hub transport host, same as exchAdUniversalHostIndex"
       ::= { exchAdHubTransExtensibilityAgentEntry 1 }

    exchAdHubTransExtensibilityAgentIndex OBJECT-TYPE
       SYNTAX      INTEGER (0..2147483647)
       ACCESS      read-only
       STATUS      mandatory
       DESCRIPTION
          "unique index for each extensibility agent on the host"
       ::= { exchAdHubTransExtensibilityAgentEntry 2 }

    exchAdHubExtensibilityAgentId OBJECT-TYPE
       SYNTAX      SnmpAdminString
       ACCESS      read-only
       STATUS      mandatory
       DESCRIPTION
          "unique identifier for each agent"
       ::= { exchAdHubTransExtensibilityAgentEntry 3 }

    exchAdHubExtAgentAvgAgentProcTime OBJECT-TYPE
       SYNTAX      Gauge
       ACCESS      read-only
       STATUS      mandatory
       DESCRIPTION
          "average agent event processing time in seconds"
       ::= { exchAdHubTransExtensibilityAgentEntry 4 } 

    exchAdHubExtAgentAgentInvocations OBJECT-TYPE
       SYNTAX      Counter
       ACCESS      read-only
       STATUS      mandatory
       DESCRIPTION
          "agent Invocations"
       ::= { exchAdHubTransExtensibilityAgentEntry 5 } 


--**************************************************************************  
--
-- Performance Variables: Client Access Role
--
--**************************************************************************

--**************************************************************************  
--
-- exchAdClntAccessOwaTable
--
--**************************************************************************

    exchAdClntAccessOwaTable OBJECT-TYPE
       SYNTAX      SEQUENCE OF  ExchAdClntAccessOwaEntry
       ACCESS      not-accessible
       STATUS      mandatory
       DESCRIPTION
           "client access OWA table"
      ::= { exchAdPerformanceClientAccessRole 1 }

    exchAdClntAccessOwaEntry OBJECT-TYPE
       SYNTAX      ExchAdClntAccessOwaEntry
       ACCESS      not-accessible
       STATUS      mandatory
       DESCRIPTION
           "defines an entry in the exchAdClntAccessOwaTable"

       INDEX {
                exchAdClntAccessOwaHostIndex
             }
       ::= { exchAdClntAccessOwaTable 1 }

    ExchAdClntAccessOwaEntry ::=
       SEQUENCE {
           exchAdClntAccessOwaHostIndex                         INTEGER,
           exchAdClntAccessOwaAvgSearchTime                     Gauge,
           exchAdClntAccessOwaCurrUniqueUsers                   Gauge,
           exchAdClntAccessOwaReqPerSec                         Gauge
          }

    exchAdClntAccessOwaHostIndex OBJECT-TYPE
       SYNTAX      INTEGER (0..2147483647)
       ACCESS      read-only
       STATUS      mandatory
       DESCRIPTION
          "unique index for each client access host, same as exchAdUniversalHostIndex"
       ::= { exchAdClntAccessOwaEntry 1 }

    exchAdClntAccessOwaAvgSearchTime OBJECT-TYPE
       SYNTAX      Gauge
       ACCESS      read-only
       STATUS      mandatory
       DESCRIPTION
          "average time that elapsed while waiting for a search to complete"
       ::= { exchAdClntAccessOwaEntry 2 }

    exchAdClntAccessOwaCurrUniqueUsers OBJECT-TYPE
       SYNTAX      Gauge
       ACCESS      read-only
       STATUS      mandatory
       DESCRIPTION
          "number of unique users currently logged onto the Outlook Web App"
       ::= { exchAdClntAccessOwaEntry 3 }

    exchAdClntAccessOwaReqPerSec OBJECT-TYPE
       SYNTAX      Gauge
       ACCESS      read-only
       STATUS      mandatory
       DESCRIPTION
          "number of requests handled by the Outlook Web App per second"
       ::= { exchAdClntAccessOwaEntry 4 }

--**************************************************************************  
--
-- exchAdClntAccessAspNetTable
--
--**************************************************************************

    exchAdClntAccessAspNetTable OBJECT-TYPE
       SYNTAX      SEQUENCE OF  ExchAdClntAccessAspNetEntry
       ACCESS      not-accessible
       STATUS      mandatory
       DESCRIPTION
           "client access ASP.NET table"
      ::= { exchAdPerformanceClientAccessRole 2 }

    exchAdClntAccessAspNetEntry OBJECT-TYPE
       SYNTAX      ExchAdClntAccessAspNetEntry
       ACCESS      not-accessible
       STATUS      mandatory
       DESCRIPTION
           "defines an entry in the exchAdClntAccessAspNetTable"

       INDEX {
                exchAdClntAccessAspNetHostIndex
             }
       ::= { exchAdClntAccessAspNetTable 1 }

    ExchAdClntAccessAspNetEntry ::=
       SEQUENCE {
           exchAdClntAccessAspNetHostIndex                      INTEGER,
           exchAdClntAccessAspNetAppRestarts                    Counter,
           exchAdClntAccessAspNetWorkerPrcRestarts              Counter,
           exchAdClntAccessAspNetRequestWaitTime                Gauge,
           exchAdClntAccessAspNetRequestinAppQueue              Gauge
          }

    exchAdClntAccessAspNetHostIndex OBJECT-TYPE
       SYNTAX      INTEGER (0..2147483647)
       ACCESS      read-only
       STATUS      mandatory
       DESCRIPTION
          "unique index for each client access host, same as exchAdUniversalHostIndex"
       ::= { exchAdClntAccessAspNetEntry 1 }

    exchAdClntAccessAspNetAppRestarts OBJECT-TYPE
       SYNTAX      Counter
       ACCESS      read-only
       STATUS      mandatory
       DESCRIPTION
          "number of times the application has been restarted during the Web server's lifetime"
       ::= { exchAdClntAccessAspNetEntry 2 }

    exchAdClntAccessAspNetWorkerPrcRestarts OBJECT-TYPE
       SYNTAX      Counter
       ACCESS      read-only
       STATUS      mandatory
       DESCRIPTION
          "number of times a worker process has restarted on the computer"
       ::= { exchAdClntAccessAspNetEntry 3 }

    exchAdClntAccessAspNetRequestWaitTime OBJECT-TYPE
       SYNTAX      Gauge
       ACCESS      read-only
       STATUS      mandatory
       DESCRIPTION
          "time the most recent request was waiting in the queue in number of milliseconds"
       ::= { exchAdClntAccessAspNetEntry 4 }

    exchAdClntAccessAspNetRequestinAppQueue OBJECT-TYPE
       SYNTAX      Gauge
       ACCESS      read-only
       STATUS      mandatory
       DESCRIPTION
          "number of requests in the application request queue"
       ::= { exchAdClntAccessAspNetEntry 5 }

--**************************************************************************  
--
-- exchAdClntAccessAvailServTable
--
--**************************************************************************

    exchAdClntAccessAvailServTable OBJECT-TYPE
       SYNTAX      SEQUENCE OF  ExchAdClntAccessAvailServEntry
       ACCESS      not-accessible
       STATUS      mandatory
       DESCRIPTION
           "client access Availability Service table"
      ::= { exchAdPerformanceClientAccessRole 3 }

    exchAdClntAccessAvailServEntry OBJECT-TYPE
       SYNTAX      ExchAdClntAccessAvailServEntry
       ACCESS      not-accessible
       STATUS      mandatory
       DESCRIPTION
           "defines an entry in the exchAdClntAccessAvailServTable"

       INDEX {
                exchAdClntAccessAvailServHostIndex
             }
       ::= { exchAdClntAccessAvailServTable 1 }

    ExchAdClntAccessAvailServEntry ::=
       SEQUENCE {
           exchAdClntAccessAvailServHostIndex                   INTEGER,
           exchAdClntAccessAvailServFBRAvgTime                  Gauge,
           exchAdClntAccessAvailServReqPerSec                   Gauge
          }

    exchAdClntAccessAvailServHostIndex OBJECT-TYPE
       SYNTAX      INTEGER (0..2147483647)
       ACCESS      read-only
       STATUS      mandatory
       DESCRIPTION
          "unique index for each client access host, same as exchAdUniversalHostIndex"
       ::= { exchAdClntAccessAvailServEntry 1 }

    exchAdClntAccessAvailServFBRAvgTime OBJECT-TYPE
       SYNTAX      Gauge
       ACCESS      read-only
       STATUS      mandatory
       DESCRIPTION
          "average time to process a free/busy request in seconds"
       ::= { exchAdClntAccessAvailServEntry 2 }

    exchAdClntAccessAvailServReqPerSec OBJECT-TYPE
       SYNTAX      Gauge
       ACCESS      read-only
       STATUS      mandatory
       DESCRIPTION
          "number of requests serviced per second"
       ::= { exchAdClntAccessAvailServEntry 3 }

--**************************************************************************  
--
-- exchAdClntAccessActSyncTable
--
--**************************************************************************

    exchAdClntAccessActSyncTable OBJECT-TYPE
       SYNTAX      SEQUENCE OF  ExchAdClntAccessActSyncEntry
       ACCESS      not-accessible
       STATUS      mandatory
       DESCRIPTION
           "client access ActiveSync table"
      ::= { exchAdPerformanceClientAccessRole 4 }

    exchAdClntAccessActSyncEntry OBJECT-TYPE
       SYNTAX      ExchAdClntAccessActSyncEntry
       ACCESS      not-accessible
       STATUS      mandatory
       DESCRIPTION
           "defines an entry in the exchAdClntAccessActSyncTable"

       INDEX {
                exchAdClntAccessActSyncHostIndex
             }
       ::= { exchAdClntAccessActSyncTable 1 }

    ExchAdClntAccessActSyncEntry ::=
       SEQUENCE {
           exchAdClntAccessActSyncHostIndex                     INTEGER,
           exchAdClntAccessActSyncPingCmdsPending               Gauge,
           exchAdClntAccessActSyncReqQueued                     Gauge,
           exchAdClntAccessActSyncReqPerSec                     Gauge,
           exchAdClntAccessActSyncSyncCmdsPerSec                Gauge,
           exchAdClntAccessActSyncSyncCmdsPending               Gauge
          }

    exchAdClntAccessActSyncHostIndex OBJECT-TYPE
       SYNTAX      INTEGER (0..2147483647)
       ACCESS      read-only
       STATUS      mandatory
       DESCRIPTION
          "unique index for each client access host, same as exchAdUniversalHostIndex"
       ::= { exchAdClntAccessActSyncEntry 1 }

    exchAdClntAccessActSyncPingCmdsPending OBJECT-TYPE
       SYNTAX      Gauge
       ACCESS      read-only
       STATUS      mandatory
       DESCRIPTION
          "number of Ping commands that are currently pending on the server"
       ::= { exchAdClntAccessActSyncEntry 2 }

    exchAdClntAccessActSyncReqQueued OBJECT-TYPE
       SYNTAX      Gauge
       ACCESS      read-only
       STATUS      mandatory
       DESCRIPTION
          "number of HTTP requests that are waiting to be assigned to a thread"
       ::= { exchAdClntAccessActSyncEntry 3 }

    exchAdClntAccessActSyncReqPerSec OBJECT-TYPE
       SYNTAX      Gauge
       ACCESS      read-only
       STATUS      mandatory
       DESCRIPTION
          "number of HTTP requests received from the client via ASP.NET per second"
       ::= { exchAdClntAccessActSyncEntry 4 }

    exchAdClntAccessActSyncSyncCmdsPerSec OBJECT-TYPE
       SYNTAX      Gauge
       ACCESS      read-only
       STATUS      mandatory
       DESCRIPTION
          "number of sync commands processed per second"
       ::= { exchAdClntAccessActSyncEntry 5 }

    exchAdClntAccessActSyncSyncCmdsPending  OBJECT-TYPE
       SYNTAX      Gauge
       ACCESS      read-only
       STATUS      mandatory
       DESCRIPTION
          "number of sync commands currently pending on the server"
       ::= { exchAdClntAccessActSyncEntry 6 }

--**************************************************************************  
--
-- exchAdClntAccessRpcHttpPxyTable
--
--**************************************************************************

    exchAdClntAccessRpcHttpPxyTable OBJECT-TYPE
       SYNTAX      SEQUENCE OF  ExchAdClntAccessRpcHttpPxyEntry
       ACCESS      not-accessible
       STATUS      mandatory
       DESCRIPTION
           "client access RPC/HTTP Proxy table"
      ::= { exchAdPerformanceClientAccessRole 5 }

    exchAdClntAccessRpcHttpPxyEntry OBJECT-TYPE
       SYNTAX      ExchAdClntAccessRpcHttpPxyEntry
       ACCESS      not-accessible
       STATUS      mandatory
       DESCRIPTION
           "defines an entry in the exchAdClntAccessRpcHttpPxyTable"

       INDEX {
                exchAdClntAccessRpcHttpPxyHostIndex
             }
       ::= { exchAdClntAccessRpcHttpPxyTable 1 }

    ExchAdClntAccessRpcHttpPxyEntry ::=
       SEQUENCE {
           exchAdClntAccessRpcHttpPxyHostIndex                  INTEGER,
           exchAdClntAccessRpcHttpPxyFailedBackEndConnAttempts  Gauge
          }

    exchAdClntAccessRpcHttpPxyHostIndex OBJECT-TYPE
       SYNTAX      INTEGER (0..2147483647)
       ACCESS      read-only
       STATUS      mandatory
       DESCRIPTION
          "unique index for each client access host, same as exchAdUniversalHostIndex"
       ::= { exchAdClntAccessRpcHttpPxyEntry 1 }

    exchAdClntAccessRpcHttpPxyFailedBackEndConnAttempts OBJECT-TYPE
       SYNTAX      Gauge
       ACCESS      read-only
       STATUS      mandatory
       DESCRIPTION
          "rate at which the RPC proxy attempts are occurring but fail to establish a connection to a back-end server"
       ::= { exchAdClntAccessRpcHttpPxyEntry 2 }

--**************************************************************************  
--
-- exchAdClntAccessRpcClntAccessTable
--
--**************************************************************************

    exchAdClntAccessRpcClntAccessTable OBJECT-TYPE
       SYNTAX      SEQUENCE OF  ExchAdClntAccessRpcClntAccessEntry
       ACCESS      not-accessible
       STATUS      mandatory
       DESCRIPTION
           "client access RPC Client Access table"
      ::= { exchAdPerformanceClientAccessRole 6 }

    exchAdClntAccessRpcClntAccessEntry OBJECT-TYPE
       SYNTAX      ExchAdClntAccessRpcClntAccessEntry
       ACCESS      not-accessible
       STATUS      mandatory
       DESCRIPTION
           "defines an entry in the exchAdClntAccessRpcClntAccessTable"

       INDEX {
                exchAdClntAccessRpcClntAccessHostIndex
             }
       ::= { exchAdClntAccessRpcClntAccessTable 1 }

    ExchAdClntAccessRpcClntAccessEntry ::=
       SEQUENCE {
           exchAdClntAccessRpcClntAccessHostIndex               INTEGER,
           exchAdClntAccessRpcClntAccessRpcAvgLatency           Gauge,
           exchAdClntAccessRpcClntAccessRpcOpsPerSec            Gauge,
           exchAdClntAccessRpcClntAccessRpcRequests             Gauge,
           exchAdClntAccessRpcClntAccessActiveUsers             Gauge,
           exchAdClntAccessRpcClntAccessConnections             Gauge,
           exchAdClntAccessRpcClntAccessUsers                   Gauge
          }

    exchAdClntAccessRpcClntAccessHostIndex OBJECT-TYPE
       SYNTAX      INTEGER (0..2147483647)
       ACCESS      read-only
       STATUS      mandatory
       DESCRIPTION
          "unique index for each client access host, same as exchAdUniversalHostIndex"
       ::= { exchAdClntAccessRpcClntAccessEntry 1 }

    exchAdClntAccessRpcClntAccessRpcAvgLatency OBJECT-TYPE
       SYNTAX      Gauge
       ACCESS      read-only
       STATUS      mandatory
       DESCRIPTION
          "average latency over last 1024 packets in milliseconds"
       ::= { exchAdClntAccessRpcClntAccessEntry 2 }

    exchAdClntAccessRpcClntAccessRpcOpsPerSec OBJECT-TYPE
       SYNTAX      Gauge
       ACCESS      read-only
       STATUS      mandatory
       DESCRIPTION
          "rate at which RPC operations occur per second"
       ::= { exchAdClntAccessRpcClntAccessEntry 3 }

    exchAdClntAccessRpcClntAccessRpcRequests OBJECT-TYPE
       SYNTAX      Gauge
       ACCESS      read-only
       STATUS      mandatory
       DESCRIPTION
          "number of client requests that are currently being processed by the RPC Client Access service"
       ::= { exchAdClntAccessRpcClntAccessEntry 4 }

    exchAdClntAccessRpcClntAccessActiveUsers OBJECT-TYPE
       SYNTAX      Gauge
       ACCESS      read-only
       STATUS      mandatory
       DESCRIPTION
          "number of unique users that have shown some activity in the last 2 minutes"
       ::= { exchAdClntAccessRpcClntAccessEntry 5 }

    exchAdClntAccessRpcClntAccessConnections OBJECT-TYPE
       SYNTAX      Gauge
       ACCESS      read-only
       STATUS      mandatory
       DESCRIPTION
          "total number of client connections maintained"
       ::= { exchAdClntAccessRpcClntAccessEntry 6 }

    exchAdClntAccessRpcClntAccessUsers OBJECT-TYPE
       SYNTAX      Gauge
       ACCESS      read-only
       STATUS      mandatory
       DESCRIPTION
          "number of users connected to the service"
       ::= { exchAdClntAccessRpcClntAccessEntry 7 }

--**************************************************************************  
--
-- exchAdClntAccessABTable
--
--**************************************************************************

    exchAdClntAccessABTable OBJECT-TYPE
       SYNTAX      SEQUENCE OF  ExchAdClntAccessABEntry
       ACCESS      not-accessible
       STATUS      mandatory
       DESCRIPTION
           "client access Address Book table"
      ::= { exchAdPerformanceClientAccessRole 7 }

    exchAdClntAccessABEntry OBJECT-TYPE
       SYNTAX      ExchAdClntAccessABEntry
       ACCESS      not-accessible
       STATUS      mandatory
       DESCRIPTION
           "defines an entry in the exchAdClntAccessABTable"

       INDEX {
                exchAdClntAccessABHostIndex
             }
       ::= { exchAdClntAccessABTable 1 }

    ExchAdClntAccessABEntry ::=
       SEQUENCE {
           exchAdClntAccessABHostIndex                          INTEGER,
           exchAdClntAccessABNspiRpcBrsReqAvgLatency            Gauge,
           exchAdClntAccessABNspiRpcReqAvgLatency               Gauge,
           exchAdClntAccessABRefRpcReqAvgLatency                Gauge
          }

    exchAdClntAccessABHostIndex OBJECT-TYPE
       SYNTAX      INTEGER (0..2147483647)
       ACCESS      read-only
       STATUS      mandatory
       DESCRIPTION
          "unique index for each client access host, same as exchAdUniversalHostIndex"
       ::= { exchAdClntAccessABEntry 1 }

    exchAdClntAccessABNspiRpcBrsReqAvgLatency OBJECT-TYPE
       SYNTAX      Gauge
       ACCESS      read-only
       STATUS      mandatory
       DESCRIPTION
          "average time that NSPI browse requests took to complete during the sampling period in milliseconds"
       ::= { exchAdClntAccessABEntry 2 }

    exchAdClntAccessABNspiRpcReqAvgLatency OBJECT-TYPE
       SYNTAX      Gauge
       ACCESS      read-only
       STATUS      mandatory
       DESCRIPTION
          "average time that NSPI requests took to complete during the sampling period in milliseconds"
       ::= { exchAdClntAccessABEntry 3 }

    exchAdClntAccessABRefRpcReqAvgLatency OBJECT-TYPE
       SYNTAX      Gauge
       ACCESS      read-only
       STATUS      mandatory
       DESCRIPTION
          "average time that referral requests took to complete during the sampling period in milliseconds"
       ::= { exchAdClntAccessABEntry 4 }

--**************************************************************************  
--
-- exchAdClntAccessCPTable
--
--**************************************************************************

    exchAdClntAccessCPTable OBJECT-TYPE
       SYNTAX      SEQUENCE OF  ExchAdClntAccessCPEntry
       ACCESS      not-accessible
       STATUS      mandatory
       DESCRIPTION
           "client access Control Panel table"
      ::= { exchAdPerformanceClientAccessRole 8 }

    exchAdClntAccessCPEntry OBJECT-TYPE
       SYNTAX      ExchAdClntAccessCPEntry
       ACCESS      not-accessible
       STATUS      mandatory
       DESCRIPTION
           "defines an entry in the exchAdClntAccessCPTable"

       INDEX {
                exchAdClntAccessCPHostIndex
             }
       ::= { exchAdClntAccessCPTable 1 }

    ExchAdClntAccessCPEntry ::=
       SEQUENCE {
           exchAdClntAccessCPHostIndex                          INTEGER,
           exchAdClntAccessCPOutPRAvgRespTime                   Gauge,
           exchAdClntAccessCPReqAvgRespTime                     Gauge,
           exchAdClntAccessCPAspNetReqFailedPerSec              Gauge,
           exchAdClntAccessCPExpSOInPxyReqPerSec                Gauge,
           exchAdClntAccessCPExpSOInPxySessionsPerSec           Gauge,
           exchAdClntAccessCPExpSOOutPxyReqPerSec               Gauge,
           exchAdClntAccessCPExpSOOutPxySessionsPerSec          Gauge,
           exchAdClntAccessCPExpSOStdRbacReqPerSec              Gauge,
           exchAdClntAccessCPExpSOStdRbacSessionsPerSec         Gauge,
           exchAdClntAccessCPInPxyReqPerSec                     Gauge,
           exchAdClntAccessCPInPxySessionsPerSec                Gauge,
           exchAdClntAccessCPOutPxyReqPerSec                    Gauge,
           exchAdClntAccessCPOutPxySessionsPerSec               Gauge,
           exchAdClntAccessCPPSRunSpcActPerSec                  Gauge,
           exchAdClntAccessCPPSRunSpcAcvgActiveTime             Gauge,
           exchAdClntAccessCPPSRunSpcPerSec                     Gauge,
           exchAdClntAccessCPRbacSessionsPerSec                 Gauge,
           exchAdClntAccessCPReqActPerSec                       Gauge
          }

    exchAdClntAccessCPHostIndex OBJECT-TYPE
       SYNTAX      INTEGER (0..2147483647)
       ACCESS      read-only
       STATUS      mandatory
       DESCRIPTION
          "unique index for each client access host, same as exchAdUniversalHostIndex"
       ::= { exchAdClntAccessCPEntry 1 }

    exchAdClntAccessCPOutPRAvgRespTime OBJECT-TYPE
       SYNTAX      Gauge
       ACCESS      read-only
       STATUS      mandatory
       DESCRIPTION
          "average time that requests sent to a secondary Client Access server took to complete during the sampling period in milliseconds"
       ::= { exchAdClntAccessCPEntry 2 }

    exchAdClntAccessCPReqAvgRespTime OBJECT-TYPE
       SYNTAX      Gauge
       ACCESS      read-only
       STATUS      mandatory
       DESCRIPTION
          "average time the Exchange Control Panel took to respond to a request during the sampling period in milliseconds"
       ::= { exchAdClntAccessCPEntry 3 }

    exchAdClntAccessCPAspNetReqFailedPerSec OBJECT-TYPE
       SYNTAX      Gauge
       ACCESS      read-only
       STATUS      mandatory
       DESCRIPTION
          "number of failures detected by ASP.NET in the Exchange Control Panel per second"
       ::= { exchAdClntAccessCPEntry 4 }

    exchAdClntAccessCPExpSOInPxyReqPerSec OBJECT-TYPE
       SYNTAX      Gauge
       ACCESS      read-only
       STATUS      mandatory
       DESCRIPTION
          "number of explicit sign-on requests received from a primary Client Access server per second"
       ::= { exchAdClntAccessCPEntry 5 }

    exchAdClntAccessCPExpSOInPxySessionsPerSec OBJECT-TYPE
       SYNTAX      Gauge
       ACCESS      read-only
       STATUS      mandatory
       DESCRIPTION
          "number of explicit sign-on inbound proxy sessions loaded in the Exchange Control Panel per second"
       ::= { exchAdClntAccessCPEntry 6 }

    exchAdClntAccessCPExpSOOutPxyReqPerSec OBJECT-TYPE
       SYNTAX      Gauge
       ACCESS      read-only
       STATUS      mandatory
       DESCRIPTION
          "number of explicit sign-on requests sent to a secondary Client Access server per second"
       ::= { exchAdClntAccessCPEntry 7 }

    exchAdClntAccessCPExpSOOutPxySessionsPerSec OBJECT-TYPE
       SYNTAX      Gauge
       ACCESS      read-only
       STATUS      mandatory
       DESCRIPTION
          "number of explicit sign-on outbound proxy sessions loaded in the Exchange Control Panel per second"
       ::= { exchAdClntAccessCPEntry 8 }

    exchAdClntAccessCPExpSOStdRbacReqPerSec OBJECT-TYPE
       SYNTAX      Gauge
       ACCESS      read-only
       STATUS      mandatory
       DESCRIPTION
          "number of requests received by an explicit sign-on standard RBAC session per second"
       ::= { exchAdClntAccessCPEntry 9 }

    exchAdClntAccessCPExpSOStdRbacSessionsPerSec OBJECT-TYPE
       SYNTAX      Gauge
       ACCESS      read-only
       STATUS      mandatory
       DESCRIPTION
          "number of explicit sign-on standard RBAC sessions loaded in the Exchange Control Panel per second"
       ::= { exchAdClntAccessCPEntry 10 }

    exchAdClntAccessCPInPxyReqPerSec OBJECT-TYPE
       SYNTAX      Gauge
       ACCESS      read-only
       STATUS      mandatory
       DESCRIPTION
          "number of requests received from a primary Client Access server per second"
       ::= { exchAdClntAccessCPEntry 11 }

    exchAdClntAccessCPInPxySessionsPerSec OBJECT-TYPE
       SYNTAX      Gauge
       ACCESS      read-only
       STATUS      mandatory
       DESCRIPTION
          "number of inbound proxy sessions loaded in the Exchange Control Panel per second"
       ::= { exchAdClntAccessCPEntry 12 }

    exchAdClntAccessCPOutPxyReqPerSec OBJECT-TYPE
       SYNTAX      Gauge
       ACCESS      read-only
       STATUS      mandatory
       DESCRIPTION
          "number of requests sent to a secondary Client Access server per second"
       ::= { exchAdClntAccessCPEntry 13 }

    exchAdClntAccessCPOutPxySessionsPerSec OBJECT-TYPE
       SYNTAX      Gauge
       ACCESS      read-only
       STATUS      mandatory
       DESCRIPTION
          "number of outbound proxy sessions loaded in the Exchange Control Panel per second"
       ::= { exchAdClntAccessCPEntry 14 }

    exchAdClntAccessCPPSRunSpcActPerSec OBJECT-TYPE
       SYNTAX      Gauge
       ACCESS      read-only
       STATUS      mandatory
       DESCRIPTION
          "number of Windows Powershell runspaces activated in the Exchange Control Panel per second"
       ::= { exchAdClntAccessCPEntry 15 }

    exchAdClntAccessCPPSRunSpcAcvgActiveTime OBJECT-TYPE
       SYNTAX      Gauge
       ACCESS      read-only
       STATUS      mandatory
       DESCRIPTION
          "average time that a Windows PowerShell runspace stays active while executing cmdlets in the Exchange Control Panel during the sampling period in seconds"
       ::= { exchAdClntAccessCPEntry 16 }

    exchAdClntAccessCPPSRunSpcPerSec OBJECT-TYPE
       SYNTAX      Gauge
       ACCESS      read-only
       STATUS      mandatory
       DESCRIPTION
          "number of Windows PowerShell runspaces created in the Exchange Control Panel per second"
       ::= { exchAdClntAccessCPEntry 17 }

    exchAdClntAccessCPRbacSessionsPerSec OBJECT-TYPE
       SYNTAX      Gauge
       ACCESS      read-only
       STATUS      mandatory
       DESCRIPTION
          "number of RBAC sessions loaded in the Exchange Control Panel per second"
       ::= { exchAdClntAccessCPEntry 18 }

    exchAdClntAccessCPReqActPerSec OBJECT-TYPE
       SYNTAX      Gauge
       ACCESS      read-only
       STATUS      mandatory
       DESCRIPTION
          "number of requests activated in the Exchange Control Panel per second"
       ::= { exchAdClntAccessCPEntry 19 }

--**************************************************************************  
--
-- exchAdClntAccessOABTable
--
--**************************************************************************

    exchAdClntAccessOABTable OBJECT-TYPE
       SYNTAX      SEQUENCE OF  ExchAdClntAccessOABEntry
       ACCESS      not-accessible
       STATUS      mandatory
       DESCRIPTION
           "client access Offline Address Book table"
      ::= { exchAdPerformanceClientAccessRole 9 }

    exchAdClntAccessOABEntry OBJECT-TYPE
       SYNTAX      ExchAdClntAccessOABEntry
       ACCESS      not-accessible
       STATUS      mandatory
       DESCRIPTION
           "defines an entry in the exchAdClntAccessOABTable"

       INDEX {
                exchAdClntAccessOABHostIndex,
                exchAdClntAccessOABIndex
             }
       ::= { exchAdClntAccessOABTable 1 }

    ExchAdClntAccessOABEntry ::=
       SEQUENCE {
           exchAdClntAccessOABHostIndex                         INTEGER,
           exchAdClntAccessOABIndex                             INTEGER,
           exchAdClntAccessOABID                                SnmpAdminString,
           exchAdClntAccessOABDnldTaskQueued                    Gauge,
           exchAdClntAccessOABDnldTasksCompleted                Gauge
          }

    exchAdClntAccessOABHostIndex OBJECT-TYPE
       SYNTAX      INTEGER (0..2147483647)
       ACCESS      read-only
       STATUS      mandatory
       DESCRIPTION
          "unique index for each client access host, same as exchAdUniversalHostIndex"
       ::= { exchAdClntAccessOABEntry 1 }

    exchAdClntAccessOABIndex OBJECT-TYPE
       SYNTAX      INTEGER (0..2147483647)
       ACCESS      read-only
       STATUS      mandatory
       DESCRIPTION
          "unique index for each Offline Address Book on the host"
       ::= { exchAdClntAccessOABEntry 2 }

    exchAdClntAccessOABID OBJECT-TYPE
       SYNTAX      SnmpAdminString
       ACCESS      read-only
       STATUS      mandatory
       DESCRIPTION
          "unique identifier for each Offline Address Book on the host"
       ::= { exchAdClntAccessOABEntry 3 }

    exchAdClntAccessOABDnldTaskQueued OBJECT-TYPE
       SYNTAX      Gauge
       ACCESS      read-only
       STATUS      mandatory
       DESCRIPTION
          "value of 1 if the task is queued for execution, otherwise shows 0"
       ::= { exchAdClntAccessOABEntry 4 }

    exchAdClntAccessOABDnldTasksCompleted OBJECT-TYPE
       SYNTAX      Gauge
       ACCESS      read-only
       STATUS      mandatory
       DESCRIPTION
          "number of OAB download tasks completed since the File Distribution service started"
       ::= { exchAdClntAccessOABEntry 5 }

--**************************************************************************  
--
-- exchAdClntAccessISTable
--
--**************************************************************************

    exchAdClntAccessISTable OBJECT-TYPE
       SYNTAX      SEQUENCE OF  ExchAdClntAccessISEntry
       ACCESS      not-accessible
       STATUS      mandatory
       DESCRIPTION
           "client access Information Store table"
      ::= { exchAdPerformanceClientAccessRole 10 }

    exchAdClntAccessISEntry OBJECT-TYPE
       SYNTAX      ExchAdClntAccessISEntry
       ACCESS      not-accessible
       STATUS      mandatory
       DESCRIPTION
           "defines an entry in the exchAdClntAccessISTable"

       INDEX {
                exchAdClntAccessISHostIndex
             }
       ::= { exchAdClntAccessISTable 1 }

    ExchAdClntAccessISEntry ::=
       SEQUENCE {
           exchAdClntAccessISHostIndex                          INTEGER,
           exchAdClntAccessISRpcClntBkoffPerSec                 Gauge
          }

    exchAdClntAccessISHostIndex OBJECT-TYPE
       SYNTAX      INTEGER (0..2147483647)
       ACCESS      read-only
       STATUS      mandatory
       DESCRIPTION
          "unique index for each client access host, same as exchAdUniversalHostIndex"
       ::= { exchAdClntAccessISEntry 1 }

    exchAdClntAccessISRpcClntBkoffPerSec OBJECT-TYPE
       SYNTAX      Gauge
       ACCESS      read-only
       STATUS      mandatory
       DESCRIPTION
          "rate at which client backoffs are occurring per second"
       ::= { exchAdClntAccessISEntry 2 }

--**************************************************************************  
--
-- exchAdClntAccessMiscPerformanceTable
--
--**************************************************************************

    exchAdClntAccessMiscPerformanceTable OBJECT-TYPE
       SYNTAX      SEQUENCE OF  ExchAdClntAccessMiscPerformanceEntry
       ACCESS      not-accessible
       STATUS      mandatory
       DESCRIPTION
           "client access miscellaneous performance metrics table"
      ::= { exchAdPerformanceClientAccessRole 11 }

    exchAdClntAccessMiscPerformanceEntry OBJECT-TYPE
       SYNTAX      ExchAdClntAccessMiscPerformanceEntry
       ACCESS      not-accessible
       STATUS      mandatory
       DESCRIPTION
           "defines an entry in the exchAdClntAccessMiscPerformanceTable"

       INDEX {
                exchAdClntAccessMiscPerformanceHostIndex
             }
       ::= { exchAdClntAccessMiscPerformanceTable 1 }

    ExchAdClntAccessMiscPerformanceEntry ::=
       SEQUENCE {
           exchAdClntAccessMiscPerformanceHostIndex                     INTEGER,
           exchAdClntAccessMiscPerformanceADReqPerSec                   Gauge,
           exchAdClntAccessMiscPerformanceWSReqPerSec                   Gauge,
           exchAdClntAccessMiscPerformanceWSTotCurrConn                 Gauge,
           exchAdClntAccessMiscPerformanceWSTotConnAttemptsPerSec       Gauge,
           exchAdClntAccessMiscPerformanceWSTotIsapiExtReqPerSec        Gauge,
           exchAdClntAccessMiscPerformanceWSTotOtherReqMethPerSec       Gauge
          }

    exchAdClntAccessMiscPerformanceHostIndex OBJECT-TYPE
       SYNTAX      INTEGER (0..2147483647)
       ACCESS      read-only
       STATUS      mandatory
       DESCRIPTION
          "unique index for each client access host, same as exchAdUniversalHostIndex"
       ::= { exchAdClntAccessMiscPerformanceEntry 1 }

    exchAdClntAccessMiscPerformanceADReqPerSec OBJECT-TYPE
       SYNTAX      Gauge
       ACCESS      read-only
       STATUS      mandatory
       DESCRIPTION
          "number of Autodiscover service requests processed per second"
       ::= { exchAdClntAccessMiscPerformanceEntry 2 }

    exchAdClntAccessMiscPerformanceWSReqPerSec OBJECT-TYPE
       SYNTAX      Gauge
       ACCESS      read-only
       STATUS      mandatory
       DESCRIPTION
          "number of Web Service requests processed per second"
       ::= { exchAdClntAccessMiscPerformanceEntry 3 }

    exchAdClntAccessMiscPerformanceWSTotCurrConn OBJECT-TYPE
       SYNTAX      Gauge
       ACCESS      read-only
       STATUS      mandatory
       DESCRIPTION
          "current number of connections established with the Web service"
       ::= { exchAdClntAccessMiscPerformanceEntry 4 }

    exchAdClntAccessMiscPerformanceWSTotConnAttemptsPerSec OBJECT-TYPE
       SYNTAX      Gauge
       ACCESS      read-only
       STATUS      mandatory
       DESCRIPTION
          "rate that connections to the Web service are being attempted per second"
       ::= { exchAdClntAccessMiscPerformanceEntry 5 }

    exchAdClntAccessMiscPerformanceWSTotIsapiExtReqPerSec OBJECT-TYPE
       SYNTAX      Gauge
       ACCESS      read-only
       STATUS      mandatory
       DESCRIPTION
          "rate that Internet Server API (ISAPI) extension requests are received by the Web service per second"
       ::= { exchAdClntAccessMiscPerformanceEntry 6 }

    exchAdClntAccessMiscPerformanceWSTotOtherReqMethPerSec OBJECT-TYPE
       SYNTAX      Gauge
       ACCESS      read-only
       STATUS      mandatory
       DESCRIPTION
          "rate HTTP requests are made that don't use the OPTIONS, GET, HEAD, POST, PUT, DELETE, TRACE, MOVE, COPY, MKCOL, PROPFIND, PROPPATCH, SEARCH, LOCK, or UNLOCK methods per second"
       ::= { exchAdClntAccessMiscPerformanceEntry 7 }


--**************************************************************************  
--**************************************************************************  
--
-- Windows Event Table
--
--**************************************************************************
--**************************************************************************  

   exchAdWindowsEventTable OBJECT-TYPE
       SYNTAX      SEQUENCE OF ExchAdWindowsEventEntry
       ACCESS      not-accessible
       STATUS      mandatory
       DESCRIPTION
           "Windows event table"
       ::= { exchAdWindowsEvents 1 }

   exchAdWindowsEventEntry OBJECT-TYPE
       SYNTAX      ExchAdWindowsEventEntry
       ACCESS      not-accessible
       STATUS      mandatory
       DESCRIPTION
           "defines an entry in the exchAdWindowsEventTable"
       INDEX { 
                exchAdWindowsEventHostIndex,
                exchAdWindowsEventIndex
             }
       ::= { exchAdWindowsEventTable 1 }

   ExchAdWindowsEventEntry ::=
       SEQUENCE {
           exchAdWindowsEventHostIndex                  INTEGER,                        
           exchAdWindowsEventTimeCreated                SnmpAdminString,
           exchAdWindowsEventIndex                      INTEGER,
           exchAdWindowsEventHost                       SnmpAdminString,
           exchAdWindowsEventProviderName               SnmpAdminString,
           exchAdWindowsEventId                         INTEGER,
           exchAdWindowsEventLevel                      INTEGER,
           exchAdWindowsEventData                       SnmpAdminString
       }

   exchAdWindowsEventHostIndex OBJECT-TYPE
       SYNTAX      INTEGER (0..2147483647)
       ACCESS      read-only
       STATUS      mandatory
       DESCRIPTION
          "index of host that generated the event, same as exchAdUniversalHostIndex"
       ::= { exchAdWindowsEventEntry 1 }

   exchAdWindowsEventTimeCreated OBJECT-TYPE
       SYNTAX      SnmpAdminString
       ACCESS      read-only
       STATUS      mandatory
       DESCRIPTION
          "event creation time"
       ::= { exchAdWindowsEventEntry 2 }

   exchAdWindowsEventIndex OBJECT-TYPE
       SYNTAX      INTEGER (0..2147483647)
       ACCESS      read-only
       STATUS      mandatory
       DESCRIPTION
          "unique index for each event for a given host and creation time - this value ascends for newer events"
       ::= { exchAdWindowsEventEntry 3 }

   exchAdWindowsEventHost OBJECT-TYPE
       SYNTAX     SnmpAdminString
       ACCESS      read-only
       STATUS      mandatory
       DESCRIPTION
          "name of host that generated the event"
       ::= { exchAdWindowsEventEntry 4 }

   exchAdWindowsEventProviderName OBJECT-TYPE
       SYNTAX     SnmpAdminString
       ACCESS      read-only
       STATUS      mandatory
       DESCRIPTION
          "generating application"
       ::= { exchAdWindowsEventEntry 5 }

   exchAdWindowsEventId OBJECT-TYPE
       SYNTAX      INTEGER
       ACCESS      read-only
       STATUS      mandatory
       DESCRIPTION
          "unique index for each event for a given host and creation time"
       ::= { exchAdWindowsEventEntry 6 }

   exchAdWindowsEventLevel OBJECT-TYPE
       SYNTAX      INTEGER { information(1), warning(2), critical(3) }
       ACCESS      read-only
       STATUS      mandatory
       DESCRIPTION
          "event severity"
       ::= { exchAdWindowsEventEntry 7 }

   exchAdWindowsEventData OBJECT-TYPE
       SYNTAX     SnmpAdminString
       ACCESS      read-only
       STATUS      mandatory
       DESCRIPTION
          "event specific data, maximum 255 characters"
       ::= { exchAdWindowsEventEntry 8 }


--**************************************************************************
--**************************************************************************
--
-- DAG Parameters
--
--**************************************************************************
--**************************************************************************

--**************************************************************************  
--
-- exchAdDagTable
--
--**************************************************************************

   exchAdDagTable OBJECT-TYPE
       SYNTAX      SEQUENCE OF ExchAdDagEntry
       ACCESS      not-accessible
       STATUS      mandatory
       DESCRIPTION
           "data availability group table"
      ::= { exchAdDag 1 }

   exchAdDagEntry OBJECT-TYPE
       SYNTAX      ExchAdDagEntry
       ACCESS      not-accessible
       STATUS      mandatory
       DESCRIPTION
           "defines an entry in the exchAdDagTable"

       INDEX {
                exchAdDagIndex
             }
       ::= { exchAdDagTable 1 }

   ExchAdDagEntry ::=
       SEQUENCE {
           exchAdDagIndex                    INTEGER,
           exchAdDagName                     SnmpAdminString,
           exchAdDagWitnessServerIndex       INTEGER,
           exchAdDagWitnessDirectory         SnmpAdminString,
           exchAdDagAltWitnessServerIndex    INTEGER,
           exchAdDagAltWitnessDirectory      SnmpAdminString,
           exchAdDagNetworkCompression       INTEGER,    
           exchAdDagNetworkEncryptionStatus  INTEGER,           
           exchAdDagDataCenterActivationMode INTEGER,
           exchAdDagIpv4Addresses            SnmpAdminString,
           exchAdDagServers                  SnmpAdminString,
           exchAdPrimaryActiveManagerIndex   INTEGER,
           exchAdDagThirdPartyReplStatus     INTEGER,
           exchAdDagReplicaPort              INTEGER,
           exchAdDagOrigServerIndex          INTEGER,
           exchAdDagIdentity                 SnmpAdminString
       }

   exchAdDagIndex  OBJECT-TYPE
       SYNTAX      INTEGER (0..2147483647)
       ACCESS      read-only
       STATUS      mandatory
       DESCRIPTION
          "unique index for each DAG"
       ::= { exchAdDagEntry 1 }

   exchAdDagName  OBJECT-TYPE
       SYNTAX      SnmpAdminString
       ACCESS      read-only
       STATUS      mandatory
       DESCRIPTION
          "name of Database Availability Group"
       ::= { exchAdDagEntry 2 }

   exchAdDagWitnessServerIndex  OBJECT-TYPE
       SYNTAX      INTEGER
       ACCESS      read-only
       STATUS      mandatory
       DESCRIPTION
          "index of Witness Server in exchAdUniversalHostTable, same as exchAdUniversalHostIndex"
       ::= { exchAdDagEntry 3 }

   exchAdDagWitnessDirectory  OBJECT-TYPE
       SYNTAX      SnmpAdminString
       ACCESS      read-only
       STATUS      mandatory
       DESCRIPTION
          "name and path of the directory used to store quorum data on the witness server"
       ::= { exchAdDagEntry 4 }

   exchAdDagAltWitnessServerIndex  OBJECT-TYPE
       SYNTAX      INTEGER
       ACCESS      read-only
       STATUS      mandatory
       DESCRIPTION
          "index of Alternate Witness Server in exchAdUniversalHostTable, same as exchAdUniversalHostIndex"
       ::= { exchAdDagEntry 5 }

   exchAdDagAltWitnessDirectory  OBJECT-TYPE
       SYNTAX      SnmpAdminString
       ACCESS      read-only
       STATUS      mandatory
       DESCRIPTION
          "name and path of the directory used to store quorum data on the alternate witness server"
       ::= { exchAdDagEntry 6 }

   exchAdDagNetworkCompression  OBJECT-TYPE
       SYNTAX      INTEGER {enabled(1), disabled(2), intersubnetOnly(3), seedOnly(4)}
       ACCESS      read-only
       STATUS      mandatory
       DESCRIPTION
          "network compression status"
       ::= { exchAdDagEntry 7 }

   exchAdDagNetworkEncryptionStatus  OBJECT-TYPE
       SYNTAX      INTEGER {enabled(1), disabled(2), intersubnetOnly(3), seedOnly(4)}
       ACCESS      read-only
       STATUS      mandatory
       DESCRIPTION
          "network encryption status"
       ::= { exchAdDagEntry 8 }

   exchAdDagDataCenterActivationMode  OBJECT-TYPE
       SYNTAX      INTEGER {off(1), dagonly(2)}
       ACCESS      read-only
       STATUS      mandatory
       DESCRIPTION
          "data center activation mode"
       ::= { exchAdDagEntry 9 }

   exchAdDagIpv4Addresses  OBJECT-TYPE
       SYNTAX      SnmpAdminString
       ACCESS      read-only
       STATUS      mandatory
       DESCRIPTION
          "DAG IP V4 addresses: string with multiple IP addresses"
       ::= { exchAdDagEntry 10 }

   exchAdDagServers  OBJECT-TYPE
       SYNTAX      SnmpAdminString
       ACCESS      read-only
       STATUS      mandatory
       DESCRIPTION
          "DAG servers: string with multiple server names"
       ::= { exchAdDagEntry 11 }

   exchAdPrimaryActiveManagerIndex  OBJECT-TYPE
       SYNTAX      INTEGER
       ACCESS      read-only
       STATUS      mandatory
       DESCRIPTION
          "index of primary active manager in DAG in exchAdUniversalHostTable, same as exchAdUniversalHostIndex"
       ::= { exchAdDagEntry 12 }

   exchAdDagThirdPartyReplStatus  OBJECT-TYPE
       SYNTAX      INTEGER {enabled(1), disabled(2)}
       ACCESS      read-only
       STATUS      mandatory
       DESCRIPTION
          "third party replication status"
       ::= { exchAdDagEntry 13 }

   exchAdDagReplicaPort  OBJECT-TYPE
       SYNTAX      INTEGER
       ACCESS      read-only
       STATUS      mandatory
       DESCRIPTION
          "replication port on which DAG is running"
       ::= { exchAdDagEntry 14 }

   exchAdDagOrigServerIndex  OBJECT-TYPE
       SYNTAX      INTEGER
       ACCESS      read-only
       STATUS      mandatory
       DESCRIPTION
          "pointer to DC machine from which EMS gets the data in exchAdUniversalHostTable, same as exchAdUniversalHostIndex"
       ::= { exchAdDagEntry 15 }

   exchAdDagIdentity  OBJECT-TYPE
       SYNTAX      SnmpAdminString
       ACCESS      read-only
       STATUS      mandatory
       DESCRIPTION
          "Identity of the DAG"
       ::= { exchAdDagEntry 16 }

--**************************************************************************  
--
-- exchAdDagHostTable
--
--**************************************************************************

   exchAdDagHostTable OBJECT-TYPE
       SYNTAX      SEQUENCE OF ExchAdDagHostEntry
       ACCESS      not-accessible
       STATUS      mandatory
       DESCRIPTION
           "data availability group host table"
      ::= { exchAdDag 2 }

    exchAdDagHostEntry OBJECT-TYPE
       SYNTAX      ExchAdDagHostEntry
       ACCESS      not-accessible
       STATUS      mandatory
       DESCRIPTION
           "defines an entry in the exchAdDagHostTable"

       INDEX {
                exchAdDagHostIndex
             }
       ::= { exchAdDagHostTable 1 }

    ExchAdDagHostEntry ::=
       SEQUENCE {

           exchAdDagHostIndex               INTEGER,
           exchAdDagHostStartStopStatus     INTEGER,
           exchAdDagHostOperStatus          INTEGER,
           exchAdDagHostDagIndex            INTEGER
       }

   exchAdDagHostIndex OBJECT-TYPE
       SYNTAX      INTEGER (0..2147483647)
       ACCESS      read-only
       STATUS      mandatory
       DESCRIPTION
          "unique index for each DAG host, same as exchAdUniversalHostIndex"
       ::= { exchAdDagHostEntry 1 }

   exchAdDagHostStartStopStatus OBJECT-TYPE
       SYNTAX      INTEGER {started(1), stopped(2)}
       ACCESS      read-only
       STATUS      mandatory
       DESCRIPTION
          "DAG host start/stop status"
       ::= { exchAdDagHostEntry 2 }

   exchAdDagHostOperStatus OBJECT-TYPE
       SYNTAX      INTEGER {operational(1), nonOperational(2)}
       ACCESS      read-only
       STATUS      mandatory
       DESCRIPTION
          "DAG  host operational status"
       ::= { exchAdDagHostEntry 3 }

   exchAdDagHostDagIndex OBJECT-TYPE
       SYNTAX      INTEGER
       ACCESS      read-only
       STATUS      mandatory
       DESCRIPTION
          "index of associated DAG in exchAdDagTable"
       ::= { exchAdDagHostEntry 4 }

--**************************************************************************  
--
-- exchAdDagNetworkTable
--
--**************************************************************************

   exchAdDagNetworkTable OBJECT-TYPE
       SYNTAX      SEQUENCE OF ExchAdDagNetworkEntry
       ACCESS      not-accessible
       STATUS      mandatory
       DESCRIPTION
           "data availability group network table"
      ::= { exchAdDag 3 }

    exchAdDagNetworkEntry OBJECT-TYPE
       SYNTAX      ExchAdDagNetworkEntry
       ACCESS      not-accessible
       STATUS      mandatory
       DESCRIPTION
           "defines an entry in the exchAdDagNeworkTable"

       INDEX {
                exchAdDagNetworkIndex
             }
       ::= { exchAdDagNetworkTable 1 }

    ExchAdDagNetworkEntry ::=
       SEQUENCE {
          exchAdDagNetworkIndex             INTEGER,
          exchAdDagNetworkName              SnmpAdminString,
          exchAdDagNetworkMapIAccess        INTEGER,
          exchAdDagNetworkReplication       INTEGER,
          exchAdDagNetworkIgnoreNetwork     INTEGER,
          exchAdDagNetworkIdentity          SnmpAdminString,
          exchAdDagNetworkDagIndex          INTEGER
       }

   exchAdDagNetworkIndex OBJECT-TYPE
       SYNTAX      INTEGER (0..2147483647)
       ACCESS      read-only
       STATUS      mandatory
       DESCRIPTION
          "unique index for each DAG network"
       ::= { exchAdDagNetworkEntry 1 }

   exchAdDagNetworkName OBJECT-TYPE
       SYNTAX      SnmpAdminString
       ACCESS      read-only
       STATUS      mandatory
       DESCRIPTION
          "name of DAG network"
       ::= { exchAdDagNetworkEntry 2 }

   exchAdDagNetworkMapIAccess OBJECT-TYPE
       SYNTAX      INTEGER {enabled(1), disabled(2)}
       ACCESS      read-only
       STATUS      mandatory
       DESCRIPTION
          "whether Mapi Access is enabled"
       ::= { exchAdDagNetworkEntry 3 }

   exchAdDagNetworkReplication OBJECT-TYPE
       SYNTAX      INTEGER {enabled(1), disabled(2)}
       ACCESS      read-only
       STATUS      mandatory
       DESCRIPTION
          "whether Replication is enabled"
       ::= { exchAdDagNetworkEntry 4 }

   exchAdDagNetworkIgnoreNetwork OBJECT-TYPE
       SYNTAX      INTEGER {ignore(1), doNotIgnore(2)}
       ACCESS      read-only
       STATUS      mandatory
       DESCRIPTION
          " whether the DAG network is ignored"
       ::= { exchAdDagNetworkEntry 5 }

   exchAdDagNetworkIdentity OBJECT-TYPE
       SYNTAX      SnmpAdminString
       ACCESS      read-only
       STATUS      mandatory
       DESCRIPTION
          "DAG network identity"
       ::= { exchAdDagNetworkEntry 6 }

   exchAdDagNetworkDagIndex OBJECT-TYPE
       SYNTAX      INTEGER
       ACCESS      read-only
       STATUS      mandatory
       DESCRIPTION
          "pointer to associated DAG in exchAdDagTable"
       ::= { exchAdDagNetworkEntry 7 }

--**************************************************************************  
--
-- exchAdDagSubnetTable
--
--**************************************************************************

   exchAdDagSubnetTable OBJECT-TYPE
       SYNTAX      SEQUENCE OF ExchAdDagSubnetEntry
       ACCESS      not-accessible
       STATUS      mandatory
       DESCRIPTION
           "data availability group subnet table"
      ::= { exchAdDag 4 }

    exchAdDagSubnetEntry OBJECT-TYPE
       SYNTAX      ExchAdDagSubnetEntry
       ACCESS      not-accessible
       STATUS      mandatory
       DESCRIPTION
           "defines an entry in the exchAdDagSubnetTable"

       INDEX {
                exchAdDagSubnetIndex
             }
       ::= { exchAdDagSubnetTable 1 }

    ExchAdDagSubnetEntry ::=
       SEQUENCE {
          exchAdDagSubnetIndex         INTEGER,
          exchAdDagSubnetName          SnmpAdminString,
          exchAdDagSubnetState         INTEGER,
          exchAdDagSubnetDagIndex      INTEGER,
          exchAdDagSubnetNetworkIndex  INTEGER
       }

   exchAdDagSubnetIndex OBJECT-TYPE
       SYNTAX      INTEGER (0..2147483647)
       ACCESS      read-only
       STATUS      mandatory
       DESCRIPTION
          "unique index for each DAG subnet"
       ::= { exchAdDagSubnetEntry 1 }

   exchAdDagSubnetName OBJECT-TYPE
       SYNTAX      SnmpAdminString
       ACCESS      read-only
       STATUS      mandatory
       DESCRIPTION
          "name of DAG subnet"
       ::= { exchAdDagSubnetEntry 2 }

   exchAdDagSubnetState OBJECT-TYPE
       SYNTAX      INTEGER {up(1), down(2), partitioned(3), misconfigured(4), unavailable(5), unknown(6)}
       ACCESS      read-only
       STATUS      mandatory
       DESCRIPTION
          "state of DAG subnet"
       ::= { exchAdDagSubnetEntry 3 }

   exchAdDagSubnetDagIndex OBJECT-TYPE
       SYNTAX      INTEGER
       ACCESS      read-only
       STATUS      mandatory
       DESCRIPTION
          "pointer to associated DAG in exchAdDagTable"
       ::= { exchAdDagSubnetEntry 4 }

   exchAdDagSubnetNetworkIndex OBJECT-TYPE
       SYNTAX      INTEGER
       ACCESS      read-only
       STATUS      mandatory
       DESCRIPTION
          "pointer to associated network in exchAdDagNetworkTable"
       ::= { exchAdDagSubnetEntry 5 }

--**************************************************************************  
--
-- exchAdDagNetworkInterfaceTable
--
--**************************************************************************

   exchAdDagNetworkInterfaceTable OBJECT-TYPE
       SYNTAX      SEQUENCE OF ExchAdDagNetworkInterfaceEntry
       ACCESS      not-accessible
       STATUS      mandatory
       DESCRIPTION
           "data availability group network interface table"
      ::= { exchAdDag 5 }

    exchAdDagNetworkInterfaceEntry OBJECT-TYPE
       SYNTAX      ExchAdDagNetworkInterfaceEntry
       ACCESS      not-accessible
       STATUS      mandatory
       DESCRIPTION
           "defines an entry in the exchAdDagNetworkInterfaceTable"

       INDEX {
                exchAdDagNetworkInterfaceIndex
             }
       ::= { exchAdDagNetworkInterfaceTable 1 }

    ExchAdDagNetworkInterfaceEntry ::=
       SEQUENCE {
          exchAdDagNetworkInterfaceIndex        INTEGER,
          exchAdDagNetworkInterfaceName         SnmpAdminString,
          exchAdDagNetworkInterfaceStatus       INTEGER,
          exchAdDagNetworkInterfaceDagIndex     INTEGER,
          exchAdDagNetworkInterfaceHostIndex    INTEGER
            }

   exchAdDagNetworkInterfaceIndex OBJECT-TYPE
       SYNTAX      INTEGER (0..2147483647)
       ACCESS      read-only
       STATUS      mandatory
       DESCRIPTION
          "unique index for each DAG network interface"
       ::= { exchAdDagNetworkInterfaceEntry 1 }

   exchAdDagNetworkInterfaceName OBJECT-TYPE
       SYNTAX      SnmpAdminString
       ACCESS      read-only
       STATUS      mandatory
       DESCRIPTION
          "DAG network interface name"
       ::= { exchAdDagNetworkInterfaceEntry 2 }

   exchAdDagNetworkInterfaceStatus OBJECT-TYPE
       SYNTAX      INTEGER {up(1), failed(2), unreachable(3), unavailable(4), unknown(5) }
       ACCESS      read-only
       STATUS      mandatory
       DESCRIPTION
          "status of DAG network interface"
       ::= { exchAdDagNetworkInterfaceEntry 3 }

   exchAdDagNetworkInterfaceDagIndex OBJECT-TYPE
       SYNTAX      INTEGER
       ACCESS      read-only
       STATUS      mandatory
       DESCRIPTION
          "pointer to associated DAG in exchAdDagTable"
       ::= { exchAdDagNetworkInterfaceEntry 4 }

   exchAdDagNetworkInterfaceHostIndex OBJECT-TYPE
       SYNTAX      INTEGER
       ACCESS      read-only
       STATUS      obsolete
       DESCRIPTION
          "pointer to associated DAG mailbox host, same as exchAdUniversalHostIndex - this object is obsolete"
       ::= { exchAdDagNetworkInterfaceEntry 5 }

--**************************************************************************  
--
-- exchAdDagDatabaseCopyTable
--
-- This table's implementation was changed from version 1.0 to version 1.1. The
-- 1.0 version of this MIB was never implemented by the ADES AIM agent.
--
--**************************************************************************

   exchAdDagDatabaseCopyTable OBJECT-TYPE
       SYNTAX      SEQUENCE OF ExchAdDagDatabaseCopyEntry
       ACCESS      not-accessible
       STATUS      mandatory
       DESCRIPTION
           "data availability group database copy table"
      ::= { exchAdDag 6 }

   exchAdDagDatabaseCopyEntry OBJECT-TYPE
       SYNTAX      ExchAdDagDatabaseCopyEntry
       ACCESS      not-accessible
       STATUS      mandatory
       DESCRIPTION
           "defines an entry in the exchAdDagDatabaseCopyTable"

       INDEX {
                exchAdDagDatabaseCopyIndex
             }
       ::= { exchAdDagDatabaseCopyTable 1 }

    ExchAdDagDatabaseCopyEntry ::=
       SEQUENCE {
          exchAdDagDatabaseCopyIndex                                        INTEGER,
          exchAdDagDatabaseInventoryIndex                                   INTEGER,
          exchAdDagDatabaseCopyDbaseMountStatus                             INTEGER,
          exchAdDagDatabaseCopyMailboxServerIndex                           INTEGER,
          exchAdDagDatabaseCopyActiveDatabaseCopyIndex                      INTEGER,
          exchAdDagDatabaseCopyActivationStatus                             INTEGER,
          exchAdDagDatabaseCopyActionInitiator                              SnmpAdminString,
          exchAdDagDatabaseCopyErrorMessage                                 SnmpAdminString,
          exchAdDagDatabaseCopyErrorEventId                                 INTEGER,
          exchAdDagDatabaseCopyExtendedErrorInfo                            SnmpAdminString,
          exchAdDagDatabaseCopySinglePageRestores                           Counter,
          exchAdDagDatabaseCopyContentIndexHealthStatus                     INTEGER,     
          exchAdDagDatabaseCopyCopyQueueLength                              Gauge,
          exchAdDagDatabaseCopyReplayQueueLength                            Gauge,
          exchAdDagDatabaseCopyDbaseLatestAvailableLogTime                  SnmpAdminString,
          exchAdDagDatabaseCopyDbaseLastCopyNotificationedLogTime           SnmpAdminString,
          exchAdDagDatabaseCopyDbaseLastCopiedLogTime                       SnmpAdminString,
          exchAdDagDatabaseCopyDbaseLastInspectedLogTime                    SnmpAdminString,
          exchAdDagDatabaseCopyDbaseLastReplayedLogTime                     SnmpAdminString,
          exchAdDagDatabaseCopyDbaseLastLogGenerated                        SnmpAdminString,
          exchAdDagDatabaseCopyDbaseLastLogCopyNotified                     SnmpAdminString,
          exchAdDagDatabaseCopyDbaseLastLogCopied                           SnmpAdminString,
          exchAdDagDatabaseCopyDbaseLastLogInspected                        SnmpAdminString,
          exchAdDagDatabaseCopyDbaseLastLogReplayed                         SnmpAdminString,
          exchAdDagDatabaseCopyDbaseLatestFullBackupTime                    SnmpAdminString,
          exchAdDagDatabaseCopyDbaseLatestIncrementalBackupTime             SnmpAdminString,
          exchAdDagDatabaseCopyDbaseLatestDifferentialBackupTime            SnmpAdminString,
          exchAdDagDatabaseCopyDbaseLatestCopyBackupTime                    SnmpAdminString,
          exchAdDagDatabaseCopyDbaseLatestSnapshotBackupTime                SnmpAdminString,
          exchAdDagDatabaseCopyDbaseLatestSnapshotFullBackupTime            SnmpAdminString,
          exchAdDagDatabaseCopyDbaseLatestSnapshotIncrementalBackupTime     SnmpAdminString,
          exchAdDagDatabaseCopyDbaseLatestSnapshotDifferentialBackupTime    SnmpAdminString,
          exchAdDagDatabaseCopyDbaseLatestSnapshotCopyBackupTime            SnmpAdminString,
          exchAdDagDatabaseCopyDbaseLogReplayQueueIncreasing                INTEGER,
          exchAdDagDatabaseCopyDbaseLogCopyQueueIncreasing                  INTEGER,
          exchAdDagDatabaseCopyDbaseOutstandingDumpsterRequests             Gauge,
          exchAdDagDatabaseCopyDbaseOutgoingConnections                     Gauge,
          exchAdDagDatabaseCopyDbaseIncomingLogCopyingNetwork               SnmpAdminString,
          exchAdDagDatabaseCopyDbaseSeedingNetwork                          SnmpAdminString,
          exchAdDagDatabaseCopyDbaseActiveCopy                              INTEGER,
          exchAdDagDatabaseCopyDbaseCopyMailboxHostIndex                    INTEGER
            }

   exchAdDagDatabaseCopyIndex OBJECT-TYPE
       SYNTAX      INTEGER (0..2147483647)
       ACCESS      read-only
       STATUS      mandatory
       DESCRIPTION
          "unique index for each mailbox database copy"
       ::= { exchAdDagDatabaseCopyEntry 1 }

   exchAdDagDatabaseInventoryIndex OBJECT-TYPE
       SYNTAX      INTEGER
       ACCESS      read-only
       STATUS      mandatory
       DESCRIPTION
          "pointer to database in exchAdMailboxDatabaseInventoryTable"
       ::= { exchAdDagDatabaseCopyEntry 2 }

   exchAdDagDatabaseCopyDbaseMountStatus OBJECT-TYPE
       SYNTAX      INTEGER {mounted(1), unmounted(2), failed(3)}
       ACCESS      read-only
       STATUS      mandatory
       DESCRIPTION
          "mount status of associated database"
       ::= { exchAdDagDatabaseCopyEntry 3 }

   exchAdDagDatabaseCopyMailboxServerIndex OBJECT-TYPE
       SYNTAX      INTEGER
       ACCESS      read-only
       STATUS      mandatory
       DESCRIPTION
          "pointer to mailbox server, same as exchAdUniversalHostIndex"
       ::= { exchAdDagDatabaseCopyEntry 4 }

   exchAdDagDatabaseCopyActiveDatabaseCopyIndex OBJECT-TYPE
       SYNTAX      INTEGER
       ACCESS      read-only
       STATUS      mandatory
       DESCRIPTION
          "pointer to server on which active database copy is located, same as exchAdUniversalHostIndex"
       ::= { exchAdDagDatabaseCopyEntry 5 }

   exchAdDagDatabaseCopyActivationStatus OBJECT-TYPE
       SYNTAX      INTEGER {active(1), suspended(2)}
       ACCESS      read-only
       STATUS      mandatory
       DESCRIPTION
          "database copy activation status"
       ::= { exchAdDagDatabaseCopyEntry 6 }

   exchAdDagDatabaseCopyActionInitiator OBJECT-TYPE
       SYNTAX      SnmpAdminString
       ACCESS      read-only
       STATUS      mandatory
       DESCRIPTION
          "action initiator of the Database copy"
       ::= { exchAdDagDatabaseCopyEntry 7 }

   exchAdDagDatabaseCopyErrorMessage OBJECT-TYPE
       SYNTAX      SnmpAdminString
       ACCESS      read-only
       STATUS      mandatory
       DESCRIPTION
          "error messages if any"
       ::= { exchAdDagDatabaseCopyEntry 8 }

   exchAdDagDatabaseCopyErrorEventId OBJECT-TYPE
       SYNTAX      INTEGER
       ACCESS      read-only
       STATUS      mandatory
       DESCRIPTION
          "error Event ID of any error message"
       ::= { exchAdDagDatabaseCopyEntry 9 }

   exchAdDagDatabaseCopyExtendedErrorInfo OBJECT-TYPE
       SYNTAX      SnmpAdminString
       ACCESS      read-only
       STATUS      mandatory
       DESCRIPTION
          "extended error information"
       ::= { exchAdDagDatabaseCopyEntry 10 }

   exchAdDagDatabaseCopySinglePageRestores OBJECT-TYPE
       SYNTAX      Counter
       ACCESS      read-only
       STATUS      mandatory
       DESCRIPTION
          "single page restores"
       ::= { exchAdDagDatabaseCopyEntry 11 }

   exchAdDagDatabaseCopyContentIndexHealthStatus OBJECT-TYPE
       SYNTAX      INTEGER {healthy(1), notHealthy(2)}
       ACCESS      read-only
       STATUS      mandatory
       DESCRIPTION
          "content index health status"
       ::= { exchAdDagDatabaseCopyEntry 12 }

   exchAdDagDatabaseCopyCopyQueueLength OBJECT-TYPE
       SYNTAX      Gauge
       ACCESS      read-only
       STATUS      mandatory
       DESCRIPTION
          "copy queue Length to database copy"
       ::= { exchAdDagDatabaseCopyEntry 13 }

   exchAdDagDatabaseCopyReplayQueueLength OBJECT-TYPE
       SYNTAX      Gauge
       ACCESS      read-only
       STATUS      mandatory
       DESCRIPTION
          "replay queue length to database copy"
       ::= { exchAdDagDatabaseCopyEntry 14 }

   exchAdDagDatabaseCopyDbaseLatestAvailableLogTime OBJECT-TYPE
       SYNTAX      SnmpAdminString
       ACCESS      read-only
       STATUS      mandatory
       DESCRIPTION
          "date/time at latest available log time"
       ::= { exchAdDagDatabaseCopyEntry 15 }

   exchAdDagDatabaseCopyDbaseLastCopyNotificationedLogTime OBJECT-TYPE
       SYNTAX      SnmpAdminString
       ACCESS      read-only
       STATUS      mandatory
       DESCRIPTION
          "date/time at log time for the last copy notification"
       ::= { exchAdDagDatabaseCopyEntry 16 }

   exchAdDagDatabaseCopyDbaseLastCopiedLogTime OBJECT-TYPE
       SYNTAX      SnmpAdminString
       ACCESS      read-only
       STATUS      mandatory
       DESCRIPTION
          "date/time at last time log copied"
       ::= { exchAdDagDatabaseCopyEntry 17 }

   exchAdDagDatabaseCopyDbaseLastInspectedLogTime OBJECT-TYPE
       SYNTAX      SnmpAdminString
       ACCESS      read-only
       STATUS      mandatory
       DESCRIPTION
          "date/time at last time log inspected"
       ::= { exchAdDagDatabaseCopyEntry 18 }

   exchAdDagDatabaseCopyDbaseLastReplayedLogTime OBJECT-TYPE
       SYNTAX      SnmpAdminString
       ACCESS      read-only
       STATUS      mandatory
       DESCRIPTION
          "date/time at last time log replayed"
       ::= { exchAdDagDatabaseCopyEntry 19 }

   exchAdDagDatabaseCopyDbaseLastLogGenerated OBJECT-TYPE
       SYNTAX      SnmpAdminString
       ACCESS      read-only
       STATUS      mandatory
       DESCRIPTION
          "last generated log"
       ::= { exchAdDagDatabaseCopyEntry 20 }

   exchAdDagDatabaseCopyDbaseLastLogCopyNotified OBJECT-TYPE
       SYNTAX      SnmpAdminString
       ACCESS      read-only
       STATUS      mandatory
       DESCRIPTION
          "last log copy notified"
       ::= { exchAdDagDatabaseCopyEntry 21 }

   exchAdDagDatabaseCopyDbaseLastLogCopied OBJECT-TYPE
       SYNTAX      SnmpAdminString
       ACCESS      read-only
       STATUS      mandatory
       DESCRIPTION
          "last log copied to the database"
       ::= { exchAdDagDatabaseCopyEntry 22 }

   exchAdDagDatabaseCopyDbaseLastLogInspected OBJECT-TYPE
       SYNTAX      SnmpAdminString
       ACCESS      read-only
       STATUS      mandatory
       DESCRIPTION
          "last log which has been inspected"
       ::= { exchAdDagDatabaseCopyEntry 23 }

   exchAdDagDatabaseCopyDbaseLastLogReplayed OBJECT-TYPE
       SYNTAX      SnmpAdminString
       ACCESS      read-only
       STATUS      mandatory
       DESCRIPTION
          "last Log which has been replayed"
       ::= { exchAdDagDatabaseCopyEntry 24 }

   exchAdDagDatabaseCopyDbaseLatestFullBackupTime OBJECT-TYPE
       SYNTAX      SnmpAdminString
       ACCESS      read-only
       STATUS      mandatory
       DESCRIPTION
          "date/time at log time for latest full backup"
       ::= { exchAdDagDatabaseCopyEntry 25 }

   exchAdDagDatabaseCopyDbaseLatestIncrementalBackupTime OBJECT-TYPE
       SYNTAX      SnmpAdminString
       ACCESS      read-only
       STATUS      mandatory
       DESCRIPTION
          "date/time at log time for latest Incremental backup"
       ::= { exchAdDagDatabaseCopyEntry 26 }

   exchAdDagDatabaseCopyDbaseLatestDifferentialBackupTime OBJECT-TYPE
       SYNTAX      SnmpAdminString
       ACCESS      read-only
       STATUS      mandatory
       DESCRIPTION
          "date/time at log time for latest differential backup"
       ::= { exchAdDagDatabaseCopyEntry 27 }

   exchAdDagDatabaseCopyDbaseLatestCopyBackupTime OBJECT-TYPE
       SYNTAX      SnmpAdminString
       ACCESS      read-only
       STATUS      mandatory
       DESCRIPTION
          "date/time at log time for latest copy backup"
       ::= { exchAdDagDatabaseCopyEntry 28 }

   exchAdDagDatabaseCopyDbaseLatestSnapshotBackupTime OBJECT-TYPE
       SYNTAX      SnmpAdminString
       ACCESS      read-only
       STATUS      mandatory
       DESCRIPTION
          "date/time at latest snapshot backup time"
       ::= { exchAdDagDatabaseCopyEntry 29 }

   exchAdDagDatabaseCopyDbaseLatestSnapshotFullBackupTime OBJECT-TYPE
       SYNTAX      SnmpAdminString
       ACCESS      read-only
       STATUS      mandatory
       DESCRIPTION
          "date/time at latest snapshot full backup time"
       ::= { exchAdDagDatabaseCopyEntry 30 }

   exchAdDagDatabaseCopyDbaseLatestSnapshotIncrementalBackupTime OBJECT-TYPE
       SYNTAX      SnmpAdminString
       ACCESS      read-only
       STATUS      mandatory
       DESCRIPTION
          "date/time at latest snapshot incremental backup time"
       ::= { exchAdDagDatabaseCopyEntry 31 }

   exchAdDagDatabaseCopyDbaseLatestSnapshotDifferentialBackupTime OBJECT-TYPE
       SYNTAX      SnmpAdminString
       ACCESS      read-only
       STATUS      mandatory
       DESCRIPTION
          "date/time at latest snapshot differential backup time"
       ::= { exchAdDagDatabaseCopyEntry 32 }

   exchAdDagDatabaseCopyDbaseLatestSnapshotCopyBackupTime OBJECT-TYPE
       SYNTAX      SnmpAdminString
       ACCESS      read-only
       STATUS      mandatory
       DESCRIPTION
          "date/time at latest snapshot copy backup time"
       ::= { exchAdDagDatabaseCopyEntry 33 }

   exchAdDagDatabaseCopyDbaseLogReplayQueueIncreasing OBJECT-TYPE
       SYNTAX      INTEGER { true(1), false(2)}
       ACCESS      read-only
       STATUS      mandatory
       DESCRIPTION
          "whether Log Replay Queue Increasing"
       ::= { exchAdDagDatabaseCopyEntry 34 }

   exchAdDagDatabaseCopyDbaseLogCopyQueueIncreasing OBJECT-TYPE
       SYNTAX      INTEGER { true(1), false(2)}
       ACCESS      read-only
       STATUS      mandatory
       DESCRIPTION
          "whether Log Copy Queue Increasing"
       ::= { exchAdDagDatabaseCopyEntry 35 }

   exchAdDagDatabaseCopyDbaseOutstandingDumpsterRequests OBJECT-TYPE
       SYNTAX      Gauge
       ACCESS      read-only
       STATUS      mandatory
       DESCRIPTION
          "outstanding Dumpster Requests"
       ::= { exchAdDagDatabaseCopyEntry 36 }

   exchAdDagDatabaseCopyDbaseOutgoingConnections OBJECT-TYPE
       SYNTAX      Gauge
       ACCESS      read-only
       STATUS      mandatory
       DESCRIPTION
          "outgoing connections"
       ::= { exchAdDagDatabaseCopyEntry 37 }

   exchAdDagDatabaseCopyDbaseIncomingLogCopyingNetwork OBJECT-TYPE
       SYNTAX      SnmpAdminString
       ACCESS      read-only
       STATUS      mandatory
       DESCRIPTION
          "incoming copying network for log Database copy status log"
       ::= { exchAdDagDatabaseCopyEntry 38 }

   exchAdDagDatabaseCopyDbaseSeedingNetwork OBJECT-TYPE
       SYNTAX      SnmpAdminString
       ACCESS      read-only
       STATUS      mandatory
       DESCRIPTION
          "seeding network"
       ::= { exchAdDagDatabaseCopyEntry 39 }

   exchAdDagDatabaseCopyDbaseActiveCopy OBJECT-TYPE
       SYNTAX      INTEGER { true(1), false(2)}
       ACCESS      read-only
       STATUS      mandatory
       DESCRIPTION
          "whether current DB is an active copy"
       ::= { exchAdDagDatabaseCopyEntry 40 }

   exchAdDagDatabaseCopyDbaseCopyMailboxHostIndex OBJECT-TYPE
       SYNTAX      INTEGER
       ACCESS      read-only
       STATUS      mandatory
       DESCRIPTION
          "pointer to associated mailbox host, same as exchAdUniversalHostIndex"
       ::= { exchAdDagDatabaseCopyEntry 41 }


--**************************************************************************
--**************************************************************************
-- 
-- Synthetic Tests Parameters
--
--**************************************************************************
--**************************************************************************

--**************************************************************************  
--
-- Test-ServiceHealth
--
-- returns whether all the Microsoft Windows services that Exchange requires on a
-- server have started for each Role installed.
--
--**************************************************************************

exchAdTestServiceHealthMaxTests  OBJECT-TYPE
       SYNTAX       INTEGER
       ACCESS       read-write
       STATUS       mandatory
       DESCRIPTION "maximum number of entries in exchAdTestServiceHealthControlTable"
       ::= { exchAdSyntheticTests 1 }


--**************************************************************************  
--
-- exchAdTestServiceHealthControlTable
--
--**************************************************************************

exchAdTestServiceHealthControlTable OBJECT-TYPE
       SYNTAX      SEQUENCE OF ExchAdTestServiceHealthControlEntry
       ACCESS      not-accessible
       STATUS      mandatory
       DESCRIPTION
           "Test-ServiceHealth control table"
      ::= { exchAdSyntheticTests 2 }

exchAdTestServiceHealthControlEntry OBJECT-TYPE
       SYNTAX      ExchAdTestServiceHealthControlEntry
       ACCESS      not-accessible
       STATUS      mandatory
       DESCRIPTION
           "defines an entry in the exchAdTestServiceHealthControlTable"

       INDEX {
                exchAdTestServiceHealthOwnerIndex,
                exchAdTestServiceHealthTestIndex
             }
       ::= { exchAdTestServiceHealthControlTable 1 }

    ExchAdTestServiceHealthControlEntry ::=
       SEQUENCE {
          exchAdTestServiceHealthOwnerIndex             SnmpAdminString,
          exchAdTestServiceHealthTestIndex              SnmpAdminString,
          exchAdTestServiceHealthRowStatus              RowStatus,
          exchAdTestServiceHealthAdminStatus            INTEGER,
          exchAdTestServiceHealthHostIndex              INTEGER,
          exchAdTestServiceHealthActiveDirectoryTimeout INTEGER,
          exchAdTestServiceHealthDomainControllerIndex  INTEGER
            }

    exchAdTestServiceHealthOwnerIndex OBJECT-TYPE
       SYNTAX      SnmpAdminString (SIZE(1..56))
       ACCESS      read-only
       STATUS      mandatory
       DESCRIPTION
          "uniquely identifies owner (supplied by agent)"
       ::= { exchAdTestServiceHealthControlEntry 1 }

    exchAdTestServiceHealthTestIndex OBJECT-TYPE
       SYNTAX      SnmpAdminString (SIZE(1..56))
       ACCESS      read-only
       STATUS      mandatory
       DESCRIPTION
          "uniquely identifies test associated with owner (supplied by agent)"
       ::= { exchAdTestServiceHealthControlEntry 2 }

    exchAdTestServiceHealthRowStatus OBJECT-TYPE
       SYNTAX      RowStatus
       ACCESS      read-write
       STATUS      mandatory
       DESCRIPTION
          "sets up the test"
       ::= { exchAdTestServiceHealthControlEntry 3 }

    exchAdTestServiceHealthAdminStatus OBJECT-TYPE
       SYNTAX      INTEGER {enabled(1), disabled(2)}
       ACCESS      read-write
       STATUS      mandatory
       DESCRIPTION
          "administrative status: starts/stops the test"
       ::= { exchAdTestServiceHealthControlEntry 4 }

    exchAdTestServiceHealthHostIndex OBJECT-TYPE
       SYNTAX      INTEGER
       ACCESS      read-write
       STATUS      mandatory
       DESCRIPTION
          "pointer to the host on which to check that the required services are running, same as exchAdUniversalHostIndex"
       ::= { exchAdTestServiceHealthControlEntry 5 }

    exchAdTestServiceHealthActiveDirectoryTimeout  OBJECT-TYPE
       SYNTAX      INTEGER
       ACCESS      read-write
       STATUS      mandatory
       DESCRIPTION
          "the amount of time, in seconds, allowed for each Active Directory operation to complete before the operation times out. The default value is 15 seconds"
       ::= { exchAdTestServiceHealthControlEntry 6 }

    exchAdTestServiceHealthDomainControllerIndex  OBJECT-TYPE
       SYNTAX      INTEGER
       ACCESS      read-only
       STATUS      mandatory
       DESCRIPTION
          "pointer to domain controller in exchAdDomainControllerTable, same as exchAdUniversalHostIndex"
       ::= { exchAdTestServiceHealthControlEntry 7 }

--**************************************************************************  
--
-- exchAdTestServiceHealthResultsTable
--
--**************************************************************************

exchAdTestServiceHealthResultsTable   OBJECT-TYPE
       SYNTAX      SEQUENCE OF ExchAdTestServiceHealthResultsEntry
       ACCESS      not-accessible
       STATUS      mandatory
       DESCRIPTION
           "Test-ServiceHealth results table"
      ::= { exchAdSyntheticTests 3 }

exchAdTestServiceHealthResultsEntry OBJECT-TYPE
       SYNTAX      ExchAdTestServiceHealthResultsEntry
       ACCESS      not-accessible
       STATUS      mandatory
       DESCRIPTION
           "defines an entry in the exchAdTestServiceHealthResultsTable"

       INDEX {
                exchAdTestServiceHealthOwnerIndex,
                exchAdTestServiceHealthTestIndex
             }
       ::= { exchAdTestServiceHealthResultsTable 1 }

    ExchAdTestServiceHealthResultsEntry ::=
       SEQUENCE {
                  exchAdTestServiceHealthOperStatus                   INTEGER,
                  exchAdTestServiceHealthCompletionStatus             INTEGER, 
                  exchAdTestServiceHealthManagedHostExRoleMask        INTEGER, 
                  exchAdTestServiceHealthManagedHostExRoleRunningMask INTEGER 
                }


    exchAdTestServiceHealthOperStatus  OBJECT-TYPE
       SYNTAX      INTEGER {enabled(1), disabled(2)}
       ACCESS      read-only
       STATUS      mandatory
       DESCRIPTION
          "operational status of test"
       ::= { exchAdTestServiceHealthResultsEntry 1 }

    exchAdTestServiceHealthCompletionStatus  OBJECT-TYPE
       SYNTAX      INTEGER {success(1), failure(2), inProgress(3)}
       ACCESS      read-only
       STATUS      mandatory
       DESCRIPTION
          "completion status of test"
       ::= { exchAdTestServiceHealthResultsEntry 2 }

    exchAdTestServiceHealthManagedHostExRoleMask  OBJECT-TYPE
       SYNTAX      INTEGER
       ACCESS      read-only
       STATUS      mandatory
       DESCRIPTION
            "This object is a bit field. Each bit represents the following Exchange roles:
            Hex: 0000 0001, Decimal:  1 - Edge Transport
            Hex: 0000 0002, Decimal:  2 - Hub Transport
            Hex: 0000 0004, Decimal:  4 - Client Access
            Hex: 0000 0008, Decimal:  8 - Mailbox
            Hex: 0000 0010, Decimal: 16 - Unified Messaging"
       ::= { exchAdTestServiceHealthResultsEntry 3 }

    exchAdTestServiceHealthManagedHostExRoleRunningMask  OBJECT-TYPE
       SYNTAX      INTEGER
       ACCESS      read-only
       STATUS      mandatory
       DESCRIPTION
            "This object is a bit field. Each bit represents the following Exchange roles:
            Hex: 0000 0001, Decimal:  1 - Edge Transport
            Hex: 0000 0002, Decimal:  2 - Hub Transport
            Hex: 0000 0004, Decimal:  4 - Client Access
            Hex: 0000 0008, Decimal:  8 - Mailbox
            Hex: 0000 0010, Decimal: 16 - Unified Messaging"
       ::= { exchAdTestServiceHealthResultsEntry 4 }

--**************************************************************************  
--
-- Test-MapiConnectivity
--
-- returns whether server functionality is working fine. It logs on to the 
-- mailbox that you specify and retrieves a list of items in the Inbox
--
--**************************************************************************

exchAdTestMapiConnectivityMaxTests  OBJECT-TYPE
       SYNTAX       INTEGER
       ACCESS       read-write
       STATUS       mandatory
       DESCRIPTION "maximum number of entries in maximum number of entries in exchAdTestMapiConnectivityControlTable"
       ::= { exchAdSyntheticTests 4 }

--**************************************************************************  
--
-- exchAdTestMapiConnectivityControlTable
--
--**************************************************************************

exchAdTestMapiConnectivityControlTable OBJECT-TYPE
       SYNTAX      SEQUENCE OF ExchAdTestMapiConnectivityControlEntry
       ACCESS      not-accessible
       STATUS      mandatory
       DESCRIPTION
           "Test-MapiConnectivity control table"
      ::= { exchAdSyntheticTests 5 }

exchAdTestMapiConnectivityControlEntry OBJECT-TYPE
       SYNTAX      ExchAdTestMapiConnectivityControlEntry
       ACCESS      not-accessible
       STATUS      mandatory
       DESCRIPTION
           "defines an entry in the exchAdTestMapiConnectivityControlTable"

       INDEX {
                exchAdTestMapiConnectivityOwnerIndex,
                exchAdTestMapiConnectivityTestIndex
             }
       ::= { exchAdTestMapiConnectivityControlTable 1 }

    ExchAdTestMapiConnectivityControlEntry ::=
       SEQUENCE {
          exchAdTestMapiConnectivityOwnerIndex                SnmpAdminString,
          exchAdTestMapiConnectivityTestIndex                 SnmpAdminString,
          exchAdTestMapiConnectivityRowStatus                 RowStatus,
          exchAdTestMapiConnectivityAdminStatus               INTEGER,
          exchAdTestMapiConnectivityHostIndex                 INTEGER,
          exchAdTestMapiConnectivityDatabaseIndex             INTEGER,
          exchAdTestMapiConnectivityMailbox                   SnmpAdminString,
          exchAdTestMapiConnectivityArchive                   INTEGER,
          exchAdTestMapiConnectivityActiveDirectoryTimeout    INTEGER,
          exchAdTestMapiConnectivityAllConnectionsTimeout     INTEGER,
          exchAdTestMapiConnectivityDomainControllerIndex     INTEGER,
          exchAdTestMapiConnectivityPerConnectionTimeout      INTEGER
            }

    exchAdTestMapiConnectivityOwnerIndex OBJECT-TYPE
       SYNTAX      SnmpAdminString (SIZE(1..56))
       ACCESS      read-only
       STATUS      mandatory
       DESCRIPTION
          "uniquely identifies owner (supplied by agent)"
       ::= { exchAdTestMapiConnectivityControlEntry 1 }

    exchAdTestMapiConnectivityTestIndex OBJECT-TYPE
       SYNTAX      SnmpAdminString (SIZE(1..56))
       ACCESS      read-only
       STATUS      mandatory
       DESCRIPTION
          "uniquely identifies test associated with owner (supplied by agent)"
       ::= { exchAdTestMapiConnectivityControlEntry 2 }

    exchAdTestMapiConnectivityRowStatus OBJECT-TYPE
       SYNTAX      RowStatus
       ACCESS      read-write
       STATUS      mandatory
       DESCRIPTION
          "sets up the test"
       ::= { exchAdTestMapiConnectivityControlEntry 3 }

    exchAdTestMapiConnectivityAdminStatus OBJECT-TYPE
       SYNTAX      INTEGER {enabled(1), disabled(2)}
       ACCESS      read-write
       STATUS      mandatory
       DESCRIPTION
          "administrative status: starts/stops the test"
       ::= { exchAdTestMapiConnectivityControlEntry 4 }

    exchAdTestMapiConnectivityHostIndex OBJECT-TYPE
       SYNTAX      INTEGER
       ACCESS      read-write
       STATUS      mandatory
       DESCRIPTION
          "index of the host  on which you will test the MAPI connectivity, same as exchAdUniversalHostIndex"
       ::= { exchAdTestMapiConnectivityControlEntry 5 }

    exchAdTestMapiConnectivityDatabaseIndex OBJECT-TYPE
       SYNTAX      INTEGER
       ACCESS      read-write
       STATUS      mandatory
       DESCRIPTION
          "index of the database in exchAdMailboxDatabaseInventoryTable on which to test the connectivity to the system mailbox (alternative to exchAdTestMapiConnectivityMailbox parameter)"
       ::= { exchAdTestMapiConnectivityControlEntry 6 }

    exchAdTestMapiConnectivityMailbox OBJECT-TYPE
       SYNTAX      SnmpAdminString
       ACCESS      read-write
       STATUS      mandatory
       DESCRIPTION
          "The mailbox to test. You can use the following values: GUID, Distinguished name (DN), Domain\Account,  User principal name (UPN), Legacy Exchange DN, SMTP address, Alias (alternative to exchAdTestMapiConnectivityDatabase parameter)"
       ::= { exchAdTestMapiConnectivityControlEntry 7 }

    exchAdTestMapiConnectivityArchive OBJECT-TYPE
       SYNTAX      INTEGER {test(1), doNotTest(2)}
       ACCESS      read-write
       STATUS      mandatory
       DESCRIPTION
          "whether or not to test the MAPI connectivity of the personal archive associated with the  mailbox (Exchange 2010 only, requires exchAdTestMapiConnectivityMailbox parameter)"
       ::= { exchAdTestMapiConnectivityControlEntry 8 }

    exchAdTestMapiConnectivityActiveDirectoryTimeout OBJECT-TYPE
       SYNTAX      INTEGER
       ACCESS      read-write
       STATUS      mandatory
       DESCRIPTION
          "amount of time, in seconds, allowed for each Active Directory operation to complete before the operation times out"
       DEFVAL      { 15 }
       ::= { exchAdTestMapiConnectivityControlEntry 9 }

    exchAdTestMapiConnectivityAllConnectionsTimeout OBJECT-TYPE
       SYNTAX      INTEGER
       ACCESS      read-write
       STATUS      mandatory
       DESCRIPTION
          "the amount of time, in seconds, allowed for all connections to complete before the cmdlet times out; doesn't begin until all information necessary to perform the connections is gathered from Active Directory"
       DEFVAL     { 90 }
       ::= { exchAdTestMapiConnectivityControlEntry 10 }

    exchAdTestMapiConnectivityDomainControllerIndex OBJECT-TYPE
       SYNTAX      INTEGER
       ACCESS      read-write
       STATUS      mandatory
       DESCRIPTION
          "pointer to domain controller in exchAdDomainControllerTable, same as exchAdUniversalHostIndex"
       ::= { exchAdTestMapiConnectivityControlEntry 11 }

    exchAdTestMapiConnectivityPerConnectionTimeout OBJECT-TYPE
       SYNTAX      INTEGER
       ACCESS      read-write
       STATUS      mandatory
       DESCRIPTION
          "amount of time, in seconds, allowed for each connection to complete before the connection times out"
        DEFVAL     { 10 }
       ::= { exchAdTestMapiConnectivityControlEntry 12 }

--**************************************************************************  
--
-- exchAdTestMapiConnectivityResultsTable
--
--**************************************************************************

exchAdTestMapiConnectivityResultsTable   OBJECT-TYPE
       SYNTAX      SEQUENCE OF ExchAdTestMapiConnectivityResultsEntry
       ACCESS      not-accessible
       STATUS      mandatory
       DESCRIPTION
           "Test-MapiConnectivity results table"
      ::= { exchAdSyntheticTests 6 }

exchAdTestMapiConnectivityResultsEntry OBJECT-TYPE
       SYNTAX      ExchAdTestMapiConnectivityResultsEntry
       ACCESS      not-accessible
       STATUS      mandatory
       DESCRIPTION
           "defines an entry in the exchAdTestMapiConnectivityResultsTable"

       INDEX {
                exchAdTestMapiConnectivityOwnerIndex,
                exchAdTestMapiConnectivityTestIndex
             }
       ::= { exchAdTestMapiConnectivityResultsTable 1 }

    ExchAdTestMapiConnectivityResultsEntry ::=
       SEQUENCE {
                  exchAdTestMapiConnectivityOperStatus          INTEGER,
                  exchAdTestMapiConnectivityCompletionStatus    INTEGER, 
                  exchAdTestMapiConnectivityLogonLatency        INTEGER,
                  exchAdTestMapiConnectivityError               SnmpAdminString
                }

    exchAdTestMapiConnectivityOperStatus  OBJECT-TYPE
       SYNTAX      INTEGER {enabled(1), disabled(2)}
       ACCESS      read-only
       STATUS      mandatory
       DESCRIPTION
          "operational status of test"
       ::= { exchAdTestMapiConnectivityResultsEntry 1 }

    exchAdTestMapiConnectivityCompletionStatus  OBJECT-TYPE
       SYNTAX      INTEGER {success(1), failure(2), inProgress(3)}
       ACCESS      read-only
       STATUS      mandatory
       DESCRIPTION
          "completion status of test"
       ::= { exchAdTestMapiConnectivityResultsEntry 2 }

    exchAdTestMapiConnectivityLogonLatency OBJECT-TYPE
       SYNTAX      INTEGER
       ACCESS      read-only
       STATUS      mandatory
       DESCRIPTION
          "logon latency in seconds for test"
       ::= { exchAdTestMapiConnectivityResultsEntry 3 }

    exchAdTestMapiConnectivityError OBJECT-TYPE
       SYNTAX      SnmpAdminString
       ACCESS      read-only
       STATUS      mandatory
       DESCRIPTION
          "error descriptor for test"
       ::= { exchAdTestMapiConnectivityResultsEntry 4 }

--**************************************************************************  
--
-- Test-ExchangeSearch
--
-- returns the result of the test that search is currently enabled and is 
-- indexing new e-mail messages in a timely manner.
--
--**************************************************************************

exchAdTestExchangeSearchMaxTests  OBJECT-TYPE
       SYNTAX       INTEGER
       ACCESS       read-write
       STATUS       mandatory
       DESCRIPTION "maximum number of entries in exchAdTestExchangeSearchControlTable"
       ::= { exchAdSyntheticTests 7 }

--**************************************************************************  
--
-- exchAdTestExchangeSearchControlTable
--
--**************************************************************************

exchAdTestExchangeSearchControlTable OBJECT-TYPE
       SYNTAX      SEQUENCE OF ExchAdTestExchangeSearchControlEntry
       ACCESS      not-accessible
       STATUS      mandatory
       DESCRIPTION
           "Test-ExchangeSearch control table"
      ::= { exchAdSyntheticTests 8 }

exchAdTestExchangeSearchControlEntry OBJECT-TYPE
       SYNTAX      ExchAdTestExchangeSearchControlEntry
       ACCESS      not-accessible
       STATUS      mandatory
       DESCRIPTION
           "defines an entry in the exchAdTestExchangeSearchControlTable"

       INDEX {
                exchAdTestExchangeSearchOwnerIndex,
                exchAdTestExchangeSearchTestIndex
             }
       ::= { exchAdTestExchangeSearchControlTable 1 }

    ExchAdTestExchangeSearchControlEntry ::=
       SEQUENCE {
          exchAdTestExchangeSearchOwnerIndex                  SnmpAdminString,
          exchAdTestExchangeSearchTestIndex                   SnmpAdminString,
          exchAdTestExchangeSearchRowStatus                   RowStatus,
          exchAdTestExchangeSearchAdminStatus                 INTEGER,
          exchAdTestExchangeSearchDomainControllerIndex       INTEGER,
          exchAdTestExchangeSearchMailbox                     SnmpAdminString,
          exchAdTestExchangeSearchHostIndex                   INTEGER,
          exchAdTestExchangeSearchDatabaseIndex               INTEGER
            }

    exchAdTestExchangeSearchOwnerIndex OBJECT-TYPE
       SYNTAX      SnmpAdminString (SIZE(1..56))
       ACCESS      read-only
       STATUS      mandatory
       DESCRIPTION
          "uniquely identifies owner (supplied by agent)"
       ::= { exchAdTestExchangeSearchControlEntry 1 }

   exchAdTestExchangeSearchTestIndex OBJECT-TYPE
       SYNTAX      SnmpAdminString (SIZE(1..56))
       ACCESS      read-only
       STATUS      mandatory
       DESCRIPTION
          "uniquely identifies test associated with owner (supplied by agent)"
       ::= { exchAdTestExchangeSearchControlEntry 2 }

   exchAdTestExchangeSearchRowStatus OBJECT-TYPE
       SYNTAX      RowStatus
       ACCESS      read-write
       STATUS      mandatory
       DESCRIPTION
          "sets up the test"
       ::= { exchAdTestExchangeSearchControlEntry 3 }

   exchAdTestExchangeSearchAdminStatus OBJECT-TYPE
       SYNTAX      INTEGER {enabled(1), disabled(2)}
       ACCESS      read-write
       STATUS      mandatory
       DESCRIPTION
          "administrative status: starts/stops the test"
       ::= { exchAdTestExchangeSearchControlEntry 4 }

   exchAdTestExchangeSearchDomainControllerIndex OBJECT-TYPE
       SYNTAX      INTEGER
       ACCESS      read-write
       STATUS      mandatory
       DESCRIPTION
          "pointer to domain controller in exchAdDomainControllerTable, same as exchAdUniversalHostIndex"
       ::= { exchAdTestExchangeSearchControlEntry 5 }

   exchAdTestExchangeSearchMailbox OBJECT-TYPE
       SYNTAX      SnmpAdminString
       ACCESS      read-write
       STATUS      mandatory
       DESCRIPTION
          "The mailbox to test. You can use the following values: GUID, Distinguished name (DN), Domain\Account,  User principal name (UPN), Legacy Exchange DN, SMTP address, Alias (alternative to exchAdTestExchangeSearchDatabaseIndex)"
       ::= { exchAdTestExchangeSearchControlEntry 6 }

   exchAdTestExchangeSearchHostIndex OBJECT-TYPE
       SYNTAX      INTEGER
       ACCESS      read-write
       STATUS      mandatory
       DESCRIPTION
          "index of the host in exchAdMailboxGeneralPerformanceTable or exchAdMailboxHostInventoryTable on which you will perform the test, same as exchAdUniversalHostIndex"
       ::= { exchAdTestExchangeSearchControlEntry 7 }

   exchAdTestExchangeSearchDatabaseIndex OBJECT-TYPE
       SYNTAX      INTEGER
       ACCESS      read-write
       STATUS      mandatory
       DESCRIPTION
          "index of the database in exchAdMailboxDatabaseInventoryTable on which to test the connectivity to the system mailbox (alternative to exchAdTestExchangeSearchMailbox)"
       ::= { exchAdTestExchangeSearchControlEntry 8 }

--**************************************************************************  
--
-- exchAdTestExchangeSearchResultsTable
--
--**************************************************************************

exchAdTestExchangeSearchResultsTable   OBJECT-TYPE
       SYNTAX      SEQUENCE OF ExchAdTestExchangeSearchResultsEntry
       ACCESS      not-accessible
       STATUS      mandatory
       DESCRIPTION
           "Test-ExchangeSearch results table"
      ::= { exchAdSyntheticTests 9 }

exchAdTestExchangeSearchResultsEntry OBJECT-TYPE
       SYNTAX      ExchAdTestExchangeSearchResultsEntry
       ACCESS      not-accessible
       STATUS      mandatory
       DESCRIPTION
           "defines an entry in the exchAdTestExchangeSearchResultsTable"

       INDEX {
                exchAdTestExchangeSearchOwnerIndex,
                exchAdTestExchangeSearchTestIndex
             }
       ::= { exchAdTestExchangeSearchResultsTable 1 }

    ExchAdTestExchangeSearchResultsEntry ::=
       SEQUENCE {
                  exchAdTestExchangeSearchOperStatus          INTEGER,
                  exchAdTestExchangeSearchCompletionStatus    INTEGER,
                  exchAdTestExchangeSearchLogonLatency        INTEGER,
                  exchAdTestExchangeSearchError               SnmpAdminString 
                }

    exchAdTestExchangeSearchOperStatus OBJECT-TYPE
       SYNTAX      INTEGER {enabled(1), disabled(2)}
       ACCESS      read-only
       STATUS      mandatory
       DESCRIPTION
          "operational status of test"
       ::= { exchAdTestExchangeSearchResultsEntry 1 }

    exchAdTestExchangeSearchCompletionStatus OBJECT-TYPE
       SYNTAX      INTEGER {success(1), failure(2), inProgress(3)}
       ACCESS      read-only
       STATUS      mandatory
       DESCRIPTION
          "completion status of test"
       ::= { exchAdTestExchangeSearchResultsEntry 2 }

    exchAdTestExchangeSearchLogonLatency OBJECT-TYPE
       SYNTAX      INTEGER
       ACCESS      read-only
       STATUS      mandatory
       DESCRIPTION
          "n latency in seconds for test"
       ::= { exchAdTestExchangeSearchResultsEntry 3 }

    exchAdTestExchangeSearchError OBJECT-TYPE
       SYNTAX      SnmpAdminString
       ACCESS      read-only
       STATUS      mandatory
       DESCRIPTION
          "error descriptor for test"
       ::= { exchAdTestExchangeSearchResultsEntry 4 }

--**************************************************************************  
--
-- Test-MailFlow
--
--  return whether mail can be successfully sent from and delivered to the 
--  system mailbox on a computer that has the Mailbox server role installed.
--
--**************************************************************************

exchAdTestMailFlowMaxTests  OBJECT-TYPE
       SYNTAX       INTEGER
       ACCESS       read-write
       STATUS       mandatory
       DESCRIPTION "maximum number of entries in exchAdTestMailFlowControlTable"
       ::= { exchAdSyntheticTests 10 }

--**************************************************************************  
--
-- exchAdTestMailFlowControlTable
--
--**************************************************************************

exchAdTestMailFlowControlTable OBJECT-TYPE
       SYNTAX      SEQUENCE OF ExchAdTestMailFlowControlEntry
       ACCESS      not-accessible
       STATUS      mandatory
       DESCRIPTION
           "Test-MailFlow control table"
      ::= { exchAdSyntheticTests 11 }

exchAdTestMailFlowControlEntry OBJECT-TYPE
       SYNTAX      ExchAdTestMailFlowControlEntry
       ACCESS      not-accessible
       STATUS      mandatory
       DESCRIPTION
           "defines an entry in the exchAdTestMailFlowControlTable"

       INDEX {
                exchAdTestMailFlowOwnerIndex,
                exchAdTestMailFlowTestIndex
             }
       ::= { exchAdTestMailFlowControlTable 1 }

    ExchAdTestMailFlowControlEntry ::=
       SEQUENCE {
          exchAdTestMailFlowOwnerIndex              SnmpAdminString,
          exchAdTestMailFlowTestIndex               SnmpAdminString,
          exchAdTestMailFlowRowStatus               RowStatus,
          exchAdTestMailFlowAdminStatus             INTEGER,
          exchAdTestMailFlowTargetEmailAddress      SnmpAdminString,
          exchAdTestMailFlowTargetHostIndex         INTEGER,
          exchAdTestMailFlowTargetDatabaseIndex     INTEGER,
          exchAdTestMailFlowDomainControllerIndex   INTEGER,
          exchAdTestMailFlowErrorLatency            INTEGER,
          exchAdTestMailFlowExecutionTimeout        INTEGER,
          exchAdTestMailFlowSourceHostIndex         INTEGER,
          exchAdTestMailFlowSourceSmtpAddr          SnmpAdminString
                 }

    exchAdTestMailFlowOwnerIndex OBJECT-TYPE
       SYNTAX      SnmpAdminString (SIZE(1..56))
       ACCESS      read-only
       STATUS      mandatory
       DESCRIPTION
          "uniquely identifies owner (supplied by agent)"
       ::= { exchAdTestMailFlowControlEntry 1 }

   exchAdTestMailFlowTestIndex OBJECT-TYPE
       SYNTAX      SnmpAdminString (SIZE(1..56))
       ACCESS      read-only
       STATUS      mandatory
       DESCRIPTION
          "uniquely identifies test associated with owner (supplied by agent)"
       ::= { exchAdTestMailFlowControlEntry 2 }

   exchAdTestMailFlowRowStatus OBJECT-TYPE
       SYNTAX      RowStatus
       ACCESS      read-write
       STATUS      mandatory
       DESCRIPTION
          "sets up the test"
       ::= { exchAdTestMailFlowControlEntry 3 }

   exchAdTestMailFlowAdminStatus OBJECT-TYPE
       SYNTAX      INTEGER {enabled(1), disabled(2)}
       ACCESS      read-write
       STATUS      mandatory
       DESCRIPTION
          "administrative status: starts/stops the test"
       ::= { exchAdTestMailFlowControlEntry 4 }

   exchAdTestMailFlowTargetEmailAddress OBJECT-TYPE
       SYNTAX      SnmpAdminString
       ACCESS      read-write
       STATUS      mandatory
       DESCRIPTION
          "SMTP address of the mailbox to which test messages are sent. Use this parameter to send test messages to a Mailbox server in a remote forest. If this parameter is used, the test is always a remote test.  Alternative to exchAdTestMailFlowTargetHostIndex or exchAdTestMailFlowTargetDatabaseIndex."
       ::= { exchAdTestMailFlowControlEntry 5 }

   exchAdTestMailFlowTargetHostIndex OBJECT-TYPE
       SYNTAX      INTEGER
       ACCESS      read-write
       STATUS      mandatory
       DESCRIPTION
          "pointer to the host of a Mailbox server in the local Exchange organization to which test messages are sent, same as exchAdUniversalHostIndex.  Alternative to exchAdTestMailFlowTargetEmailAddress or exchAdTestMailFlowTargetDatabaseIndex ."
       ::= { exchAdTestMailFlowControlEntry 6 }

   exchAdTestMailFlowTargetDatabaseIndex OBJECT-TYPE
       SYNTAX      INTEGER
       ACCESS      read-write
       STATUS      mandatory
       DESCRIPTION
          "index of the database in exchAdMailboxDatabaseInventoryTable to which test messages are sent (Exchange 2010 only).  Alternative to exchAdTestMailFlowTargetEmailAddress or exchAdTestMailFlowTargetHostIndex."
       ::= { exchAdTestMailFlowControlEntry 7 }

   exchAdTestMailFlowDomainControllerIndex OBJECT-TYPE
       SYNTAX      INTEGER
       ACCESS      read-write
       STATUS      mandatory
       DESCRIPTION
          "pointer to domain controller in exchAdDomainControllerTable, same as exchAdUniversalHostIndex"
       ::= { exchAdTestMailFlowControlEntry 8 }

   exchAdTestMailFlowErrorLatency OBJECT-TYPE
       SYNTAX      INTEGER
       ACCESS      read-write
       STATUS      mandatory
       DESCRIPTION
          "how long to wait for a test message to be delivered before an error event is logged in Microsoft System Center Operations Manager 2007. The default value when a test message is sent to the local Mailbox server is 15 seconds and 180 seconds when a test message is sent to a remote Mailbox server."
       ::= { exchAdTestMailFlowControlEntry 9 }

   exchAdTestMailFlowExecutionTimeout OBJECT-TYPE
       SYNTAX      INTEGER
       ACCESS      read-write
       STATUS      mandatory
       DESCRIPTION
          "maximum time that this task can run before the test is determined to be a failure. If no test message or delivery report arrives before this time expires, the task ends and an error is reported."
       DEFVAL      { 15 }
       ::= { exchAdTestMailFlowControlEntry 10 }

   exchAdTestMailFlowSourceHostIndex OBJECT-TYPE
       SYNTAX      INTEGER
       ACCESS      read-write
       STATUS      mandatory
       DESCRIPTION
          "pointer to the source Mailbox server from which a test message is sent in exchAdUniversalHostTable, same as exchAdUniversalHostIndex.  Alternative to exchAdTestMailFlowSourceSmtpAddr."
       ::= { exchAdTestMailFlowControlEntry 11 }

   exchAdTestMailFlowSourceSmtpAddr OBJECT-TYPE
       SYNTAX      SnmpAdminString
       ACCESS      read-write
       STATUS      mandatory
       DESCRIPTION
          "Source mailbox SMTP address from which a test message is sent (alternative to exchAdTestMailFlowSourceHostIndex for Exchange 2010 only)"
       ::= { exchAdTestMailFlowControlEntry 12 }

--**************************************************************************  
--
-- exchAdTestMailFlowResultsTable
--
--**************************************************************************

exchAdTestMailFlowResultsTable   OBJECT-TYPE
       SYNTAX      SEQUENCE OF ExchAdTestMailFlowResultsEntry
       ACCESS      not-accessible
       STATUS      mandatory
       DESCRIPTION
           "Test-MailFlow results table"
      ::= { exchAdSyntheticTests 12 }

exchAdTestMailFlowResultsEntry OBJECT-TYPE
       SYNTAX      ExchAdTestMailFlowResultsEntry
       ACCESS      not-accessible
       STATUS      mandatory
       DESCRIPTION
           "defines an entry in the exchAdTestMailFlowResultsTable"

       INDEX {
                exchAdTestMailFlowOwnerIndex,
                exchAdTestMailFlowTestIndex
             }
       ::= { exchAdTestMailFlowResultsTable 1 }

    ExchAdTestMailFlowResultsEntry ::=
       SEQUENCE {
                  exchAdTestMailFlowOperStatus           INTEGER,
                  exchAdTestMailFlowCompletionStatus     INTEGER,
                  exchAdTestMailFlowMessageLatencyTime   INTEGER,
                  exchAdTestMailFlowTestLocation         INTEGER 
                }

    exchAdTestMailFlowOperStatus OBJECT-TYPE
       SYNTAX      INTEGER {enabled(1), disabled(2)}
       ACCESS      read-only
       STATUS      mandatory
       DESCRIPTION
          "operational status of test"
       ::= { exchAdTestMailFlowResultsEntry 1 }

    exchAdTestMailFlowCompletionStatus OBJECT-TYPE
       SYNTAX      INTEGER {success(1), failure(2), inProgress(3)}
       ACCESS      read-only
       STATUS      mandatory
       DESCRIPTION
          "completion status of test"
       ::= { exchAdTestMailFlowResultsEntry 2 }

   exchAdTestMailFlowMessageLatencyTime OBJECT-TYPE
       SYNTAX      INTEGER
       ACCESS      read-only
       STATUS      mandatory
       DESCRIPTION
          "time for a test message to be sent to the receiving Mailbox server in seconds"
       ::= { exchAdTestMailFlowResultsEntry 3 }

   exchAdTestMailFlowTestLocation OBJECT-TYPE
       SYNTAX      INTEGER {local(1), remote(2)}
       ACCESS      read-only
       STATUS      mandatory
       DESCRIPTION
          "whether or not test is a remote test"
       ::= { exchAdTestMailFlowResultsEntry 4 }


--**************************************************************************
--**************************************************************************
--
-- Notifications
--
--**************************************************************************
--**************************************************************************

  exchAdForestAddedTrap TRAP-TYPE
	ENTERPRISE sysmgmt
    VARIABLES {
      exchAdForestIndex,
      exchAdForestName }
    DESCRIPTION
        "Forest added to exchAdForestTable"
    ::= 166100

  exchAdForestRemovedTrap TRAP-TYPE
	ENTERPRISE sysmgmt
    VARIABLES {
      exchAdForestIndex,
      exchAdForestName }
    DESCRIPTION
        "Forest removed from exchAdForestTable"
    ::= 166101

  exchAdDomainAddedTrap TRAP-TYPE
	ENTERPRISE sysmgmt
    VARIABLES {
      exchAdDomainIndex,
      exchAdDomainName,
      exchAdForestIndex,
      exchAdForestName,
      exchAdDomainMgmtMode,
      exchAdDomainTechnology }
    DESCRIPTION
        "Domain added to exchAdDomainTable"
    ::= 166102

  exchAdDomainRemovedTrap TRAP-TYPE
	ENTERPRISE sysmgmt
    VARIABLES {
      exchAdDomainIndex,
      exchAdDomainName,
      exchAdForestIndex,
      exchAdForestName,
      exchAdDomainMgmtMode,
      exchAdDomainTechnology }
    DESCRIPTION
        "Domain removed from exchAdDomainTable"
    ::= 166103

  exchAdManagedHostAddedTrap TRAP-TYPE
	ENTERPRISE sysmgmt
    VARIABLES {
      exchAdManagedHostIndex,
      exchAdManagedHostName,
      exchAdDomainIndex,
      exchAdDomainName,
      exchAdForestIndex,
      exchAdForestName,
      exchAdDagIndex,
      exchAdDagName,
      exchAdManagedHostTechnology,
      exchAdManagedHostExRoleMask,
      exchAdManagedHostAdRoleMask,
      exchAdManagedHostIpAddressType,
      exchAdManagedHostIpAddress,
      exchAdManagedHostMacAddress }
    DESCRIPTION
        "Managed Host added to exchAdManagedHostTable"
    ::= 166104

  exchAdManagedHostRemovedTrap TRAP-TYPE
	ENTERPRISE sysmgmt
    VARIABLES {
      exchAdManagedHostIndex,
      exchAdManagedHostName,
      exchAdDomainIndex,
      exchAdDomainName,
      exchAdForestIndex,
      exchAdForestName,
      exchAdDagIndex,
      exchAdDagName,
      exchAdManagedHostTechnology,
      exchAdManagedHostExRoleMask,
      exchAdManagedHostAdRoleMask,
      exchAdManagedHostIpAddressType,
      exchAdManagedHostIpAddress,
      exchAdManagedHostMacAddress }
    DESCRIPTION
        "Host removed from exchAdManagedHostTable"
    ::= 166105

  exchAdManagedHostPollStatusChangedTrap TRAP-TYPE
	ENTERPRISE sysmgmt
    VARIABLES {
      exchAdManagedHostIndex,
      exchAdManagedHostName,
      exchAdDomainIndex,
      exchAdDomainName,
      exchAdForestIndex,
      exchAdForestName,
      exchAdDagIndex,
      exchAdDagName,
      exchAdManagedHostPreviousPollStatus,
      exchAdManagedHostPollStatus }
    DESCRIPTION
        "Managed Host poll status changed"
    ::= 166106

  exchAdDomainControllerAddedTrap TRAP-TYPE
	ENTERPRISE sysmgmt
    VARIABLES {
      exchAdDomainControllerIndex,
      exchAdDomainControllerName,
      exchAdDomainControllerFqdn }
    DESCRIPTION
        "Domain Controller added to exchAdDomainControllerTable"
    ::= 166107

  exchAdDomainControllerRemovedTrap TRAP-TYPE
	ENTERPRISE sysmgmt
    VARIABLES {
      exchAdDomainControllerIndex,
      exchAdDomainControllerName,
      exchAdDomainControllerFqdn }
    DESCRIPTION
        "Domain Controller removed from exchAdDomainControllerTable"
    ::= 166108

  exchAdDagAddedTrap TRAP-TYPE
	ENTERPRISE sysmgmt
    VARIABLES {
      exchAdDagIndex,
      exchAdDagName,
      exchAdDagDataCenterActivationMode,
      exchAdDagIpv4Addresses,
      exchAdDagServers }
    DESCRIPTION
        "DAG added to exchAdDagTable"
    ::= 166109

  exchAdDagRemovedTrap TRAP-TYPE
	ENTERPRISE sysmgmt
    VARIABLES {
      exchAdDagIndex,
      exchAdDagName,
      exchAdDagDataCenterActivationMode,
      exchAdDagIpv4Addresses,
      exchAdDagServers }
    DESCRIPTION
        "DAG removed from exchAdDagTable"
    ::= 166110

  exchAdHostAddedToDagTrap TRAP-TYPE
	ENTERPRISE sysmgmt
    VARIABLES {
      exchAdManagedHostIndex,
      exchAdManagedHostName,
      exchAdDagIndex,
      exchAdDagName,
      exchAdDagIpv4Addresses,
      exchAdDagServers }
    DESCRIPTION
        "host added to DAG"
    ::= 166111

  exchAdHostRemovedFromDagTrap TRAP-TYPE
	ENTERPRISE sysmgmt
    VARIABLES {
      exchAdManagedHostIndex,
      exchAdManagedHostName,
      exchAdDagIndex,
      exchAdDagName,
      exchAdDagIpv4Addresses,
      exchAdDagServers }
    DESCRIPTION
        "host removed from DAG"
    ::= 166112

  exchAdTestServiceHealthCompletionStatusUpdated TRAP-TYPE
	ENTERPRISE sysmgmt
    VARIABLES {
      exchAdTestServiceHealthOwnerIndex,
      exchAdTestServiceHealthTestIndex,
      exchAdTestServiceHealthCompletionStatus,
      exchAdTestServiceHealthManagedHostExRoleMask,
      exchAdTestServiceHealthManagedHostExRoleRunningMask,
      exchAdTestServiceHealthHostIndex }
    DESCRIPTION
        "service health completion status updated"
    ::= 166113

  exchAdTestMapiConnectivityCompletionStatusUpdated TRAP-TYPE
	ENTERPRISE sysmgmt
    VARIABLES {
      exchAdTestMapiConnectivityOwnerIndex,
      exchAdTestMapiConnectivityTestIndex,
      exchAdTestMapiConnectivityCompletionStatus,
      exchAdTestMapiConnectivityLogonLatency,
      exchAdTestMapiConnectivityError,
      exchAdTestMapiConnectivityHostIndex,
      exchAdTestMapiConnectivityDatabaseIndex,
      exchAdTestMapiConnectivityMailbox }
    DESCRIPTION
        "MAPI connectivity completion status updated"
    ::= 166114

  exchAdTestExchangeSearchCompletionStatusUpdated TRAP-TYPE
	ENTERPRISE sysmgmt
    VARIABLES {
      exchAdTestExchangeSearchOwnerIndex,
      exchAdTestExchangeSearchTestIndex,
      exchAdTestExchangeSearchCompletionStatus,
      exchAdTestExchangeSearchLogonLatency,
      exchAdTestExchangeSearchError,
      exchAdTestExchangeSearchDomainControllerIndex,
      exchAdTestExchangeSearchMailbox,
      exchAdTestExchangeSearchHostIndex,
      exchAdTestExchangeSearchDatabaseIndex }
    DESCRIPTION
        "Exchange search completion status updated"
    ::= 166115

  exchAdTestMailFlowCompletionStatusUpdated TRAP-TYPE
	ENTERPRISE sysmgmt
    VARIABLES {
      exchAdTestMailFlowOwnerIndex,
      exchAdTestMailFlowTestIndex,
      exchAdTestMailFlowCompletionStatus,
      exchAdTestMailFlowMessageLatencyTime,
      exchAdTestMailFlowTestLocation,
      exchAdTestMailFlowTargetEmailAddress,
      exchAdTestMailFlowTargetHostIndex,
      exchAdTestMailFlowTargetDatabaseIndex,
      exchAdTestMailFlowDomainControllerIndex,
      exchAdTestMailFlowSourceHostIndex,
      exchAdTestMailFlowSourceSmtpAddr }
    DESCRIPTION
        "mail flow completion status updated"
    ::= 166116

  exchAdDagFailOverTrap TRAP-TYPE
	ENTERPRISE sysmgmt
    VARIABLES {
      exchAdDagIndex,
      exchAdDagName,
      exchAdDagIpv4Addresses,
      exchAdDagServers,
      exchAdDagHostIndex,
      exchAdUniversalHostName,
      exchAdDagHostOperStatus,
      exchAdDagDatabaseCopyIndex,
      exchAdDagDatabaseInventoryIndex,
      exchAdDagDatabaseCopyDbaseMountStatus,
      exchAdDagDatabaseCopyMailboxServerIndex,
      exchAdDagDatabaseCopyActiveDatabaseCopyIndex,
      exchAdDagDatabaseCopyActivationStatus,
      exchAdDagDatabaseCopyDbaseActiveCopy,
      exchAdMailboxDatabaseInventoryDatabaseName }
    DESCRIPTION
        "DAG Active Database on one host is failed/switched over to a Database copy (a passive copy) on another host"
    ::= 166117

   END
